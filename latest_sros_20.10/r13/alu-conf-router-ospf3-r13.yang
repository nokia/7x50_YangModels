module alu-conf-router-ospf3-r13 {
  yang-version "1";

  namespace "urn:alcatel-lucent.com:sros:ns:yang:conf-router-ospf3-r13";

  prefix "conf-router-ospf3-r13";

  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure OSPFv3 on SR OS based routers. 
       
       Copyright 2014-2015 Alcatel-Lucent, 2016 Nokia. All rights reserved. 
       Reproduction of this document is authorized on the condition that the 
       foregoing copyright notice is included. 
       
       This alu-conf-router-ospf3-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2021-06-11";

  grouping alu-conf-router-ospf3-r13 {
    list ospf3 {
      key "ospf-instance";
      description
          "Configure OSPFv3";
      leaf ospf-instance {
        type uint32 {
          range "0..127";
        }
        description
            "Attribute ospf-instance for ospf3";
      } //ospf-instance

      leaf router-id-create {
        type inet:ip-address;
        description
            "<ip-address>";
      } //router-id-create

      container advertise-router-capability {
        description
            "Enable/disable router advertisement capabilities";
        leaf advertise-router-capability-id {
          type enumeration {
            enum link;
            enum area;
            enum as;
          }
        } //advertise-router-capability-id

      } //container advertise-router-capability

      leaf asbr {
        type boolean;
        description
            "Configure the router as an ASBR (Autonomous System Boundary Router)";
      }

      container database-export {
        description
            "Enable/Disable database export";
        leaf identifier {
          type string;
          description
              "[0..18446744073709551615]";
        } //identifier

        leaf bgp-ls-identifier {
          type uint32;
        } //bgp-ls-identifier

      } //container database-export

      leaf disable-ldp-sync {
        type boolean;
        description
            "Disable/enable synchronization of IGP and LDP";
      }

      container export {
        description
            "Configure export route policies to determine which routes are exported from 
             the route table";
        leaf-list policy-name {
          type string {
            length "1..32";
          }
          max-elements 5;
        } //policy-name

      } //container export

      container export-limit {
        description
            "Maximum number of routes (prefixes) that can be exported into OSPF3 from the 
             route table.";
        leaf number {
          type uint32 {
            range "1..4294967295";
          }
        } //number

        leaf log {
          type uint16 {
            range "1..100";
          }
        } //log

      } //container export-limit

      container extended-lsa {
        description
            "Configure OSPF3 extended LSA mode";
        leaf mode {
          type enumeration {
            enum sparse;
            enum only;
          }
        } //mode

      } //container extended-lsa

      container external-db-overflow {
        description
            "Limit on number of AS-external-LSAs in LSDB and wait time before processing 
             these if limit is exceeded";
        leaf limit {
          type int64 {
            range "-1..2147483647";
          }
          description
              "[0..2147483647]";
        } //limit

        leaf interval {
          type int32 {
            range "0..2147483647";
          }
          description
              "[0..2147483647]";
        } //interval

      } //container external-db-overflow

      container external-preference {
        description
            "Preference for OSPF3 external routes";
        leaf preference {
          type uint16 {
            range "1..255";
          }
          default 150;
        } //preference

      } //container external-preference

      container import {
        description
            "Configure import route policies to determine which routes are imported into 
             the route table";
        leaf-list policy-name {
          type string {
            length "1..32";
          }
          max-elements 5;
        } //policy-name

      } //container import

      container loopfree-alternate {
        status "obsolete";
        description
            "Enable/disable loopfree-alternate for OSPF3";
        leaf remote-lfa {
          type boolean;
        } //remote-lfa

        leaf max-pq-cost {
          type uint32;
        } //max-pq-cost

        leaf ti-lfa {
          type boolean;
        } //ti-lfa

        leaf max-sr-frr-labels {
          type uint32 {
            range "0..3";
          }
          default 2;
        } //max-sr-frr-labels

      } //container loopfree-alternate

      container loopfree-alternate-exclude {
        status "obsolete";
        description
            "Configure LFA exclude policies";
        leaf-list prefix-policy {
          type string {
            length "1..32";
          }
          max-elements 5;
        } //prefix-policy

      } //container loopfree-alternate-exclude

      leaf multicast-import {
        type boolean;
        description
            "Enable/disable submission of routes into the multicast Route Table Manager by 
             OSPF3";
      }

      container overload {
        description
            "Configure the local router so that it appears to be overloaded";
        leaf timeout {
          type uint32 {
            range "60..1800";
          }
        } //timeout

      } //container overload

      leaf overload-include-ext-1 {
        type boolean;
        description
            "Enable/disable OSPF maximum metric usage for external type-1 routes in case of 
             overload";
      }

      leaf overload-include-ext-2 {
        type boolean;
        description
            "Enable/disable OSPF maximum metric usage for external type-2 routes in case of 
             overload";
      }

      leaf overload-include-stub {
        type boolean;
        description
            "Enable/disable OSPF3 maximum metric usage for stub advertisement in case of 
             overload";
      }

      container overload-on-boot {
        description
            "Configure the local router so that it appears to be overloaded at boot up";
        leaf timeout {
          type uint32 {
            range "60..1800";
          }
        } //timeout

      } //container overload-on-boot

      container preference {
        description
            "Preference for OSPF3 internal routes";
        leaf preference {
          type uint16 {
            range "1..255";
          }
          default 10;
        } //preference

      } //container preference

      container reference-bandwidth {
        description
            "Reference bandwidth that provides a reference for the default costing of 
             interfaces";
        leaf bandwidth-in-kbps {
          type uint32 {
            range "1..4000000000";
          }
        } //bandwidth-in-kbps

        leaf bandwidth-in-kbps-1 {
          type string;
          description
              "Attribute bandwidth-in-kbps for reference-bandwidth";
        } //bandwidth-in-kbps-1

        leaf zbps {
          type uint32 {
            range "1..18";
          }
        } //zbps

        leaf ebps {
          type uint32 {
            range "1..999";
          }
        } //ebps

        leaf pbps {
          type uint32 {
            range "1..999";
          }
        } //pbps

        leaf tbps {
          type string;
          description
              "Attribute Tera-bps for reference-bandwidth";
        } //tbps

        leaf gbps {
          type uint32 {
            range "1..999";
          }
        } //gbps

        leaf mbps {
          type uint32 {
            range "1..999";
          }
        } //mbps

        leaf kbps {
          type uint32 {
            range "1..999";
          }
        } //kbps

      } //container reference-bandwidth

      list rib-priority {
        key "high";
        description
            "Configure RIB priority for OSPF";
        leaf high {
          type boolean;
        } //high

        leaf prefix-list-name {
          type string {
            length "1..32";
          }
        } //prefix-list-name

      } //list rib-priority

      container router-id {
        description
            "Configure router-id for OSPF3";
        leaf ip-address {
          type inet:ip-address;
        } //ip-address

      } //container router-id

      container rtr-adv-lsa-limit {
        description
            "Configure max LSA's we accept from 1 advertising router";
        leaf rtr-adv-lsa-limit-id {
          type uint32 {
            range "1..4294967295";
          }
        } //rtr-adv-lsa-limit-id

        leaf log-only {
          type boolean;
        } //log-only

        leaf threshold {
          type uint32 {
            range "0..100";
          }
        } //threshold

        leaf overload-timeout {
          type boolean;
        } //overload-timeout

        leaf seconds {
          type uint32 {
            range "1..1800";
          }
        } //seconds

        leaf forever {
          type boolean;
        } //forever

      } //container rtr-adv-lsa-limit

      leaf shutdown {
        type boolean;
        description
            "Administratively enable/disable the OSPF3 instance";
      }

      leaf unicast-import-disable {
        type boolean;
        description
            "Enable/disable submission of routes into the unicast Route Table Manager by 
             OSPF3";
      }

      list area {
        key "area-id";
        description
            "Configure an OSPF3 area";
        leaf area-id {
          type string;
          description
              "<ip-address> | [0..4294967295]";
        } //area-id

        leaf advertise-router-capability {
          type boolean;
          description
              "Enable/disable router advertisement capabilities";
        }

        list area-range {
          key "ipv4-prefix-mask---ipv6-prefix-prefix-length";
          description
              "Create/delete address ranges on an ABR for route summarization or suppression";
          leaf ipv4-prefix-mask---ipv6-prefix-prefix-length {
            type string;
            description
                "Attribute ipv4-prefix/mask | ipv6-prefix/prefix-length for area-range";
          } //ipv4-prefix-mask---ipv6-prefix-prefix-length

          leaf advertise-not-advertise {
            type enumeration {
              enum advertise;
              enum not-advertise;
            }
            description
                "keywords";
          } //advertise-not-advertise

        } //list area-range

        leaf blackhole-aggregate {
          type boolean;
          description
              "Add/Remove low priority blackhole route to avoid loops";
        }

        leaf database-export-exclude {
          type boolean;
          description
              "Enable/disable database export for OSPF3 at area level";
        }

        container export {
          description
              "Configure export policies to determine whether a route is exported as summary 
               type 3/inter-area-prefix-LSA from this Area to another Area";
          leaf-list policy-name {
            type string {
              length "1..32";
            }
            max-elements 5;
          } //policy-name

        } //container export

        container extended-lsa {
          description
              "Configure OSPF3 extended LSA mode";
          leaf mode {
            type enumeration {
              enum inherit;
              enum only;
            }
          } //mode

        } //container extended-lsa

        container import {
          description
              "Configure import policies to determine whether a route is imported as summary 
               type 3/inter-area-prefix-LSA from another Area into this Area";
          leaf-list policy-name {
            type string {
              length "1..32";
            }
            max-elements 5;
          } //policy-name

        } //container import

        container key-rollover-interval {
          description
              "Configure the key rollover interval";
          leaf seconds {
            type uint32 {
              range "10..300";
            }
          } //seconds

        } //container key-rollover-interval

        leaf loopfree-alternate-exclude {
          type boolean;
          description
              "Enable/disable fast re-route capability for OSPF at area level";
        }

        list interface {
          key "ip-int-name";
          description
              "Configure OSPF3 on an IP interface";
          leaf ip-int-name {
            type string {
              length "1..32";
            }
          } //ip-int-name

          leaf secondary {
            type boolean;
          } //secondary

          leaf advertise-router-capability {
            type boolean;
            description
                "Enable/disable router advertisement capabilities";
          }

          container authentication {
            description
                "Configure OSPFv3 authentication";
            leaf inbound {
              type string {
                length "1..32";
              }
            } //inbound

            leaf outbound {
              type string {
                length "1..32";
              }
              description
                  "sa-name";
            } //outbound

            leaf bidirectional {
              type string {
                length "1..32";
              }
              description
                  "sa-name";
            } //bidirectional

          } //container authentication

          container bfd-enable {
            description
                "Enable BFD";
            leaf remain-down-on-failure {
              type boolean;
              description
                  "keyword - Forces adjacency down on BFD failure";
            } //remain-down-on-failure

          } //container bfd-enable

          container dead-interval {
            description
                "Time OSPF3 waits without receiving hello packets before declaring a neighbor 
                 down";
            leaf seconds {
              type uint32 {
                range "2..65535";
              }
            } //seconds

          } //container dead-interval

          container hello-interval {
            description
                "Time interval between OSPF3 hellos issued on the interface";
            leaf seconds {
              type uint32 {
                range "1..65535";
              }
            } //seconds

          } //container hello-interval

          container interface-type {
            description
                "Configure the interface type to be either broadcast or point-to-point";
            leaf interface-type-id {
              type enumeration {
                enum broadcast;
                enum point-to-point;
                enum non-broadcast;
              }
            } //interface-type-id

          } //container interface-type

          container lfa-policy-map {
            description
                "Configure a route-next-hop template";
            leaf route-nh-template {
              type string {
                length "1..32";
              }
            } //route-nh-template

          } //container lfa-policy-map

          container load-balancing-weight {
            description
                "Configure load-balancing-weight";
            leaf load-balancing-weight-id {
              type uint32 {
                range "1..4294967295";
              }
            } //load-balancing-weight-id

          } //container load-balancing-weight

          leaf loopfree-alternate-exclude {
            type boolean;
            description
                "Enable/disable fast re-route capability for OSPF at interface level (only 
                 valid for primary interface)";
          }

          container lsa-filter-out {
            description
                "Configure LSA flooding reduction";
            leaf all-except-own-rtrlsa-except-own-rtrlsa-and-defaults {
              type enumeration {
                enum all;
                enum except-own-rtrlsa;
                enum except-own-rtrlsa-and-defaults;
              }
            } //all-except-own-rtrlsa-except-own-rtrlsa-and-defaults

          } //container lsa-filter-out

          container metric {
            description
                "Configure an explicit route cost metric for the interface";
            leaf metric {
              type uint32 {
                range "1..65535";
              }
            } //metric

          } //container metric

          container mtu {
            description
                "Enter the mtu to be used by OSPF3 for this logical interface";
            leaf mtu-bytes {
              type string;
              description
                  "Attribute mtu-bytes for mtu";
            } //mtu-bytes

          } //container mtu

          list neighbor {
            key "ipv6-address";
            description
                "Configure neighbor addresses for the interface";
            leaf ipv6-address {
              type inet:ipv6-address;
            } //ipv6-address

          } //list neighbor

          container node-sid {
            description
                "Configure node-sid";
            leaf index {
              type uint32;
            } //index

            leaf label {
              type uint32 {
                range "1..4294967295";
              }
            } //label

            leaf clear-n-flag {
              type boolean;
            } //clear-n-flag

          } //container node-sid

          leaf passive {
            type boolean;
            description
                "Add/remove the passive property to/from the interface";
          }

          container poll-interval {
            description
                "Configure the poll-interval for this interface";
            leaf poll-interval-id {
              type uint32;
            } //poll-interval-id

          } //container poll-interval

          container priority {
            description
                "Priority of the interface that is used in the designated router election on 
                 the subnet";
            leaf number {
              type uint16 {
                range "0..255";
              }
            } //number

          } //container priority

          container retransmit-interval {
            description
                "Time OSPF3 will wait before retransmitting an unacknowledged LSA to a neighbor";
            leaf seconds {
              type uint32 {
                range "1..1800";
              }
            } //seconds

          } //container retransmit-interval

          container rib-priority {
            description
                "Configure RIB priority for OSPF3";
            leaf high {
              type boolean;
            } //high

          } //container rib-priority

          leaf shutdown {
            type boolean;
            description
                "Administratively enable/disable OSPF3 on the interface";
          }

          leaf sid-protection {
            type boolean;
            description
                "Enable/disable the SID protection";
          }

          container transit-delay {
            description
                "Time that it takes to transmit an LSA on the interface";
            leaf seconds {
              type uint32 {
                range "1..1800";
              }
            } //seconds

          } //container transit-delay

        } //list interface

        container nssa {
          presence
              "Configure an OSPF3 Not So Stubby Area (NSSA)";
          list area-range {
            key "ipv4-prefix-mask---ipv6-prefix-prefix-length";
            description
                "Create/delete address ranges for route summarization or suppression";
            leaf ipv4-prefix-mask---ipv6-prefix-prefix-length {
              type string;
              description
                  "Attribute ipv4-prefix/mask | ipv6-prefix/prefix-length for area-range";
            } //ipv4-prefix-mask---ipv6-prefix-prefix-length

            leaf advertise-not-advertise {
              type enumeration {
                enum advertise;
                enum not-advertise;
              }
              description
                  "keywords";
            } //advertise-not-advertise

          } //list area-range

          container originate-default-route {
            description
                "Enable/disable generation of default route and its LSA type (ie-pfx or nssa) 
                 into the NSSA";
            leaf type-nssa {
              type boolean;
            } //type-nssa

            leaf no-adjacency-check {
              type boolean;
            } //no-adjacency-check

          } //container originate-default-route

          leaf redistribute-external {
            type boolean;
            description
                "Enable/disable redistribution of external routes into the NSSA";
          }

          leaf summaries {
            type boolean;
            description
                "Enable/disable sending summary (type ie-pfx) LSAs into the NSSA";
          }

        } //container nssa

        container stub {
          presence
              "Configure an OSPF3 stub area";
          container default-metric {
            description
                "Metric used by the ABR for the default route into the stub area";
            leaf metric {
              type uint32 {
                range "1..16777215";
              }
              description
                  "1..16777214";
            } //metric

          } //container default-metric

          leaf summaries {
            type boolean;
            description
                "Enable/disable sending summary (type 3) LSAs into the stub area";
          }

        } //container stub

        list virtual-link {
          key "router-id transit-area";
          description
              "Configure an OSPF3 virtual-link";
          leaf router-id {
            type inet:ip-address;
          } //router-id

          leaf transit-area {
            type string;
            description
                "<ip-address> | [0..4294967295]";
          } //transit-area

          container authentication {
            description
                "Configure OPSFv3 confidentiality authentication";
            leaf inbound {
              type string {
                length "1..32";
              }
            } //inbound

            leaf outbound {
              type string {
                length "1..32";
              }
              description
                  "sa-name";
            } //outbound

            leaf bidirectional {
              type string {
                length "1..32";
              }
              description
                  "sa-name";
            } //bidirectional

          } //container authentication

          container dead-interval {
            description
                "Time OSPF3 waits without receiving hello packets before declaring a 
                 virtual-neighbor down";
            leaf seconds {
              type uint32 {
                range "2..65535";
              }
              default 60;
            } //seconds

          } //container dead-interval

          container hello-interval {
            description
                "Time interval between OSPF3 hellos issued on the virtual-link";
            leaf seconds {
              type uint32 {
                range "1..65535";
              }
            } //seconds

          } //container hello-interval

          container retransmit-interval {
            description
                "Time OSPF3 will wait before retransmitting an unacknowledged LSA to a 
                 virtual-neighbor";
            leaf seconds {
              type uint32 {
                range "1..1800";
              }
            } //seconds

          } //container retransmit-interval

          leaf shutdown {
            type boolean;
            description
                "Administratively enable/disable OSPF3 on the virtual-link";
          }

          container transit-delay {
            description
                "Time that it takes to transmit an LSA on the virtual-link";
            leaf seconds {
              type uint32 {
                range "0..1800";
              }
              default 1;
              description
                  "[1..1800]";
            } //seconds

          } //container transit-delay

        } //list virtual-link

      } //list area

      container graceful-restart {
        presence
            "Enable/disable graceful-restart for OSPF3";
        leaf helper-disable {
          type boolean;
          description
              "Enable/disable graceful restart helper mode for OSPF3";
        }

        leaf strict-lsa-checking {
          type boolean;
          description
              "Enable/disable strict LSA checking during OSPF3 graceful restart";
        }

      } //container graceful-restart

      container igp-shortcut {
        description
            "Configure OSPF3 IGP shortcut";
        leaf shutdown {
          type boolean;
          description
              "Administratively enable or disable IGP shortcut";
        }

        container tunnel-next-hop {
          description
              "Configure IGP shortcut tunnel next-hop";
          container family {
            description
                "Configure IGP shortcut tunnel next-hop family";
            leaf family-id {
              type enumeration {
                enum ipv4;
                enum srv4;
                enum ipv6;
                enum srv6;
              }
            } //family-id

            container resolution {
              description
                  "Configure resolution behavior for OSPF3 routes";
              leaf resolution-id {
                type enumeration {
                  enum any;
                  enum disabled;
                  enum filter;
                  enum match-family-ip;
                }
              } //resolution-id

            } //container resolution

            container resolution-filter {
              description
                  "Configure specific tunnels to be used for resolving OSPF3 routes";
              leaf rsvp {
                type boolean;
                description
                    "Enable/Disable use of RSVP for next hop resolution";
              }

              leaf sr-te {
                type boolean;
                description
                    "Enable/Disable use of SR TE for next hop resolution";
              }

            } //container resolution-filter

          } //container family

        } //container tunnel-next-hop

      } //container igp-shortcut

      container loopfree-alternates {
        presence
            "Enable/disable fast re-route capability for OSPF3";
        container exclude {
          description
              "Configure LFA exclude policies";
          container prefix-policy {
            description
                "Configure LFA exclude prefix policies";
            leaf-list prefix-policy {
              type string {
                length "1..32";
              }
              max-elements 5;
            } //prefix-policy

          } //container prefix-policy

        } //container exclude

        container remote-lfa {
          description
              "Enable/disable remote loopfree-alternate";
          leaf max-pq-cost {
            type uint32;
            default 65535;
            description
                "[0..4294967295] - default: 65535";
          } //max-pq-cost

          container node-protect {
            description
                "Enable/disable node protection";
            leaf max-pq-nodes {
              type uint32 {
                range "1..32";
              }
              default 16;
              description
                  "[1..32] - default: 16";
            } //max-pq-nodes

          } //container node-protect

        } //container remote-lfa

        container ti-lfa {
          description
              "Enable/disable Topology Independent loopfree-alternate";
          leaf max-sr-frr-labels {
            type uint32 {
              range "0..3";
            }
            default 2;
            description
                "[0..3] - default: 2";
          } //max-sr-frr-labels

          leaf node-protect {
            type boolean;
            description
                "Enable/disable node protection";
          }

        } //container ti-lfa

      } //container loopfree-alternates

      container segment-routing {
        presence
            "Configure OSPF3 segment-routing";
        container adj-sid-hold {
          description
              "Configure adjacency SID hold time";
          leaf seconds {
            type uint32 {
              range "1..300";
            }
            default 15;
            description
                "[1..300] - default: 15";
          } //seconds

        } //container adj-sid-hold

        container prefix-sid-range {
          description
              "Configure prefix-sid-range";
          leaf global {
            type boolean;
          } //global

          leaf start-label {
            type uint32 {
              range "0..524287";
            }
          } //start-label

          leaf max-index {
            type uint32 {
              range "0..524287";
            }
          } //max-index

        } //container prefix-sid-range

        leaf shutdown {
          type boolean;
          description
              "Administratively enable or disable segment-routing";
        }

        container tunnel-mtu {
          description
              "Configure tunnel MTU size";
          leaf mtu-bytes {
            type string;
            description
                "Attribute mtu-bytes for tunnel-mtu";
          } //mtu-bytes

        } //container tunnel-mtu

        container tunnel-table-pref {
          description
              "Configure tunnel-table-preference";
          leaf tunnel-table-pref-id {
            type uint32 {
              range "1..255";
            }
          } //tunnel-table-pref-id

        } //container tunnel-table-pref

        container egress-statistics {
          description
              "Configure egress statistics for SIDs";
          leaf adj-sid {
            type boolean;
            description
                "Enable/disable stats on Adjacency SIDs";
          }

          leaf node-sid {
            type boolean;
            description
                "Enable/disable stats on Node SIDs";
          }

        } //container egress-statistics

        container ingress-statistics {
          description
              "Configure ingress statistics for SIDs";
          leaf adj-sid {
            type boolean;
            description
                "Enable/disable stats on Adjacency SIDs";
          }

          leaf node-sid {
            type boolean;
            description
                "Enable/disable stats on Node SIDs";
          }

        } //container ingress-statistics

      } //container segment-routing

      container timers {
        description
            "Configure OSPF3 timers";
        container incremental-spf-wait {
          description
              "Configure the delay before an incremental SPF calculation is started";
          leaf incremental-spf-wait {
            type uint32 {
              range "0..1000";
            }
            description
                "[0..1000] in milliseconds";
          } //incremental-spf-wait

        } //container incremental-spf-wait

        container lsa-accumulate {
          description
              "Configure the delay to accumulate multiple LSAs before advertising them to 
               neighbors";
          leaf lsa-accumulate {
            type uint32 {
              range "0..1000";
            }
            description
                "[0..1000] in milliseconds";
          } //lsa-accumulate

        } //container lsa-accumulate

        container lsa-arrival {
          description
              "Configure the minimum delay that must pass between receipt of the same LSAs 
               arriving from neighbors";
          leaf lsa-arrival-time {
            type uint32 {
              range "0..600000";
            }
            description
                "[0..600000] in milliseconds";
          } //lsa-arrival-time

        } //container lsa-arrival

        container lsa-generate {
          description
              "Configure the throttling of OSPF LSA-generation";
          leaf max-lsa-wait {
            type uint32 {
              range "10..600000";
            }
            description
                "[10..600000] in milliseconds";
          } //max-lsa-wait

          leaf lsa-generate-id {
            type uint32 {
              range "10..600000";
            }
            status "obsolete";
          } //lsa-generate-id

          leaf lsa-generate-id-2 {
            type uint32 {
              range "10..600000";
            }
            status "obsolete";
          } //lsa-generate-id-2

          leaf lsa-initial-wait {
            type uint32 {
              range "10..600000";
            }
            description
                "[10..600000] in milliseconds";
          } //lsa-initial-wait

          leaf lsa-second-wait {
            type uint32 {
              range "10..600000";
            }
            description
                "[10..600000] in milliseconds";
          } //lsa-second-wait

        } //container lsa-generate

        container redistribute-delay {
          description
              "Configure the hold down timer for external routes being redistributed in OSPF";
          leaf redistribute-delay {
            type uint32 {
              range "0..1000";
            }
            description
                "[0..1000] in milliseconds";
          } //redistribute-delay

        } //container redistribute-delay

        container spf-wait {
          description
              "Configure the maximum interval between two consecutive SPF calculations";
          leaf spf-max-wait {
            type uint32 {
              range "10..120000";
            }
            description
                "[10..120000] in milliseconds";
          } //spf-max-wait

          leaf spf-wait-id {
            type uint32 {
              range "10..100000";
            }
            status "obsolete";
          } //spf-wait-id

          leaf spf-wait-id-2 {
            type uint32 {
              range "10..100000";
            }
            status "obsolete";
          } //spf-wait-id-2

          leaf spf-initial-wait {
            type uint32 {
              range "10..100000";
            }
            description
                "[10..100000] in milliseconds";
          } //spf-initial-wait

          leaf spf-second-wait {
            type uint32 {
              range "10..100000";
            }
            description
                "[10..100000] in milliseconds";
          } //spf-second-wait

        } //container spf-wait

      } //container timers

    } //list ospf3

  } //grouping alu-conf-router-ospf3-r13

} //module  alu-conf-router-ospf3-r13
