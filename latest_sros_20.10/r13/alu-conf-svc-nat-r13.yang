module alu-conf-svc-nat-r13 {
  yang-version "1";

  namespace "urn:alcatel-lucent.com:sros:ns:yang:conf-svc-nat-r13";

  prefix "conf-svc-nat-r13";

  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure Network Address Translation on SR 
       OS based routers. 
       
       Copyright 2014-2015 Alcatel-Lucent, 2016 Nokia. All rights reserved. 
       Reproduction of this document is authorized on the condition that the 
       foregoing copyright notice is included. 
       
       This alu-conf-svc-nat-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-10-16";

  grouping alu-conf-svc-nat-r13 {
    container nat {
      description
          "Configure Network Address Translation";
      container deterministic-script {
        description
            "Configure the script generated for Deterministic NAT";
        container location {
          description
              "Configure the URL for the generated script";
          leaf remote-url {
            type string {
              length "1..180";
            }
          } //remote-url

        } //container location

      } //container deterministic-script

      list firewall-policy {
        key "name";
        description
            "Configure a firewall policy";
        leaf name {
          type string;
        } //name

        container description {
          description
              "Configure the description";
          leaf description-string {
            type string {
              length "1..80";
            }
          } //description-string

        } //container description

        container domain {
          description
              "Configure the firewall domain";
          leaf router {
            type string {
              length "1..32";
            }
            description
                "Attribute router-name for domain";
          } //router

          leaf name {
            type string;
          } //name

        } //container domain

        container filtering {
          description
              "Configure the filtering of this policy";
          leaf filtering-mode {
            type enumeration {
              enum address-and-port-dependent;
              enum endpoint-independent;
            }
          } //filtering-mode

        } //container filtering

        leaf l2-outside {
          type boolean;
          description
              "Configure the use of L2 outside NAT";
        }

        container tcp-mss-adjust {
          description
              "Configure the value to adjust the TCP Maximum Segment Size (MSS) option";
          leaf segment-size {
            type uint32 {
              range "160..10240";
            }
          } //segment-size

        } //container tcp-mss-adjust

        leaf udp-inbound-refresh {
          type boolean;
          description
              "Configure the UDP inbound refresh behavior";
        }

        container alg {
          description
              "Configure Application Level Gateway parameters of this policy";
          leaf ftp {
            type boolean;
            description
                "Enable FTP ALG";
          }

          leaf rtsp {
            type boolean;
            description
                "Enable RTSP ALG";
          }

          leaf sip {
            type boolean;
            description
                "Enable SIP ALG";
          }

        } //container alg

        container port-limits {
          description
              "Configure the port limits of this policy";
          container forwarding {
            description
                "Configure the maximum number of port forwarding entries";
            leaf limit {
              type uint16 {
                range "1..64";
              }
            } //limit

          } //container forwarding

        } //container port-limits

        container priority-sessions {
          presence
              "Configure the prioritized sessions of this policy";
          list fc {
            key "fc-name";
            description
                "Configure the forwarding classes that have their sessions prioritized";
            leaf fc-name {
              type enumeration {
                enum be;
                enum l2;
                enum af;
                enum l1;
                enum h2;
                enum ef;
                enum h1;
                enum nc;
              }
            } //fc-name

          } //list fc

        } //container priority-sessions

        container session-limits {
          description
              "Configure the session limits of this policy";
          container max {
            description
                "Configure the session limit of this policy";
            leaf num-sessions {
              type uint32 {
                range "1..65535";
              }
            } //num-sessions

          } //container max

          container reserved {
            description
                "Configure the number of sessions reserved for prioritized sessions";
            leaf num-sessions {
              type uint16 {
                range "1..65534";
              }
            } //num-sessions

          } //container reserved

          container watermarks {
            description
                "Configure the session watermarks of this policy";
            leaf high {
              type uint32 {
                range "1..100";
              }
            } //high

            leaf low {
              type uint32 {
                range "0..99";
              }
            } //low

          } //container watermarks

        } //container session-limits

        container timeouts {
          presence
              "Configure the session idle timeouts of this policy";
          container icmp6-query {
            description
                "Configure the timeout applied to an ICMP Query session";
            leaf min {
              type uint32 {
                range "1..4";
              }
            } //min

            leaf sec {
              type uint32 {
                range "1..59";
              }
            } //sec

          } //container icmp6-query

          container sip {
            description
                "Configure SIP inactive media timeout";
            leaf hrs {
              type uint32 {
                range "1..2";
              }
            } //hrs

            leaf min {
              type uint32 {
                range "1..59";
              }
            } //min

            leaf sec {
              type uint32 {
                range "1..59";
              }
            } //sec

          } //container sip

          container tcp-established {
            description
                "Configure the idle timeout applied to a TCP session in the established state";
            leaf hrs {
              type uint32 {
                range "1..24";
              }
            } //hrs

            leaf min {
              type uint32 {
                range "1..59";
              }
            } //min

            leaf sec {
              type uint32 {
                range "1..59";
              }
            } //sec

          } //container tcp-established

          container tcp-rst {
            description
                "Configure the time after receiving RST before a TCP session can return to the 
                 state LISTEN";
            leaf min {
              type uint32 {
                range "1..4";
              }
            } //min

            leaf sec {
              type uint32 {
                range "1..59";
              }
            } //sec

          } //container tcp-rst

          container tcp-syn {
            description
                "Configure the timeout applied to a TCP session when synchronizing its initial 
                 sequence";
            leaf hrs {
              type uint32 {
                range "1..24";
              }
            } //hrs

            leaf min {
              type uint32 {
                range "1..59";
              }
            } //min

            leaf sec {
              type uint32 {
                range "1..59";
              }
            } //sec

          } //container tcp-syn

          container tcp-time-wait {
            description
                "Configure the timeout applied to a TCP session in the time-wait state";
            leaf min {
              type uint32 {
                range "1..4";
              }
            } //min

            leaf sec {
              type uint32 {
                range "1..59";
              }
            } //sec

          } //container tcp-time-wait

          container tcp-transitory {
            description
                "Configure the idle timeout applied to a TCP session in a transitory state";
            leaf hrs {
              type uint32 {
                range "1..24";
              }
            } //hrs

            leaf min {
              type uint32 {
                range "1..59";
              }
            } //min

            leaf sec {
              type uint32 {
                range "1..59";
              }
            } //sec

          } //container tcp-transitory

          container udp {
            description
                "Configure the UDP mapping timeout";
            leaf hrs {
              type uint32 {
                range "1..24";
              }
            } //hrs

            leaf min {
              type uint32 {
                range "1..59";
              }
            } //min

            leaf sec {
              type uint32 {
                range "1..59";
              }
            } //sec

          } //container udp

          container udp-dns {
            description
                "Configure the timeout applied to a UDP session with destination port 53";
            leaf hrs {
              type uint32 {
                range "1..24";
              }
            } //hrs

            leaf min {
              type uint32 {
                range "1..59";
              }
            } //min

            leaf sec {
              type uint32 {
                range "1..59";
              }
            } //sec

          } //container udp-dns

          container udp-initial {
            description
                "Configure the UDP mapping timeout applied to new sessions";
            leaf min {
              type uint32 {
                range "1..59";
              }
            } //min

            leaf sec {
              type uint32 {
                range "1..59";
              }
            } //sec

          } //container udp-initial

          container unknown-protocol {
            description
                "Configure the timeout for flows with an unknown protocol";
            leaf hrs {
              type uint32 {
                range "1..24";
              }
            } //hrs

            leaf min {
              type uint32 {
                range "1..59";
              }
            } //min

            leaf sec {
              type uint32 {
                range "1..59";
              }
            } //sec

          } //container unknown-protocol

        } //container timeouts

        container unknown-protocols {
          description
              "Allow traffic flows for unknown protocols";
          container protocol {
            description
                "Add or remove a protocol";
            leaf number {
              type uint32 {
                range "0..255";
              }
            } //number

            leaf any {
              type boolean;
              description
                  "keyword - allow flows with any protocol";
            } //any

          } //container protocol

        } //container unknown-protocols

      } //list firewall-policy

      list map-domain {
        key "domain-name";
        description
            "Configure a domain for Mapping of Address and Port with Translation (MAP-T)";
        leaf domain-name {
          type string;
        } //domain-name

        container description {
          description
              "Configure a description";
          leaf description-string {
            type string {
              length "1..80";
            }
          } //description-string

        } //container description

        container dmr-prefix {
          description
              "Configure the Default Mapping Rule prefix";
          leaf dmr-prefix {
            type string;
            description
                "Attribute dmr-prefix for dmr-prefix";
          } //dmr-prefix

        } //container dmr-prefix

        container mtu {
          description
              "Configure the MTU";
          leaf mtu-id {
            type uint32 {
              range "160..8686";
            }
          } //mtu-id

        } //container mtu

        leaf shutdown {
          type boolean;
          description
              "Disable or enable the map domain";
        }

        container tcp-mss-adjust {
          description
              "Configure the value to adjust the TCP Maximum Segment Size (MSS) option";
          leaf segment-size {
            type uint32 {
              range "160..8626";
            }
          } //segment-size

        } //container tcp-mss-adjust

        container ip-fragmentation {
          presence
              "Configure IP fragmentation options";
          leaf v6-frag-header {
            type boolean;
            description
                "Enable/disable adding an IPv6 fragmentation header when a non-fragmented IPv4 
                 packet with DF=0 is translated into IPv6";
          }

        } //container ip-fragmentation

        list mapping-rule {
          key "rule-name";
          description
              "Configure a mapping rule";
          leaf rule-name {
            type string;
          } //rule-name

          container description {
            description
                "Configure a description for this rule";
            leaf description-string {
              type string {
                length "1..80";
              }
            } //description-string

          } //container description

          container ea-length {
            description
                "Configure the length of the EA bits field in the End-user IPv6 prefix part of 
                 the IPv6 Map Address";
            leaf ea-length-id {
              type uint32 {
                range "1..48";
              }
            } //ea-length-id

          } //container ea-length

          container ipv4-prefix {
            description
                "Configure the IPv4 prefix";
            leaf prefix {
              type inet:ip-prefix;
              description
                  "Attribute prefix for ipv4-prefix";
            } //prefix

          } //container ipv4-prefix

          container psid-offset {
            description
                "Configure the offset of the Port Set ID (PSID) within a 16 bits wide port 
                 space";
            leaf psid-offset-id {
              type uint32 {
                range "0..16";
              }
            } //psid-offset-id

          } //container psid-offset

          container rule-prefix {
            description
                "Configure the IPv6 prefix";
            leaf rule-prefix {
              type string;
              description
                  "Attribute rule-prefix for rule-prefix";
            } //rule-prefix

          } //container rule-prefix

          leaf shutdown {
            type boolean;
            description
                "Disable or enable the mapping rule";
          }

        } //list mapping-rule

      } //list map-domain

      list nat-classifier {
        key "classifier-name";
        description
            "Configure rules to classify traffic for NAT";
        leaf classifier-name {
          type string;
        } //classifier-name

        container default-action {
          description
              "Configure the action to take for a packet that does not match any of the rules 
               of this classifier";
          leaf default-action-id {
            type enumeration {
              enum dnat;
              enum forward;
            }
          } //default-action-id

          leaf ip-address {
            type inet:ip-address;
            description
                "a.b.c.d";
          } //ip-address

        } //container default-action

        container default-dnat-ip-address {
          description
              "Configure the default IP address to substitute for the destination IP address";
          leaf ip-address {
            type inet:ip-address;
            description
                "a.b.c.d";
          } //ip-address

        } //container default-dnat-ip-address

        container description {
          description
              "Configure a description";
          leaf description-string {
            type string {
              length "1..80";
            }
          } //description-string

        } //container description

        list entry {
          key "entry-id";
          description
              "Configure a NAT classifier rule";
          leaf entry-id {
            type uint32 {
              range "1..1000";
            }
          } //entry-id

          container action {
            description
                "Configure the action for matching packets";
            leaf action-id {
              type enumeration {
                enum dnat;
                enum forward;
              }
            } //action-id

            leaf ip-address {
              type inet:ip-address;
              description
                  "a.b.c.d";
            } //ip-address

          } //container action

          container description {
            description
                "Configure a description";
            leaf description-string {
              type string {
                length "1..80";
              }
            } //description-string

          } //container description

          container match {
            description
                "Configure the match criteria for this entry";
            leaf protocol {
              type enumeration {
                enum udp;
                enum tcp;
              }
            } //protocol

            container dst-port-range {
              description
                  "Configure the destination IP ports to match";
              leaf start {
                type uint16;
              } //start

              leaf end {
                type uint16;
                description
                    "port-number";
              } //end

            } //container dst-port-range

            container foreign-ip {
              description
                  "Configure the foreign IP address to match. The foreign IP address is the 
                   destination IP address received at the inside, before address translation";
              leaf ip-address {
                type inet:ip-address;
                description
                    "a.b.c.d";
              } //ip-address

            } //container foreign-ip

          } //container match

        } //list entry

      } //list nat-classifier

      list nat-policy {
        key "nat-policy-name";
        description
            "Configure a NAT policy";
        leaf nat-policy-name {
          type string {
            length "1..32";
          }
        } //nat-policy-name

        container block-limit {
          description
              "Configure the maximum number of port blocks per subscriber";
          leaf block-limit-id {
            type uint16 {
              range "1..40";
            }
          } //block-limit-id

        } //container block-limit

        container description {
          description
              "Configure the description of this policy";
          leaf description-string {
            type string {
              length "1..80";
            }
          } //description-string

        } //container description

        container filtering {
          description
              "Configure the filtering of this policy";
          leaf filtering-mode {
            type enumeration {
              enum address-and-port-dependent;
              enum endpoint-independent;
            }
          } //filtering-mode

        } //container filtering

        container ipfix-export-policy {
          description
              "Configure the IPFIX export policy";
          leaf ipfix-export-policy-string {
            type string {
              length "1..32";
            }
          } //ipfix-export-policy-string

        } //container ipfix-export-policy

        leaf l2-outside {
          type boolean;
          description
              "Configure the use of L2 outside NAT";
        }

        container pool {
          description
              "Configure the NAT pool of this policy";
          leaf nat-pool-name {
            type string {
              length "1..32";
            }
          } //nat-pool-name

          leaf router {
            type string {
              length "1..32";
            }
            description
                "Attribute router-instance for pool";
          } //router

          leaf service-name {
            type string;
          } //service-name

        } //container pool

        container port-forwarding-range {
          description
              "Configure the port forwarding range";
          leaf range-end {
            type uint16 {
              range "1023..65535";
            }
          } //range-end

        } //container port-forwarding-range

        leaf reset-unknown-tcp {
          type boolean;
          description
              "Configure the send of TCP RST upon non-SYN TCP message for unknown flow";
        }

        container syslog-export-policy {
          description
              "Configure the syslog export policy";
          leaf policy-name {
            type string;
          } //policy-name

        } //container syslog-export-policy

        container tcp-mss-adjust {
          description
              "Configure the value to adjust the TCP Maximum Segment Size (MSS) option";
          leaf segment-size {
            type uint32 {
              range "160..10240";
            }
          } //segment-size

        } //container tcp-mss-adjust

        leaf udp-inbound-refresh {
          type boolean;
          description
              "Configure the UDP inbound refresh behavior";
        }

        container alg {
          description
              "Configure Application Level Gateway parameters of this policy";
          leaf ftp {
            type boolean;
            description
                "Enable FTP ALG";
          }

          leaf pptp {
            type boolean;
            description
                "Enable PPTP ALG";
          }

          leaf rtsp {
            type boolean;
            description
                "Enable RTSP ALG";
          }

          leaf sip {
            type boolean;
            description
                "Enable SIP ALG";
          }

        } //container alg

        container dnat {
          presence
              "Configure Destination NAT";
          container dnat-only {
            description
                "Configure Destination-NAT-only mode of operation";
            leaf router {
              type string {
                length "1..32";
              }
              description
                  "Attribute router-instance for dnat-only";
            } //router

            leaf nat-group {
              type uint32 {
                range "1..4";
              }
            } //nat-group

          } //container dnat-only

          container nat-classifier {
            description
                "Configure the NAT classifier";
            leaf classifier-name {
              type string;
            } //classifier-name

          } //container nat-classifier

        } //container dnat

        container port-limits {
          description
              "Configure the port limits of this policy";
          container forwarding {
            description
                "Configure the maximum number of port forwarding entries";
            leaf limit {
              type uint16 {
                range "1..64";
              }
            } //limit

          } //container forwarding

          container reserved {
            description
                "Configure the number of ports reserved for prioritized sessions";
            leaf num-ports {
              type uint64 {
                range "1..65534";
              }
            } //num-ports

          } //container reserved

          container watermarks {
            description
                "Configure the port usage watermarks of this policy";
            leaf high {
              type uint32 {
                range "1..100";
              }
            } //high

            leaf low {
              type uint32 {
                range "0..99";
              }
            } //low

          } //container watermarks

        } //container port-limits

        container priority-sessions {
          presence
              "Configure the prioritized sessions of this policy";
          list fc {
            key "fc-name";
            description
                "Configure the forwarding classes that have their sessions prioritized";
            leaf fc-name {
              type enumeration {
                enum be;
                enum l2;
                enum af;
                enum l1;
                enum h2;
                enum ef;
                enum h1;
                enum nc;
              }
            } //fc-name

          } //list fc

        } //container priority-sessions

        container session-limits {
          description
              "Configure the session limits of this policy";
          container max {
            description
                "Configure the session limit of this policy";
            leaf num-sessions {
              type string;
              description
                  "Attribute num-sessions for max";
            } //num-sessions

          } //container max

          container reserved {
            description
                "Configure the number of sessions reserved for prioritized sessions";
            leaf num-sessions {
              type uint16 {
                range "1..65534";
              }
            } //num-sessions

          } //container reserved

          container watermarks {
            description
                "Configure the session watermarks of this policy";
            leaf high {
              type uint32 {
                range "1..100";
              }
            } //high

            leaf low {
              type uint32 {
                range "0..99";
              }
            } //low

          } //container watermarks

        } //container session-limits

        container timeouts {
          presence
              "Configure the session idle timeouts of this policy";
          container icmp-query {
            description
                "Configure the timeout applied to an ICMPv4 or ICMPv6 Query session";
            leaf min {
              type uint32 {
                range "1..4";
              }
            } //min

            leaf sec {
              type uint32 {
                range "1..59";
              }
            } //sec

          } //container icmp-query

          container sip {
            description
                "Configure SIP inactive media timeout";
            leaf hrs {
              type uint32 {
                range "1..2";
              }
            } //hrs

            leaf min {
              type uint32 {
                range "1..59";
              }
            } //min

            leaf sec {
              type uint32 {
                range "1..59";
              }
            } //sec

          } //container sip

          container subscriber-retention {
            description
                "Configure the time a subscribers' IP address is kept after all hosts and port 
                 blocks have expired";
            leaf hrs {
              type uint32 {
                range "1..24";
              }
            } //hrs

            leaf min {
              type uint32 {
                range "1..59";
              }
            } //min

          } //container subscriber-retention

          container tcp-established {
            description
                "Configure the idle timeout applied to a TCP session in the established state";
            leaf hrs {
              type uint32 {
                range "1..24";
              }
            } //hrs

            leaf min {
              type uint32 {
                range "1..59";
              }
            } //min

            leaf sec {
              type uint32 {
                range "1..59";
              }
            } //sec

          } //container tcp-established

          container tcp-rst {
            description
                "Configure the time after receiving RST before a TCP session can return to the 
                 state LISTEN";
            leaf min {
              type uint32 {
                range "1..4";
              }
            } //min

            leaf sec {
              type uint32 {
                range "1..59";
              }
            } //sec

          } //container tcp-rst

          container tcp-syn {
            description
                "Configure the timeout applied to a TCP session when synchronizing its initial 
                 sequence";
            leaf hrs {
              type uint32 {
                range "1..24";
              }
            } //hrs

            leaf min {
              type uint32 {
                range "1..59";
              }
            } //min

            leaf sec {
              type uint32 {
                range "1..59";
              }
            } //sec

          } //container tcp-syn

          container tcp-time-wait {
            description
                "Configure the timeout applied to a TCP session in the time-wait state";
            leaf min {
              type uint32 {
                range "1..4";
              }
            } //min

            leaf sec {
              type uint32 {
                range "1..59";
              }
            } //sec

          } //container tcp-time-wait

          container tcp-transitory {
            description
                "Configure the idle timeout applied to a TCP session in a transitory state";
            leaf hrs {
              type uint32 {
                range "1..24";
              }
            } //hrs

            leaf min {
              type uint32 {
                range "1..59";
              }
            } //min

            leaf sec {
              type uint32 {
                range "1..59";
              }
            } //sec

          } //container tcp-transitory

          container udp {
            description
                "Configure the UDP mapping timeout";
            leaf hrs {
              type uint32 {
                range "1..24";
              }
            } //hrs

            leaf min {
              type uint32 {
                range "1..59";
              }
            } //min

            leaf sec {
              type uint32 {
                range "1..59";
              }
            } //sec

          } //container udp

          container udp-dns {
            description
                "Configure the timeout applied to a UDP session with destination port 53";
            leaf hrs {
              type uint32 {
                range "1..24";
              }
            } //hrs

            leaf min {
              type uint32 {
                range "1..59";
              }
            } //min

            leaf sec {
              type uint32 {
                range "1..59";
              }
            } //sec

          } //container udp-dns

          container udp-initial {
            description
                "Configure the UDP mapping timeout applied to new sessions";
            leaf min {
              type uint32 {
                range "1..59";
              }
            } //min

            leaf sec {
              type uint32 {
                range "1..59";
              }
            } //sec

          } //container udp-initial

        } //container timeouts

      } //list nat-policy

      list nat-prefix-list {
        key "name";
        description
            "Configure a NAT prefix list";
        leaf name {
          type string;
        } //name

        leaf application {
          type enumeration {
            enum l2-aware-dest-to-policy;
            enum dnat-only-subscribers;
          }
        } //application

        list prefix {
          key "ip-prefix-length";
          description
              "Configure a NAT prefix";
          leaf ip-prefix-length {
            type inet:ip-prefix;
            description
                "ip-prefix a.b.c.d (host bits must be 0) 
                 length [0..32]";
          } //ip-prefix-length

          leaf nat-policy {
            type string {
              length "1..32";
            }
          } //nat-policy

        } //list prefix

      } //list nat-prefix-list

      list pcp-server-policy {
        key "name";
        description
            "Configure a PCP server policy";
        leaf name {
          type string {
            length "1..32";
          }
        } //name

        container description {
          description
              "Configure the description of this policy";
          leaf description-string {
            type string {
              length "1..80";
            }
          } //description-string

        } //container description

        container lifetime {
          description
              "Configure the lifetime of explicit mappings made by the PCP servers";
          leaf minimum {
            type uint32 {
              range "60..86399";
            }
          } //minimum

          leaf maximum {
            type uint32 {
              range "61..86400";
            }
          } //maximum

        } //container lifetime

        container max-description-size {
          description
              "Configure the maximum length of mapping descriptions made by the PCP servers";
          leaf size {
            type uint8 {
              range "1..64";
            }
          } //size

        } //container max-description-size

        leaf reuse-ext-ip {
          type boolean;
          description
              "Reuse the external IP address assigned to a subscriber when the requested 
               well-known port/external IP mapping is not available";
        }

        container version {
          description
              "Configure the accepted protocol version range";
          leaf minimum {
            type uint16 {
              range "1..255";
            }
          } //minimum

          leaf maximum {
            type uint16 {
              range "1..255";
            }
          } //maximum

        } //container version

        container opcode {
          presence
              "Configure the PCP opcodes supported by the PCP servers";
          leaf announce {
            type boolean;
            description
                "Enable/disable support for the ANNOUNCE opcode";
          }

          leaf get {
            type boolean;
            description
                "Enable/disable support for the GET opcode";
          }

          leaf map {
            type boolean;
            description
                "Enable/disable support for the MAP opcode";
          }

        } //container opcode

        container option {
          presence
              "Configure the PCP options supported by the PCP servers";
          leaf description {
            type boolean;
            description
                "Enable/disable support for the DESCRIPTION option";
          }

          leaf next {
            type boolean;
            description
                "Enable/disable support for the NEXT option";
          }

          leaf port-reservation {
            type boolean;
            description
                "Enable/disable support for the PORT_RESERVATION_OPTION option";
          }

          leaf port-set {
            type boolean;
            description
                "Enable/disable support for the PORT_SET option";
          }

          leaf prefer-failure {
            type boolean;
            description
                "Enable/disable support for the PREFER_FAILURE option";
          }

          leaf third-party {
            type boolean;
            description
                "Enable/disable support for the THIRD_PARTY option";
          }

        } //container option

      } //list pcp-server-policy

      container port-forwarding {
        description
            "Configure NAT port forwarding";
        list l2-aware {
          key "subscriber ip protocol port";
          description
              "Configure a Layer-2-Aware NAT port forwarding entry";
          leaf subscriber {
            type string;
            description
                "Attribute sub-ident-string for l2-aware";
          } //subscriber

          leaf ip {
            type inet:ip-address;
            description
                "a.b.c.d";
          } //ip

          leaf protocol {
            type enumeration {
              enum tcp;
              enum udp;
            }
          } //protocol

          leaf port {
            type uint16 {
              range "1..65535";
            }
            description
                "[1..65535]";
          } //port

          leaf outside-ip {
            type inet:ip-address;
            description
                "ip-address";
          } //outside-ip

          leaf outside-port {
            type uint16 {
              range "1..65535";
            }
            description
                "port";
          } //outside-port

          leaf nat-policy {
            type string;
          } //nat-policy

          leaf member {
            type uint16;
          } //member

          leaf port-range-start {
            type uint32 {
              range "0..65535";
            }
            description
                "port";
          } //port-range-start

        } //list l2-aware

        list lsn {
          key "router b4 ip protocol port nat-policy";
          description
              "Configure a Large Scale NAT port forwarding entry";
          leaf router {
            type string {
              length "1..32";
            }
            description
                "<router-name>|<service-id>";
          } //router

          leaf b4 {
            type inet:ipv6-address;
            description
                "Attribute ipv6-address for lsn";
          } //b4

          leaf aftr {
            type inet:ipv6-address;
            description
                "ipv6-address";
          } //aftr

          leaf ip {
            type string;
            description
                "Attribute ip-address for lsn";
          } //ip

          leaf protocol {
            type enumeration {
              enum tcp;
              enum udp;
            }
          } //protocol

          leaf port {
            type uint16 {
              range "1..65535";
            }
            description
                "[1..65535]";
          } //port

          leaf outside-ip {
            type inet:ip-address;
            description
                "a.b.c.d";
          } //outside-ip

          leaf outside-port {
            type uint16 {
              range "1..65535";
            }
            description
                "port";
          } //outside-port

          leaf nat-policy {
            type string;
          } //nat-policy

        } //list lsn

      } //container port-forwarding

      container syslog {
        description
            "Configure syslog reporting of NAT flows";
        list syslog-export-policy {
          key "name";
          description
              "Configure a NAT syslog export policy";
          leaf name {
            type string;
          } //name

          container description {
            description
                "Configure the description";
            leaf description-string {
              type string {
                length "1..80";
              }
            } //description-string

          } //container description

          container facility {
            description
                "Configure the facility number in the PRI part of the syslog messages (default: 
                 local0)";
            leaf syslog-facility {
              type enumeration {
                enum kernel;
                enum user;
                enum mail;
                enum systemd;
                enum auth;
                enum syslogd;
                enum printer;
                enum netnews;
                enum uucp;
                enum cron;
                enum authpriv;
                enum ftp;
                enum ntp;
                enum logaudit;
                enum logalert;
                enum cron2;
                enum local0;
                enum local1;
                enum local2;
                enum local3;
                enum local4;
                enum local5;
                enum local6;
                enum local7;
              }
            } //syslog-facility

          } //container facility

          container log-prefix {
            description
                "Configure the optional prefix text in the MSG part of the NAT syslog messages 
                 (default TMNX)";
            leaf prefix-text {
              type string {
                length "1..32";
              }
            } //prefix-text

          } //container log-prefix

          container max-tx-delay {
            description
                "Configure the maximum time a syslog message is delayed in the output buffer 
                 (default 0.3 seconds)";
            leaf deciseconds {
              type uint32 {
                range "1..100";
              }
            } //deciseconds

          } //container max-tx-delay

          container mtu {
            description
                "Configure the Maximum Transmission Unit (default: 1500)";
            leaf mtu-size {
              type uint32 {
                range "512..9000";
              }
            } //mtu-size

          } //container mtu

          container rate-limit {
            description
                "Configure the packet rate limit";
            leaf packets-per-second {
              type uint32 {
                range "10..2147483647";
              }
            } //packets-per-second

          } //container rate-limit

          container severity-level {
            description
                "Configure the severity level in the PRI part of the syslog messages (default: 
                 info)";
            leaf syslog-level {
              type enumeration {
                enum emergency;
                enum alert;
                enum critical;
                enum error;
                enum warning;
                enum notice;
                enum info;
                enum debug;
              }
            } //syslog-level

          } //container severity-level

          list collector {
            key "ip";
            description
                "Configure the transmission of NAT syslog messages to a syslog collector";
            leaf router {
              type string {
                length "1..32";
              }
              description
                  "Attribute router-name for collector";
            } //router

            leaf service-name {
              type string;
            } //service-name

            leaf ip {
              type inet:ip-address;
            } //ip

            container destination-port {
              description
                  "Configure the destination port (default: 514)";
              leaf destination-port-id {
                type uint32 {
                  range "1..65535";
                }
              } //destination-port-id

            } //container destination-port

            container ipv4-source-address {
              description
                  "Configure the IPv4 source address";
              leaf ip-address {
                type inet:ip-address;
              } //ip-address

            } //container ipv4-source-address

            leaf shutdown {
              type boolean;
              description
                  "Administratively disable or enable this collector";
            }

          } //list collector

          container include {
            presence
                "Configure what optional fields to include in the NAT syslog messages";
            leaf destination-ip {
              type boolean;
              description
                  "Include the destination IP address field";
            }

            leaf foreign-ip {
              type boolean;
              description
                  "Include the foreign IP address field";
            }

            leaf foreign-port {
              type boolean;
              description
                  "Include the foreign port field";
            }

            leaf nat-policy-name {
              type boolean;
              description
                  "Include the NAT policy name field";
            }

            leaf sub-id {
              type boolean;
              description
                  "Include the sub-id field";
            }

          } //container include

        } //list syslog-export-policy

      } //container syslog

      list up-nat-policy {
        key "policy-name";
        description
            "Configure a CUPS User Plane NAT policy";
        leaf policy-name {
          type string;
        } //policy-name

        container description {
          description
              "Configure the description";
          leaf description-string {
            type string {
              length "1..80";
            }
          } //description-string

        } //container description

        container filtering {
          description
              "Configure the filtering of this policy";
          leaf filtering-mode {
            type enumeration {
              enum address-and-port-dependent;
              enum endpoint-independent;
            }
          } //filtering-mode

        } //container filtering

        container ipfix-export-policy {
          description
              "Configure the IPFIX export policy";
          leaf ipfix-export-policy-string {
            type string {
              length "1..32";
            }
          } //ipfix-export-policy-string

        } //container ipfix-export-policy

        leaf reset-unknown-tcp {
          type boolean;
          description
              "Configure the send of TCP RST upon non-SYN TCP message for unknown flow";
        }

        container tcp-mss-adjust {
          description
              "Configure the value to adjust the TCP Maximum Segment Size (MSS) option";
          leaf segment-size {
            type uint32 {
              range "160..10240";
            }
          } //segment-size

        } //container tcp-mss-adjust

        leaf udp-inbound-refresh {
          type boolean;
          description
              "Configure the UDP inbound refresh behavior";
        }

        container alg {
          description
              "Configure Application Level Gateway parameters of this policy";
          leaf ftp {
            type boolean;
            description
                "Enable FTP ALG";
          }

          leaf pptp {
            type boolean;
            description
                "Enable PPTP ALG";
          }

          leaf rtsp {
            type boolean;
            description
                "Enable RTSP ALG";
          }

          leaf sip {
            type boolean;
            description
                "Enable SIP ALG";
          }

        } //container alg

        container port-limits {
          description
              "Configure the port limits of this policy";
          container reserved {
            description
                "Configure the number of ports reserved for prioritized sessions";
            leaf num-ports {
              type uint64 {
                range "1..65534";
              }
            } //num-ports

          } //container reserved

          container watermarks {
            description
                "Configure the port usage watermarks of this policy";
            leaf high {
              type uint32 {
                range "1..100";
              }
            } //high

            leaf low {
              type uint32 {
                range "0..99";
              }
            } //low

          } //container watermarks

        } //container port-limits

        container priority-sessions {
          presence
              "Configure the prioritized sessions of this policy";
          list fc {
            key "fc-name";
            description
                "Configure the forwarding classes that have their sessions prioritized";
            leaf fc-name {
              type enumeration {
                enum be;
                enum l2;
                enum af;
                enum l1;
                enum h2;
                enum ef;
                enum h1;
                enum nc;
              }
            } //fc-name

          } //list fc

        } //container priority-sessions

        container session-limits {
          description
              "Configure the session limits of this policy";
          container max {
            description
                "Configure the session limit of this policy";
            leaf num-sessions {
              type uint32 {
                range "1..65535";
              }
            } //num-sessions

          } //container max

          container reserved {
            description
                "Configure the number of sessions reserved for prioritized sessions";
            leaf num-sessions {
              type uint16 {
                range "1..65534";
              }
            } //num-sessions

          } //container reserved

          container watermarks {
            description
                "Configure the session watermarks of this policy";
            leaf high {
              type uint32 {
                range "1..100";
              }
            } //high

            leaf low {
              type uint32 {
                range "0..99";
              }
            } //low

          } //container watermarks

        } //container session-limits

        container timeouts {
          presence
              "Configure the session idle timeouts of this policy";
          container icmp-query {
            description
                "Configure the timeout applied to an ICMP Query session";
            leaf min {
              type uint32 {
                range "1..4";
              }
            } //min

            leaf sec {
              type uint32 {
                range "1..59";
              }
            } //sec

          } //container icmp-query

          container sip {
            description
                "Configure SIP inactive media timeout";
            leaf hrs {
              type uint32 {
                range "1..2";
              }
            } //hrs

            leaf min {
              type uint32 {
                range "1..59";
              }
            } //min

            leaf sec {
              type uint32 {
                range "1..59";
              }
            } //sec

          } //container sip

          container subscriber-retention {
            description
                "Configure the time a subscribers' IP address is kept after all hosts and port 
                 blocks have expired";
            leaf hrs {
              type uint32 {
                range "1..24";
              }
            } //hrs

            leaf min {
              type uint32 {
                range "1..59";
              }
            } //min

          } //container subscriber-retention

          container tcp-established {
            description
                "Configure the idle timeout applied to a TCP session in the established state";
            leaf hrs {
              type uint32 {
                range "1..24";
              }
            } //hrs

            leaf min {
              type uint32 {
                range "1..59";
              }
            } //min

            leaf sec {
              type uint32 {
                range "1..59";
              }
            } //sec

          } //container tcp-established

          container tcp-rst {
            description
                "Configure the time after receiving RST before a TCP session can return to the 
                 state LISTEN";
            leaf min {
              type uint32 {
                range "1..4";
              }
            } //min

            leaf sec {
              type uint32 {
                range "1..59";
              }
            } //sec

          } //container tcp-rst

          container tcp-syn {
            description
                "Configure the timeout applied to a TCP session when synchronizing its initial 
                 sequence";
            leaf hrs {
              type uint32 {
                range "1..24";
              }
            } //hrs

            leaf min {
              type uint32 {
                range "1..59";
              }
            } //min

            leaf sec {
              type uint32 {
                range "1..59";
              }
            } //sec

          } //container tcp-syn

          container tcp-time-wait {
            description
                "Configure the timeout applied to a TCP session in the time-wait state";
            leaf min {
              type uint32 {
                range "1..4";
              }
            } //min

            leaf sec {
              type uint32 {
                range "1..59";
              }
            } //sec

          } //container tcp-time-wait

          container tcp-transitory {
            description
                "Configure the idle timeout applied to a TCP session in a transitory state";
            leaf hrs {
              type uint32 {
                range "1..24";
              }
            } //hrs

            leaf min {
              type uint32 {
                range "1..59";
              }
            } //min

            leaf sec {
              type uint32 {
                range "1..59";
              }
            } //sec

          } //container tcp-transitory

          container udp {
            description
                "Configure the UDP mapping timeout";
            leaf hrs {
              type uint32 {
                range "1..24";
              }
            } //hrs

            leaf min {
              type uint32 {
                range "1..59";
              }
            } //min

            leaf sec {
              type uint32 {
                range "1..59";
              }
            } //sec

          } //container udp

          container udp-dns {
            description
                "Configure the timeout applied to a UDP session with destination port 53";
            leaf hrs {
              type uint32 {
                range "1..24";
              }
            } //hrs

            leaf min {
              type uint32 {
                range "1..59";
              }
            } //min

            leaf sec {
              type uint32 {
                range "1..59";
              }
            } //sec

          } //container udp-dns

          container udp-initial {
            description
                "Configure the UDP mapping timeout applied to new sessions";
            leaf min {
              type uint32 {
                range "1..59";
              }
            } //min

            leaf sec {
              type uint32 {
                range "1..59";
              }
            } //sec

          } //container udp-initial

        } //container timeouts

      } //list up-nat-policy

    } //container nat

  } //grouping alu-conf-svc-nat-r13

} //module  alu-conf-svc-nat-r13
