module alu-conf-eth-ring-r13 {
  yang-version "1";

  namespace "urn:alcatel-lucent.com:sros:ns:yang:conf-eth-ring-r13";

  prefix "conf-eth-ring-r13";

  import alu-types {
    prefix "alu";
  }
  import ietf-yang-types {
    prefix "yang";
  }

  alu:alu-major-release "rel20";

  organization "Alcatel-Lucent";

  contact
      "Alcatel-Lucent SR OS Support 
       Web: <http://www.alcatel-lucent.com>";

  description
      "Alcatel-Lucent YANG Data model to configure Ethernet Rings on SR OS based 
       routers. 
       
       Copyright 2014-2015 Alcatel-Lucent, 2016 Nokia. All rights reserved. 
       Reproduction of this document is authorized on the condition that the 
       foregoing copyright notice is included. 
       
       This alu-conf-eth-ring-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-10-23";

  grouping alu-conf-eth-ring-r13 {
    list eth-ring {
      key "ring-index";
      description
          "Configure Ethernet Rings";
      leaf ring-index {
        type string;
        description
            "Attribute ring-index for eth-ring";
      } //ring-index

      container ccm-hold-time {
        description
            "Configure eth-ring CCM dampening timers";
        leaf down {
          type uint32;
          description
              "Attribute down-timeout for ccm-hold-time";
        } //down

        leaf up {
          type uint32;
          default 20;
          description
              "[0..5000] in 10ths of seconds - Default: 20";
        } //up

      } //container ccm-hold-time

      container compatible-version {
        description
            "Configure the backward compatibility logic for the Eth-Ring";
        leaf version {
          type uint32 {
            range "1..2";
          }
          default 2;
          description
              "[1..2] - Default: 2";
        } //version

      } //container compatible-version

      container description {
        description
            "Add/remove a text description for the eth-ring";
        leaf description-string {
          type string {
            length "1..80";
          }
        } //description-string

      } //container description

      container guard-time {
        description
            "Configure the eth-ring guard time";
        leaf time {
          type uint32 {
            range "1..20";
          }
          default 5;
          description
              "[1..20] in deciseconds - Default: 5";
        } //time

      } //container guard-time

      container node-id {
        description
            "Configure the Node-ID of the Ethernet Ring";
        leaf node-id-id {
          type yang:mac-address;
        } //node-id-id

      } //container node-id

      container revert-time {
        description
            "Configure the eth-ring revert-time";
        leaf time {
          type uint32 {
            range "60..720";
          }
          default 300;
          description
              "[60..720] in seconds - Default: 300";
        } //time

      } //container revert-time

      container rpl-node {
        description
            "Configure the Ring Protection Link type for the eth-ring";
        leaf rpl-node-id {
          type enumeration {
            enum none;
            enum owner;
            enum nbr;
          }
        } //rpl-node-id

      } //container rpl-node

      leaf shutdown {
        type boolean;
        description
            "Administratively enable/disable the eth-ring";
      }

      list path {
        key "path-id";
        description
            "Configure a path for the eth-ring";
        leaf path-id {
          type enumeration {
            enum a;
            enum b;
          }
        } //path-id

        leaf port-id {
          type string {
            length "1..17";
          }
          description
              "Attribute port-id for path";
        } //port-id

        leaf raps-tag {
          type string;
          description
              "Attribute qtag1[.<qtag2>] for path";
        } //raps-tag

        container description {
          description
              "Add/remove a text description for the path";
          leaf description-string {
            type string {
              length "1..80";
            }
            description
                "[80 chars max]";
          } //description-string

        } //container description

        leaf rpl-end {
          type boolean;
          description
              "Enable/disable Ring Protection Link (RPL) for the path";
        }

        leaf shutdown {
          type boolean;
          description
              "Administratively enable/disable the eth-ring path";
        }

        container eth-cfm {
          description
              "Configure CFM parameters";
          list mep {
            key "mep-id domain association";
            description
                "Configure a CFM Maintenance Endpoint";
            leaf mep-id {
              type int16 {
                range "1..8191";
              }
            } //mep-id

            leaf domain {
              type uint32 {
                range "1..4294967295";
              }
            } //domain

            leaf association {
              type uint32 {
                range "1..4294967295";
              }
            } //association

            leaf ccm-enable {
              type boolean;
              description
                  "Enable/Disable Generation of CCM messages";
            }

            container ccm-ltm-priority {
              description
                  "Configure the priority of CCM and LTM messages";
              leaf priority {
                type uint16 {
                  range "0..7";
                }
                description
                    "[0..7] - Default highest priority on bridge-port";
              } //priority

            } //container ccm-ltm-priority

            container ccm-padding-size {
              description
                  "Insert additional padding in the CCM packets";
              leaf ccm-padding {
                type uint32 {
                  range "3..1500";
                }
                description
                    "3..1500 octets";
              } //ccm-padding

            } //container ccm-padding-size

            leaf control-mep {
              type boolean;
              description
                  "Enable/disable propagation of CC state to eth-tunnel";
            }

            container description {
              description
                  "Add/remove a text description for the MEP";
              leaf description-string {
                type string {
                  length "1..80";
                }
                description
                    "[80 chars max]";
              } //description-string

            } //container description

            leaf install-mep {
              type boolean;
              description
                  "Enable/Disable Installation of the MEP in the forwarding plane";
            }

            container low-priority-defect {
              description
                  "Configure the Lowest Priority Defect for the MEP";
              leaf allDef-macRemErrXcon-remErrXcon-errXcon-xcon-noXcon {
                type enumeration {
                  enum allDef;
                  enum macRemErrXcon;
                  enum remErrXcon;
                  enum errXcon;
                  enum xcon;
                  enum noXcon;
                }
                description
                    "keywords";
              } //allDef-macRemErrXcon-remErrXcon-errXcon-xcon-noXcon

            } //container low-priority-defect

            container mac-address {
              description
                  "Configure the MAC Address for the MEP";
              leaf mac-address {
                type yang:mac-address;
              } //mac-address

            } //container mac-address

            container one-way-delay-threshold {
              description
                  "Configure the one-way-delay test threshold";
              leaf seconds {
                type uint32 {
                  range "0..600";
                }
                default 3;
                description
                    "[0..600] Default: 3";
              } //seconds

            } //container one-way-delay-threshold

            leaf shutdown {
              type boolean;
              description
                  "Administratively enable/disable the MEP";
            }

            container alarm-notification {
              description
                  "Configure the MEP alarm notification parameters";
              container fng-alarm-time {
                description
                    "Configure the Fault Notification Generation (FNG) alarm time";
                leaf time {
                  type enumeration {
                    enum 0;
                    enum 250;
                    enum 500;
                    enum 1000;
                  }
                  default 0;
                  description
                      "[0,250,500,1000] centi-seconds - Default: 0";
                } //time

              } //container fng-alarm-time

              container fng-reset-time {
                description
                    "Configure the Fault Notification Generation (FNG) reset time";
                leaf time {
                  type enumeration {
                    enum 0;
                    enum 250;
                    enum 500;
                    enum 1000;
                  }
                  default 0;
                  description
                      "[0,250,500,1000] centi-seconds - Default: 0";
                } //time

              } //container fng-reset-time

            } //container alarm-notification

            container eth-test-enable {
              presence
                  "Enable/Disable eth-test functionality on MEP";
              container bit-error-threshold {
                description
                    "Configure the bit error trap threshold";
                leaf bit-errors {
                  type uint32 {
                    range "0..11840";
                  }
                  default 1;
                  description
                      "[0..11840] Default: 1";
                } //bit-errors

              } //container bit-error-threshold

              container test-pattern {
                description
                    "Configure the test pattern for eth-test frames";
                leaf all-zeros-all-ones {
                  type enumeration {
                    enum all-zeros;
                    enum all-ones;
                  }
                  default "all-zeros";
                  description
                      "keywords - Test pattern - default: all-zeros";
                } //all-zeros-all-ones

                leaf crc-enable {
                  type boolean;
                  description
                      "keyword - Generate CRC checksum";
                } //crc-enable

              } //container test-pattern

            } //container eth-test-enable

            container grace {
              description
                  "Configure the generation and reception of grace period parameters";
              container eth-ed {
                description
                    "Configure the generation and reception of eth-ed grace period parameters";
                container max-rx-defect-window {
                  description
                      "Configure/Disable an upper maximum defect window length; when disabled the 
                       advertised value from the peer will be used; when enabled the lower of the 
                       configured value or the advertised value from the peer will be used";
                  leaf seconds {
                    type uint32 {
                      range "1..86400";
                    }
                    description
                        "[1..86400] - Default: no max-rx-defect-window";
                  } //seconds

                } //container max-rx-defect-window

                container priority {
                  description
                      "Configure/Disable the transmission priority value for ETH-ED PDUs; when 
                       disabled the priority value of ccm-ltm-priority associated with this MEP will 
                       be used";
                  leaf priority {
                    type int32 {
                      range "0..7";
                    }
                    default 0;
                    description
                        "[0..7] - Default: no priority";
                  } //priority

                } //container priority

                leaf rx-eth-ed {
                  type boolean;
                  description
                      "Enable/Disable the receiving and processing of ETH-ED PDUs";
                }

                leaf tx-eth-ed {
                  type boolean;
                  description
                      "Enable/Disable the transmission of ETH-ED PDUs";
                }

              } //container eth-ed

              container eth-vsm-grace {
                description
                    "Configure the generation and reception of sros vendor specific message (vsm) 
                     grace period parameters";
                leaf rx-eth-vsm-grace {
                  type boolean;
                  description
                      "Enable/Disable the receiving and processing of vendor specific message (vsm) 
                       grace period notifications";
                }

                leaf tx-eth-vsm-grace {
                  type boolean;
                  description
                      "Enable/Disable the transmission of vsm grace period notifications";
                }

              } //container eth-vsm-grace

            } //container grace

          } //list mep

        } //container eth-cfm

      } //list path

      container sub-ring {
        description
            "Configure eth-ring sub-ring parameters";
        leaf sub-ring-id {
          type enumeration {
            enum virtual-link;
            enum non-virtual-link;
          }
        } //sub-ring-id

        container interconnect {
          description
              "Configure sub-ring interconnect parameters";
          leaf ring-id {
            type string;
            description
                "Attribute ring-index for interconnect";
          } //ring-id

          leaf vpls {
            type boolean;
            description
                "keyword - interconnect to a VPLS service.";
          } //vpls

          leaf propagate-topology-change {
            type boolean;
            description
                "Enable/Disable propagation of topology change";
          }

        } //container interconnect

      } //container sub-ring

    } //list eth-ring

  } //grouping alu-conf-eth-ring-r13

} //module  alu-conf-eth-ring-r13
