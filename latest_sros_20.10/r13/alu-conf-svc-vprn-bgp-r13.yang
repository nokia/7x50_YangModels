module alu-conf-svc-vprn-bgp-r13 {
  yang-version "1";

  namespace "urn:alcatel-lucent.com:sros:ns:yang:conf-svc-vprn-bgp-r13";

  prefix "conf-svc-vprn-bgp-r13";

  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure BGP for VPRN services on SR OS 
       based routers. 
       
       Copyright 2014-2015 Alcatel-Lucent, 2016 Nokia. All rights reserved. 
       Reproduction of this document is authorized on the condition that the 
       foregoing copyright notice is included. 
       
       This alu-conf-svc-vprn-bgp-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-08-18";

  grouping alu-conf-svc-vprn-bgp-r13 {
    container bgp {
      presence
          "Configure BGP for VPRN services";
      leaf advertise-inactive {
        type boolean;
        description
            "Enable/disable advertising of inactive BGP routes to other BGP peers";
      }

      container advertise-ipv6-next-hops {
        description
            "Enable/Disable setting of next-hops to global ipv6 address for the family";
        leaf ipv4 {
          type boolean;
          description
              "keyword - provision support of the specific family";
        } //ipv4

      } //container advertise-ipv6-next-hops

      leaf aggregator-id-zero {
        type boolean;
        description
            "Enable/disable setting the service vprn ID to 0 in the aggregator path 
             attribute when BGP is aggregating routes";
      }

      container auth-keychain {
        description
            "Configure TCP authentication keychain to use for the session";
        leaf name {
          type string {
            length "1..32";
          }
          description
              "keychain-name (32 char max)";
        } //name

      } //container auth-keychain

      container authentication-key {
        description
            "Configure the BGP authentication key for all peers";
        leaf authentication-key-hash-key {
          type string {
            length "1..500";
          }
          description
              "authentication-key - [255 chars max] 
               hash-key 
               hash2-key 
               custom-key";
        } //authentication-key-hash-key

        leaf hash-hash2-custom {
          type enumeration {
            enum hash;
            enum hash2;
            enum custom;
          }
          description
              "keywords - specify hashing scheme";
        } //hash-hash2-custom

      } //container authentication-key

      container backup-path {
        description
            "Enable/Disable Backup Path for the bgp family on this VPRN instance";
        leaf ipv4 {
          type boolean;
          description
              "keyword - provision support of the specific family";
        } //ipv4

        leaf ipv6 {
          type boolean;
          description
              "keyword - provision support of the specific family";
        } //ipv6

        leaf label-ipv4 {
          type boolean;
          description
              "keyword - provision support of the specific family";
        } //label-ipv4

      } //container backup-path

      leaf bfd-enable {
        type boolean;
        description
            "Enable BFD";
      }

      container cluster {
        description
            "Configure the cluster ID for a route reflector server";
        leaf cluster-id {
          type inet:ip-address;
          description
              "expressed in dotted decimal format (a.b.c.d)";
        } //cluster-id

      } //container cluster

      container connect-retry {
        description
            "Configure the BGP Connect Retry timer value";
        leaf seconds {
          type uint32 {
            range "1..65535";
          }
        } //seconds

      } //container connect-retry

      container damp-peer-oscillations {
        description
            "Configure damp peer oscillations for all BGP peers";
        leaf idle-hold-time {
          type boolean;
        } //idle-hold-time

        leaf initial-wait {
          type uint32 {
            range "0..2048";
          }
        } //initial-wait

        leaf second-wait {
          type uint32 {
            range "1..2048";
          }
        } //second-wait

        leaf max-wait {
          type uint32 {
            range "1..2048";
          }
        } //max-wait

        leaf error-interval {
          type uint32 {
            range "0..2048";
          }
        } //error-interval

      } //container damp-peer-oscillations

      leaf damping {
        type boolean;
        description
            "Enable/disable BGP route damping for learned routes as defined within the 
             route policy";
      }

      container default-label-preference {
        description
            "Configure the default route preference for labeled routes learned at the 
             global level";
        leaf ebgp {
          type uint16 {
            range "0..255";
          }
        } //ebgp

        leaf ibgp {
          type uint16 {
            range "0..255";
          }
        } //ibgp

      } //container default-label-preference

      container default-preference {
        description
            "Configure the default route preference for routes learned at the global level";
        leaf ebgp {
          type uint16 {
            range "0..255";
          }
        } //ebgp

        leaf ibgp {
          type uint16 {
            range "0..255";
          }
        } //ibgp

      } //container default-preference

      container description {
        description
            "Create a textual description stored in the configuration file";
        leaf description-string {
          type string {
            length "1..80";
          }
        } //description-string

      } //container description

      leaf disable-4byte-asn {
        type boolean;
        description
            "Enable/disable the advertisement of 4-byte ASN capability at the global level";
      }

      leaf disable-client-reflect {
        type boolean;
        description
            "Enable/disable the reflection of routes by the route reflector at the global 
             level";
      }

      container disable-communities {
        description
            "Configure BGP to disable sending communities";
        leaf standard {
          type boolean;
        } //standard

        leaf extended {
          type boolean;
        } //extended

        leaf large {
          type boolean;
        } //large

      } //container disable-communities

      leaf disable-fast-external-failover {
        type boolean;
        description
            "Configure BGP fast external failover";
      }

      container dynamic-neighbor-limit {
        description
            "Maximum number of dynamic neighbors should be configurable for the entire BGP 
             instance.";
        leaf dynamic-neighbor-limit-id {
          type uint32 {
            range "1..8192";
          }
        } //dynamic-neighbor-limit-id

      } //container dynamic-neighbor-limit

      container ebgp-default-reject-policy {
        description
            "Enable import/export of routes receive/sent from/to EBGP peers";
        leaf import {
          type boolean;
        } //import

        leaf export {
          type boolean;
        } //export

      } //container ebgp-default-reject-policy

      leaf eibgp-loadbalance {
        type boolean;
        description
            "Enable/disable eibgp load balancing";
      }

      leaf enable-peer-tracking {
        type boolean;
        description
            "Enable/disable BGP peer tracking";
      }

      leaf enforce-first-as {
        type boolean;
        description
            "Enable/Disable Enforce First AS";
      }

      container export {
        description
            "Export route policies used to determine which routes are advertised to all 
             peers";
        leaf-list policy-name {
          type string;
          max-elements 15;
          description
              "Attribute policy-name for export";
        } //policy-name

        leaf plcy-or-long-expr {
          type string {
            length "1..255";
          }
          description
              "Attribute plcy-or-long-expr for export";
        } //plcy-or-long-expr

        leaf-list plcy-or-expr {
          type string {
            length "1..64";
          }
          max-elements 14;
          description
              "Attribute plcy-or-expr for export";
        } //plcy-or-expr

      } //container export

      container extended-nh-encoding {
        description
            "Configure the family for extended next-hop encoding";
        leaf ipv4 {
          type boolean;
          description
              "keyword - provision support of the specific family";
        } //ipv4

      } //container extended-nh-encoding

      container family {
        description
            "Configure the IP family capability";
        leaf ipv4 {
          type boolean;
          description
              "keyword - provision support of the specific family";
        } //ipv4

        leaf ipv6 {
          type boolean;
          description
              "keyword - provision support of the specific family";
        } //ipv6

        leaf mcast-ipv4 {
          type boolean;
          description
              "keyword - provision support of the specific family";
        } //mcast-ipv4

        leaf flow-ipv6 {
          type boolean;
          description
              "keyword - provision support of the specific family";
        } //flow-ipv6

        leaf flow-ipv4 {
          type boolean;
          description
              "keyword - provision support of the specific family";
        } //flow-ipv4

        leaf mcast-ipv6 {
          type boolean;
          description
              "keyword - provision support of the specific family";
        } //mcast-ipv6

        leaf label-ipv4 {
          type boolean;
          description
              "keyword - provision support of the specific family";
        } //label-ipv4

      } //container family

      leaf flowspec-validate {
        type boolean;
        status "obsolete";
        description
            "Enable/Disable Flowspec Validation";
      }

      container hold-time {
        description
            "Configure BGP hold time";
        leaf seconds {
          type string;
          description
              "0|[3..65535]";
        } //seconds

        leaf min {
          type string;
        } //min

      } //container hold-time

      leaf ibgp-multipath {
        type boolean;
        description
            "Define how IBGP routes with multiple next hops are added to the route-table";
      }

      container import {
        description
            "Import route policies used to determine which routes are accepted from all 
             peers";
        leaf-list policy-name {
          type string;
          max-elements 15;
          description
              "Attribute policy-name for import";
        } //policy-name

        leaf plcy-or-long-expr {
          type string {
            length "1..255";
          }
          description
              "Attribute plcy-or-long-expr for import";
        } //plcy-or-long-expr

        leaf-list plcy-or-expr {
          type string {
            length "1..64";
          }
          max-elements 14;
          description
              "Attribute plcy-or-expr for import";
        } //plcy-or-expr

      } //container import

      leaf initial-send-delay-zero {
        type boolean;
        description
            "Enable/Disable Bypassing of Min Route Advertisement Timer countdown before 
             sending BGP update";
      }

      container keepalive {
        description
            "Configure BGP keepalive timer";
        leaf seconds {
          type uint32 {
            range "0..21845";
          }
          default 30;
        } //seconds

      } //container keepalive

      container label-preference {
        description
            "Configure the route preference for labeled routes learned from all peers";
        leaf value {
          type uint16 {
            range "1..255";
          }
        } //value

      } //container label-preference

      container local-as {
        description
            "Add/remove a BGP virtual AS number";
        leaf as-number {
          type uint32 {
            range "1..4294967295";
          }
        } //as-number

        leaf private {
          type boolean;
        } //private

        leaf no-prepend-global-as {
          type boolean;
        } //no-prepend-global-as

      } //container local-as

      container local-preference {
        description
            "Configure BGP local-preference attribute in incoming routes from all peers if 
             not specified";
        leaf local-preference {
          type uint32;
        } //local-preference

      } //container local-preference

      container loop-detect {
        description
            "Configure how the BGP peer session handles loop detection in the AS Path";
        leaf drop-peer-discard-route-ignore-loop-off {
          type enumeration {
            enum drop-peer;
            enum discard-route;
            enum ignore-loop;
            enum off;
          }
          description
              "keywords";
        } //drop-peer-discard-route-ignore-loop-off

      } //container loop-detect

      container loop-detect-threshold {
        description
            "Limit the number of times global ASN appears in a received AS path";
        leaf loop-detect-threshold {
          type uint32 {
            range "0..15";
          }
          description
              "[0..15]";
        } //loop-detect-threshold

      } //container loop-detect-threshold

      container med-out {
        description
            "Enable/disable advertising the Multi-Exit Discriminator (MED)";
        leaf number {
          type uint32;
        } //number

        leaf igp-cost {
          type boolean;
        } //igp-cost

      } //container med-out

      container min-route-advertisement {
        description
            "Minimum interval at which a given prefix is advertised to a peer";
        leaf seconds {
          type uint16 {
            range "1..255";
          }
          description
              "[1..255]";
        } //seconds

      } //container min-route-advertisement

      container multihop {
        description
            "TTL value entered in the IP header of packets sent to a peer";
        leaf ttl-value {
          type uint8 {
            range "1..255";
          }
        } //ttl-value

      } //container multihop

      container multipath {
        status "obsolete";
        description
            "Configure multipath to share load traffic across multiple routes";
        leaf max-paths {
          type string;
          description
              "Attribute max-paths for multipath";
        } //max-paths

        leaf ebgp {
          type string;
          description
              "Attribute ebgp-max-paths for multipath";
        } //ebgp

        leaf ibgp {
          type string;
          description
              "Attribute ibgp-max-paths for multipath";
        } //ibgp

        leaf restrict {
          type enumeration {
            enum same-neighbor-as;
            enum exact-as-path;
          }
        } //restrict

      } //container multipath

      leaf path-mtu-discovery {
        type boolean;
        description
            "Enable/disable Path MTU Discovery";
      }

      container peer-tracking-policy {
        description
            "Configure Peer-Tracking policy";
        leaf policy-name {
          type string;
          description
              "Attribute policy-name for peer-tracking-policy";
        } //policy-name

      } //container peer-tracking-policy

      container preference {
        description
            "Configure the route preference for routes learned from all peers";
        leaf preference {
          type uint16 {
            range "1..255";
          }
        } //preference

      } //container preference

      leaf rapid-withdrawal {
        type boolean;
        description
            "Disable/Enable the delay on sending BGP rapid withdrawals";
      }

      container remove-private {
        description
            "Remove private AS numbers from the AS Path before advertising to a peer";
        leaf limited {
          type boolean;
          description
              "keyword";
        } //limited

        leaf skip-peer-as {
          type boolean;
          description
              "keyword";
        } //skip-peer-as

        leaf replace {
          type boolean;
          description
              "keyword";
        } //replace

      } //container remove-private

      container router-id {
        description
            "Configure the Router ID to be used with this BGP instance";
        leaf ip-address {
          type inet:ip-address;
        } //ip-address

      } //container router-id

      container send-default {
        description
            "Configure default route";
        leaf ipv4 {
          type boolean;
          description
              "keyword - provision support of the specific family";
        } //ipv4

        leaf ipv6 {
          type boolean;
          description
              "keyword - provision support of the specific family";
        } //ipv6

        leaf export-policy {
          type string;
          description
              "Attribute export-policy for send-default";
        } //export-policy

      } //container send-default

      leaf shutdown {
        type boolean;
        description
            "Administratively enable/disable the BGP instance";
      }

      leaf split-horizon {
        type boolean;
        description
            "Configure split horizon for the peers under this instance";
      }

      leaf third-party-nexthop {
        type boolean;
        description
            "Enable third party next-hop processing";
      }

      container best-path-selection {
        description
            "Enable/Disable Path Selection Config";
        container always-compare-med {
          description
              "Determine how the Multi-Exit Discriminator (MED) path attribute is used in the 
               BGP route selection process";
          leaf strict-as {
            type boolean;
          } //strict-as

          leaf zero-infinity {
            type enumeration {
              enum zero;
              enum infinity;
            }
            description
                "keywords";
          } //zero-infinity

        } //container always-compare-med

        container as-path-ignore {
          description
              "Determine whether the AS Path is used in determining the best BGP route";
          leaf ipv4 {
            type boolean;
            description
                "keyword - provision support of the specific family";
          } //ipv4

          leaf ipv6 {
            type boolean;
            description
                "keyword - provision support of the specific family";
          } //ipv6

          leaf label-ipv4 {
            type boolean;
            description
                "keyword - provision support of the specific family";
          } //label-ipv4

        } //container as-path-ignore

        leaf compare-origin-validation-state {
          type boolean;
          description
              "Enable/Disable compare validation state";
        }

        leaf deterministic-med {
          type boolean;
          description
              "Enable/Disable deterministic Multi-Exit Discriminator";
        }

        container ebgp-ibgp-equal {
          description
              "Determine whether EBGP and IBGP learned paths are considered equal";
          leaf ipv4 {
            type boolean;
            description
                "keyword - provision support of the specific family";
          } //ipv4

          leaf ipv6 {
            type boolean;
            description
                "keyword - provision support of the specific family";
          } //ipv6

          leaf label-ipv4 {
            type boolean;
            description
                "keyword - provision support of the specific family";
          } //label-ipv4

        } //container ebgp-ibgp-equal

        leaf ignore-nh-metric {
          type boolean;
          description
              "Enable/Disable ignore next-hop metric";
        }

        leaf ignore-router-id {
          type boolean;
          description
              "Enable/Disable ignore router-id";
        }

        leaf origin-invalid-unusable {
          type boolean;
          description
              "Enable/Disable origin invalid unusable routes.";
        }

      } //container best-path-selection

      container convergence {
        description
            "Configure delaying route convergence";
        container min-wait-to-advertise {
          description
              "Configure min wait time before advertising routes";
          leaf seconds {
            type uint32 {
              range "0..3600";
            }
          } //seconds

        } //container min-wait-to-advertise

        container family {
          description
              "Configure max wait delaying time for route convergence";
          leaf family {
            type enumeration {
              enum ipv4;
              enum ipv6;
            }
          } //family

          container max-wait-to-advertise {
            description
                "Configure max-wait time before advertising routes";
            leaf seconds {
              type uint32 {
                range "0..3600";
              }
            } //seconds

          } //container max-wait-to-advertise

        } //container family

      } //container convergence

      container error-handling {
        description
            "Enable/Disable Error Handling";
        leaf update-fault-tolerance {
          type boolean;
          description
              "Enable/Disable update-fault-tolerance";
        }

      } //container error-handling

      container flowspec {
        description
            "Enable/Disable Flowspec Validations";
        leaf validate-dest-prefix {
          type boolean;
          description
              "Enable/Disable Destination Prefix validation";
        }

        leaf validate-redirect-ip {
          type boolean;
          description
              "Enable/Disable Redirect IP validation";
        }

      } //container flowspec

      container graceful-restart {
        presence
            "Enable/disable graceful-restart for all VPRN BGP peers";
        leaf enable-notification {
          type boolean;
          description
              "Enable/Disable NOTIFICATION-triggered graceful restart";
        }

        container restart-time {
          description
              "Configure BGP graceful restart time";
          leaf time {
            type uint32 {
              range "0..4095";
            }
          } //time

        } //container restart-time

        container stale-routes-time {
          description
              "Configure BGP graceful restart stale routes time period";
          leaf time {
            type uint32 {
              range "1..3600";
            }
          } //time

        } //container stale-routes-time

        container long-lived {
          presence
              "Enable/disable long-lived graceful-restart for all VPRN BGP peers";
          container advertise-stale-to-all-neighbors {
            description
                "Enable/Disable BGP long-lived graceful restart advertise stale routes to 
                 neighbors";
            leaf without-no-export {
              type boolean;
              description
                  "keyword - Advertise stale routes to neighbors with the addition of the 
                   LLGR_STALE community";
            } //without-no-export

          } //container advertise-stale-to-all-neighbors

          container advertised-stale-time {
            description
                "Configure BGP long-lived graceful restart advertised stale routes time period";
            leaf seconds {
              type uint32 {
                range "0..16777215";
              }
            } //seconds

          } //container advertised-stale-time

          container forwarding-bits-set {
            description
                "Configure F bit behavior for each AFI/SAFI";
            leaf forwarding-bits-set-id {
              type enumeration {
                enum all;
                enum non-fwd;
              }
            } //forwarding-bits-set-id

          } //container forwarding-bits-set

          container helper-override-restart-time {
            description
                "Configure BGP long-lived graceful restart helper override restart time period";
            leaf second {
              type uint32 {
                range "0..4095";
              }
            } //second

          } //container helper-override-restart-time

          container helper-override-stale-time {
            description
                "Configure BGP long-lived graceful restart helper override stale routes time 
                 period";
            leaf seconds {
              type uint32 {
                range "0..16777215";
              }
            } //seconds

          } //container helper-override-stale-time

          list family {
            key "family-id";
            description
                "Configure Family specific long-lived graceful-restart parameters for BGP peers";
            leaf family-id {
              type enumeration {
                enum ipv4;
                enum ipv6;
                enum label-ipv4;
                enum flow-ipv4;
                enum flow-ipv6;
              }
            } //family-id

            container advertised-stale-time {
              description
                  "Configure BGP long-lived graceful restart advertised stale routes time period 
                   for this Family";
              leaf seconds {
                type uint32 {
                  range "0..16777215";
                }
              } //seconds

            } //container advertised-stale-time

            container helper-override-stale-time {
              description
                  "Configure BGP long-lived graceful restart helper override stale routes time 
                   period per family";
              leaf seconds {
                type uint32 {
                  range "0..16777215";
                }
              } //seconds

            } //container helper-override-stale-time

          } //list family

        } //container long-lived

      } //container graceful-restart

      list group {
        key "name";
        description
            "Configure a BGP group";
        leaf name {
          type string {
            length "1..64";
          }
        } //name

        leaf dynamic-peer {
          type boolean;
          status "obsolete";
        } //dynamic-peer

        leaf esm-dynamic-peer {
          type boolean;
        } //esm-dynamic-peer

        leaf advertise-inactive {
          type boolean;
          description
              "Enable/disable advertising of inactive BGP routes to other BGP peers";
        }

        container advertise-ipv6-next-hops {
          description
              "Enable/Disable setting of next-hops to global ipv6 address for the family";
          leaf ipv4 {
            type boolean;
            description
                "keyword - provision support of the specific family";
          } //ipv4

        } //container advertise-ipv6-next-hops

        leaf aggregator-id-zero {
          type boolean;
          description
              "Enable/disable (group level) setting the service vprn ID to 0 in the 
               aggregator path attribute";
        }

        leaf as-override {
          type boolean;
          description
              "Enable/disable (group level) AS override";
        }

        container auth-keychain {
          description
              "Configure TCP authentication keychain to use for the session";
          leaf name {
            type string {
              length "1..32";
            }
            description
                "keychain-name (32 char max)";
          } //name

        } //container auth-keychain

        container authentication-key {
          description
              "Configure the BGP authentication key for the group";
          leaf authentication-key-hash-key {
            type string {
              length "1..500";
            }
            description
                "authentication-key - [255 chars max] 
                 hash-key 
                 hash2-key 
                 custom-key";
          } //authentication-key-hash-key

          leaf hash-hash2-custom {
            type enumeration {
              enum hash;
              enum hash2;
              enum custom;
            }
            description
                "keywords - specify hashing scheme";
          } //hash-hash2-custom

        } //container authentication-key

        leaf bfd-enable {
          type boolean;
          description
              "Enable BFD";
        }

        container cluster {
          description
              "Configure the cluster ID for a route reflector server";
          leaf cluster-id {
            type inet:ip-address;
            description
                "expressed in dotted decimal format (a.b.c.d)";
          } //cluster-id

        } //container cluster

        container connect-retry {
          description
              "Configure the BGP Connect Retry timer value for the group";
          leaf seconds {
            type uint32 {
              range "1..65535";
            }
          } //seconds

        } //container connect-retry

        container damp-peer-oscillations {
          description
              "Configure damp peer oscillations for all BGP peer groups";
          leaf idle-hold-time {
            type boolean;
          } //idle-hold-time

          leaf initial-wait {
            type uint32 {
              range "0..2048";
            }
          } //initial-wait

          leaf second-wait {
            type uint32 {
              range "1..2048";
            }
          } //second-wait

          leaf max-wait {
            type uint32 {
              range "1..2048";
            }
          } //max-wait

          leaf error-interval {
            type uint32 {
              range "0..2048";
            }
          } //error-interval

        } //container damp-peer-oscillations

        leaf damping {
          type boolean;
          description
              "Enable/disable (group level) BGP route damping for learned routes as defined 
               within the route policy";
        }

        container default-label-preference {
          description
              "Configure the default route preference for labeled routes learned at the group 
               level";
          leaf ebgp {
            type uint16 {
              range "0..255";
            }
          } //ebgp

          leaf ibgp {
            type uint16 {
              range "0..255";
            }
          } //ibgp

        } //container default-label-preference

        container default-preference {
          description
              "Configure the default route preference for routes learned at the group level";
          leaf ebgp {
            type uint16 {
              range "0..255";
            }
          } //ebgp

          leaf ibgp {
            type uint16 {
              range "0..255";
            }
          } //ibgp

        } //container default-preference

        container description {
          description
              "Create a textual description for the group";
          leaf description-string {
            type string {
              length "1..80";
            }
          } //description-string

        } //container description

        leaf disable-4byte-asn {
          type boolean;
          description
              "Enable/disable the advertisement of 4-byte ASN capability at the group level";
        }

        leaf disable-capability-negotiation {
          type boolean;
          description
              "Configure capability negotiation for this BGP group";
        }

        leaf disable-client-reflect {
          type boolean;
          description
              "Enable/disable the reflection of routes by the route reflector at the group 
               level";
        }

        container disable-communities {
          description
              "Configure BGP to disable sending communities";
          leaf standard {
            type boolean;
          } //standard

          leaf extended {
            type boolean;
          } //extended

          leaf large {
            type boolean;
          } //large

        } //container disable-communities

        leaf disable-fast-external-failover {
          type boolean;
          description
              "Configure BGP fast external failover";
        }

        container dynamic-neighbor-limit {
          description
              "Maximum number of dynamic neighbors should be configurable per-group";
          leaf dynamic-neighbor-limit-id {
            type uint32 {
              range "1..8192";
            }
          } //dynamic-neighbor-limit-id

        } //container dynamic-neighbor-limit

        container ebgp-default-reject-policy {
          description
              "Enable import/export of routes receive/sent from/to EBGP peers";
          leaf import {
            type boolean;
          } //import

          leaf export {
            type boolean;
          } //export

        } //container ebgp-default-reject-policy

        container ebgp-link-bandwidth {
          status "obsolete";
          description
              "Add Link Bandwidth Extended Community with static AS and bandwidth values";
          leaf-list family {
            type enumeration {
              enum ipv4;
              enum ipv6;
              enum label-ipv4;
            }
            max-elements 3;
          } //family

        } //container ebgp-link-bandwidth

        container enable-origin-validation {
          description
              "Enable/Disable Origin Validation for the bgp family";
          leaf ipv4 {
            type boolean;
            description
                "keyword - provision support of the specific family";
          } //ipv4

          leaf ipv6 {
            type boolean;
            description
                "keyword - provision support of the specific family";
          } //ipv6

          leaf label-ipv4 {
            type boolean;
            description
                "keyword - provision support of the specific family";
          } //label-ipv4

        } //container enable-origin-validation

        leaf enable-peer-tracking {
          type boolean;
          description
              "Enable/disable BGP peer tracking";
        }

        leaf enforce-first-as {
          type boolean;
          description
              "Enable/Disable First AS capability";
        }

        container export {
          description
              "Export route policies used to determine which routes are advertised to peers 
               for the group";
          leaf-list policy-name {
            type string;
            max-elements 15;
            description
                "Attribute policy-name for export";
          } //policy-name

          leaf plcy-or-long-expr {
            type string {
              length "1..255";
            }
            description
                "Attribute plcy-or-long-expr for export";
          } //plcy-or-long-expr

          leaf-list plcy-or-expr {
            type string {
              length "1..64";
            }
            max-elements 14;
            description
                "Attribute plcy-or-expr for export";
          } //plcy-or-expr

        } //container export

        container extended-nh-encoding {
          description
              "Configure the family for extended next-hop encoding";
          leaf ipv4 {
            type boolean;
            description
                "keyword - provision support of the specific family";
          } //ipv4

        } //container extended-nh-encoding

        container family {
          description
              "Configure the IP family capability";
          leaf ipv4 {
            type boolean;
            description
                "keyword - provision support of the specific family";
          } //ipv4

          leaf ipv6 {
            type boolean;
            description
                "keyword - provision support of the specific family";
          } //ipv6

          leaf mcast-ipv4 {
            type boolean;
            description
                "keyword - provision support of the specific family";
          } //mcast-ipv4

          leaf flow-ipv6 {
            type boolean;
            description
                "keyword - provision support of the specific family";
          } //flow-ipv6

          leaf flow-ipv4 {
            type boolean;
            description
                "keyword - provision support of the specific family";
          } //flow-ipv4

          leaf mcast-ipv6 {
            type boolean;
            description
                "keyword - provision support of the specific family";
          } //mcast-ipv6

          leaf label-ipv4 {
            type boolean;
            description
                "keyword - provision support of the specific family";
          } //label-ipv4

        } //container family

        leaf flowspec-validate {
          type boolean;
          status "obsolete";
          description
              "Enable/Disable Flowspec Validation";
        }

        container hold-time {
          description
              "Configure BGP hold time for the group";
          leaf seconds {
            type string;
            description
                "0|[3..65535]";
          } //seconds

          leaf min {
            type string;
          } //min

        } //container hold-time

        container import {
          description
              "Import route policies used to determine which routes are accepted from peers 
               for this group";
          leaf-list policy-name {
            type string;
            max-elements 15;
            description
                "Attribute policy-name for import";
          } //policy-name

          leaf plcy-or-long-expr {
            type string {
              length "1..255";
            }
            description
                "Attribute plcy-or-long-expr for import";
          } //plcy-or-long-expr

          leaf-list plcy-or-expr {
            type string {
              length "1..64";
            }
            max-elements 14;
            description
                "Attribute plcy-or-expr for import";
          } //plcy-or-expr

        } //container import

        leaf initial-send-delay-zero {
          type boolean;
          description
              "Enable/Disable Bypassing of Min Route Advertisement Timer countdown before 
               sending BGP update";
        }

        container keepalive {
          description
              "Configure BGP keepalive timer for the group";
          leaf seconds {
            type uint32 {
              range "0..21845";
            }
            default 30;
          } //seconds

        } //container keepalive

        container label-preference {
          description
              "Configure the route preference for labeled routes learned from the all 
               group-peers";
          leaf value {
            type uint16 {
              range "1..255";
            }
          } //value

        } //container label-preference

        container local-address {
          description
              "Local IP address used by the group when communicating with BGP peers";
          leaf ip-int-name-ip-address-ipv6-address {
            type string;
          } //ip-int-name-ip-address-ipv6-address

        } //container local-address

        container local-as {
          description
              "Add/remove a BGP virtual AS number for the group";
          leaf as-number {
            type uint32;
            description
                "[1..4294967295]";
          } //as-number

          leaf private {
            type boolean;
          } //private

          leaf no-prepend-global-as {
            type boolean;
          } //no-prepend-global-as

        } //container local-as

        container local-preference {
          description
              "Configure BGP local-preference attribute in incoming routes from group peers 
               if not specified";
          leaf local-preference {
            type uint32;
          } //local-preference

        } //container local-preference

        container loop-detect {
          description
              "Configure (group level) how the BGP peer session handles loop detection in the 
               AS Path";
          leaf drop-peer-discard-route-ignore-loop-off {
            type enumeration {
              enum drop-peer;
              enum discard-route;
              enum ignore-loop;
              enum off;
            }
            description
                "keywords";
          } //drop-peer-discard-route-ignore-loop-off

        } //container loop-detect

        container loop-detect-threshold {
          description
              "Limit the number of times global ASN appears in a received AS path";
          leaf loop-detect-threshold {
            type uint32 {
              range "0..15";
            }
            description
                "[0..15]";
          } //loop-detect-threshold

        } //container loop-detect-threshold

        container med-out {
          description
              "Enable/disable (group level) advertising the Multi-Exit Discriminator (MED)";
          leaf number {
            type uint32;
          } //number

          leaf igp-cost {
            type boolean;
          } //igp-cost

        } //container med-out

        container min-route-advertisement {
          description
              "Minimum interval (group level) at which a given prefix is advertised to a peer";
          leaf seconds {
            type uint16 {
              range "1..255";
            }
            description
                "[1..255]";
          } //seconds

        } //container min-route-advertisement

        container multihop {
          description
              "TTL value (group level) entered in the IP header of packets sent to a peer";
          leaf ttl-value {
            type uint8 {
              range "1..255";
            }
          } //ttl-value

        } //container multihop

        leaf multipath-eligible {
          type boolean;
          description
              "Enable/disable multipath eligibility";
        }

        leaf next-hop-self {
          type boolean;
          description
              "Configure the group to always set the nexthop path attribute to itself when 
               advertising to a peer";
        }

        leaf passive {
          type boolean;
          description
              "Enable/disable passive mode for the BGP group";
        }

        leaf path-mtu-discovery {
          type boolean;
          description
              "Enable/Disable Path MTU Discovery";
        }

        container peer-as {
          description
              "Configure (group level) the AS number for the remote peer";
          leaf as-number {
            type uint32 {
              range "1..4294967295";
            }
            description
                "[1..4294967295]";
          } //as-number

        } //container peer-as

        container preference {
          description
              "Configure the route preference for routes learned from the all group-peers";
          leaf preference {
            type uint16 {
              range "1..255";
            }
          } //preference

        } //container preference

        list prefix-limit {
          key "family";
          description
              "Maximum number of routes BGP can learn from the peers for this group";
          leaf family-limit {
            type uint64 {
              range "1..4294967295";
            }
            description
                "Attribute family limit for prefix-limit";
          } //family-limit

          leaf log-only {
            type boolean;
          } //log-only

          leaf threshold {
            type uint32 {
              range "1..100";
            }
          } //threshold

          leaf idle-timeout {
            type boolean;
          } //idle-timeout

          leaf minutes {
            type int32 {
              range "1..1024";
            }
          } //minutes

          leaf forever {
            type boolean;
          } //forever

          leaf family {
            type enumeration {
              enum ipv4;
              enum ipv6;
              enum mcast-ipv4;
              enum flow-ipv4;
              enum flow-ipv6;
              enum mcast-ipv6;
              enum label-ipv4;
            }
          } //family

          leaf post-import {
            type boolean;
          } //post-import

        } //list prefix-limit

        container remove-private {
          description
              "Remove private AS numbers from the AS Path before advertising to the peers for 
               this group";
          leaf limited {
            type boolean;
            description
                "keyword";
          } //limited

          leaf skip-peer-as {
            type boolean;
            description
                "keyword";
          } //skip-peer-as

          leaf replace {
            type boolean;
            description
                "keyword";
          } //replace

        } //container remove-private

        container send-default {
          description
              "Configure default route";
          leaf ipv4 {
            type boolean;
            description
                "keyword - provision support of the specific family";
          } //ipv4

          leaf ipv6 {
            type boolean;
            description
                "keyword - provision support of the specific family";
          } //ipv6

          leaf export-policy {
            type string;
            description
                "Attribute export-policy for send-default";
          } //export-policy

        } //container send-default

        leaf shutdown {
          type boolean;
          description
              "Administratively enable/disable the BGP group";
        }

        leaf split-horizon {
          type boolean;
          description
              "Configure split horizon for the peers under this group";
        }

        leaf third-party-nexthop {
          type boolean;
          description
              "Enable third party next-hop processing";
        }

        container ttl-security {
          description
              "Configure TTL security parameters for incoming packet";
          leaf min-ttl-value {
            type int32 {
              range "1..255";
            }
            description
                "[1..255], minimum TTL value";
          } //min-ttl-value

          leaf log {
            type uint32 {
              range "101..199";
            }
          } //log

        } //container ttl-security

        container type {
          description
              "Configure the peers for this group as type internal or external";
          leaf internal-external {
            type enumeration {
              enum internal;
              enum external;
            }
            description
                "keywords";
          } //internal-external

        } //container type

        container dynamic-neighbor {
          description
              "Context to configure dynamic neighbor IP prefix ranges";
          list prefix {
            key "ip-prefix-ip-prefix-length";
            status "obsolete";
            description
                "Specifies the dynamic peer IP prefix ranges from which dynamic connections are 
                 allowed";
            leaf ip-prefix-ip-prefix-length {
              type string;
              description
                  "Attribute ip-prefix/ip-prefix-length for prefix";
            } //ip-prefix-ip-prefix-length

          } //list prefix

          container match {
            description
                "Configure match conditions";
            list prefix {
              key "ip-prefix-ip-prefix-length";
              description
                  "Specifies the dynamic peer IP prefix ranges from which dynamic connections are 
                   allowed";
              leaf ip-prefix-ip-prefix-length {
                type string;
                description
                    "Attribute ip-prefix/ip-prefix-length for prefix";
              } //ip-prefix-ip-prefix-length

              list allowed-peer-as {
                key "min-as-number max";
                description
                    "Configure allowed-peer AS range";
                leaf min-as-number {
                  type uint32 {
                    range "1..4294967295";
                  }
                } //min-as-number

                leaf max {
                  type uint32 {
                    range "1..4294967295";
                  }
                } //max

              } //list allowed-peer-as

            } //list prefix

          } //container match

        } //container dynamic-neighbor

        container error-handling {
          description
              "Enable/Disable Error Handling";
          leaf update-fault-tolerance {
            type boolean;
            description
                "Enable/Disable update-fault-tolerance";
          }

        } //container error-handling

        container graceful-restart {
          presence
              "Enable/disable graceful-restart for all BGP peers in the peergroup.";
          leaf enable-notification {
            type boolean;
            description
                "Enable/Disable NOTIFICATION-triggered graceful restart";
          }

          container restart-time {
            description
                "Configure BGP graceful restart time";
            leaf time {
              type uint32 {
                range "0..4095";
              }
            } //time

          } //container restart-time

          container stale-routes-time {
            description
                "Configure BGP graceful restart stale routes time period";
            leaf time {
              type uint32 {
                range "1..3600";
              }
            } //time

          } //container stale-routes-time

          container long-lived {
            presence
                "Enable/disable long-lived graceful-restart for VPRN BGP group";
            container advertise-stale-to-all-neighbors {
              description
                  "Enable/Disable BGP long-lived graceful restart advertise stale routes to 
                   neighbors";
              leaf without-no-export {
                type boolean;
                description
                    "keyword - Advertise stale routes to neighbors with the addition of the 
                     LLGR_STALE community";
              } //without-no-export

            } //container advertise-stale-to-all-neighbors

            container advertised-stale-time {
              description
                  "Configure BGP long-lived graceful restart advertised stale routes time period";
              leaf seconds {
                type uint32 {
                  range "0..16777215";
                }
              } //seconds

            } //container advertised-stale-time

            container forwarding-bits-set {
              description
                  "Configure F bit behavior for each AFI/SAFI";
              leaf forwarding-bits-set-id {
                type enumeration {
                  enum all;
                  enum non-fwd;
                }
              } //forwarding-bits-set-id

            } //container forwarding-bits-set

            container helper-override-restart-time {
              description
                  "Configure BGP long-lived graceful restart helper override restart time period";
              leaf second {
                type uint32 {
                  range "0..4095";
                }
              } //second

            } //container helper-override-restart-time

            container helper-override-stale-time {
              description
                  "Configure BGP long-lived graceful restart helper override stale routes time 
                   period";
              leaf seconds {
                type uint32 {
                  range "0..16777215";
                }
              } //seconds

            } //container helper-override-stale-time

            list family {
              key "family-id";
              description
                  "Configure Family specific long-lived graceful-restart parameters for BGP peer 
                   group";
              leaf family-id {
                type enumeration {
                  enum ipv4;
                  enum ipv6;
                  enum label-ipv4;
                  enum flow-ipv4;
                  enum flow-ipv6;
                }
              } //family-id

              container advertised-stale-time {
                description
                    "Configure BGP long-lived graceful restart advertised stale routes time period 
                     for this Family";
                leaf seconds {
                  type uint32 {
                    range "0..16777215";
                  }
                } //seconds

              } //container advertised-stale-time

              container helper-override-stale-time {
                description
                    "Configure BGP long-lived graceful restart helper override stale routes time 
                     period per family";
                leaf seconds {
                  type uint32 {
                    range "0..16777215";
                  }
                } //seconds

              } //container helper-override-stale-time

            } //list family

          } //container long-lived

        } //container graceful-restart

        container link-bandwidth {
          description
              "Link Bandwidth Extended Community with static AS and bandwidth values";
          container accept-from-ebgp {
            description
                "Configure families for accept-from-ebgp";
            leaf-list family {
              type enumeration {
                enum ipv4;
                enum ipv6;
                enum label-ipv4;
              }
              max-elements 3;
            } //family

          } //container accept-from-ebgp

          container add-to-received-ebgp {
            description
                "Add Link Bandwidth Extended Community with static AS and bandwidth values";
            leaf-list family {
              type enumeration {
                enum ipv4;
                enum ipv6;
                enum label-ipv4;
              }
              max-elements 3;
            } //family

          } //container add-to-received-ebgp

          container aggregate-used-paths {
            description
                "Configure families for aggregate-used-paths";
            leaf-list family {
              type enumeration {
                enum ipv4;
                enum ipv6;
                enum label-ipv4;
              }
              max-elements 3;
            } //family

          } //container aggregate-used-paths

          container send-to-ebgp {
            description
                "Configure families for send-to-ebgp";
            leaf-list family {
              type enumeration {
                enum ipv4;
                enum ipv6;
                enum label-ipv4;
              }
              max-elements 3;
            } //family

          } //container send-to-ebgp

        } //container link-bandwidth

        container monitor {
          presence
              "Configure BMP Monitoring";
          container route-monitoring {
            description
                "Configure when BMP messages are send";
            leaf pre-policy {
              type boolean;
            } //pre-policy

            leaf post-policy {
              type boolean;
            } //post-policy

          } //container route-monitoring

          leaf shutdown {
            type boolean;
            description
                "Enable or disable BMP monitoring station";
          }

          container station {
            description
                "Configure list of BMP stations";
            leaf-list name {
              type string {
                length "1..32";
              }
              max-elements 8;
            } //name

            leaf all {
              type boolean;
            } //all

          } //container station

        } //container monitor

        list neighbor {
          key "ip-address";
          description
              "Configure a neighbor for this group";
          leaf ip-address {
            type string;
            description
                "Attribute ip-address for neighbor";
          } //ip-address

          leaf advertise-inactive {
            type boolean;
            description
                "Enable/disable advertising of inactive BGP routes to other BGP peers";
          }

          container advertise-ipv6-next-hops {
            description
                "Enable/Disable setting of next-hops to global ipv6 address for the family";
            leaf ipv4 {
              type boolean;
              description
                  "keyword - provision support of the specific family";
            } //ipv4

          } //container advertise-ipv6-next-hops

          container advertise-label {
            status "obsolete";
            description
                "Configure advertisement label for the peer using 6PE approach";
            leaf ipv4 {
              type boolean;
            } //ipv4

          } //container advertise-label

          leaf aggregator-id-zero {
            type boolean;
            description
                "Enable/disable (neighbor level) setting the service vprn ID to 0 in the 
                 aggregator path attribute";
          }

          leaf as-override {
            type boolean;
            description
                "Enable/disable (neighbor level) AS override";
          }

          container auth-keychain {
            description
                "Configure TCP authentication keychain to use for the session";
            leaf name {
              type string {
                length "1..32";
              }
              description
                  "keychain-name (32 char max)";
            } //name

          } //container auth-keychain

          container authentication-key {
            description
                "Configure the BGP authentication key for the peer";
            leaf authentication-key-hash-key {
              type string {
                length "1..500";
              }
              description
                  "authentication-key - [255 chars max] 
                   hash-key 
                   hash2-key 
                   custom-key";
            } //authentication-key-hash-key

            leaf hash-hash2-custom {
              type enumeration {
                enum hash;
                enum hash2;
                enum custom;
              }
              description
                  "keywords - specify hashing scheme";
            } //hash-hash2-custom

          } //container authentication-key

          leaf bfd-enable {
            type boolean;
            description
                "Enable BFD";
          }

          container cluster {
            description
                "Configure the cluster ID for a route reflector server";
            leaf cluster-id {
              type inet:ip-address;
              description
                  "expressed in dotted decimal format (a.b.c.d)";
            } //cluster-id

          } //container cluster

          container connect-retry {
            description
                "Configure the BGP Connect Retry timer value for the neighbor";
            leaf seconds {
              type uint32 {
                range "1..65535";
              }
            } //seconds

          } //container connect-retry

          container damp-peer-oscillations {
            description
                "Configure BGP for damp peer oscillations";
            leaf idle-hold-time {
              type boolean;
            } //idle-hold-time

            leaf initial-wait {
              type uint32 {
                range "0..2048";
              }
            } //initial-wait

            leaf second-wait {
              type uint32 {
                range "1..2048";
              }
            } //second-wait

            leaf max-wait {
              type uint32 {
                range "1..2048";
              }
            } //max-wait

            leaf error-interval {
              type uint32 {
                range "0..2048";
              }
            } //error-interval

          } //container damp-peer-oscillations

          leaf damping {
            type boolean;
            description
                "Enable/disable (neighbor level) BGP route damping for learned routes as 
                 defined within the route policy";
          }

          container default-label-preference {
            description
                "Configure the default route preference for labeled routes learned from this 
                 neighbor";
            leaf ebgp {
              type uint16 {
                range "0..255";
              }
            } //ebgp

            leaf ibgp {
              type uint16 {
                range "0..255";
              }
            } //ibgp

          } //container default-label-preference

          container default-preference {
            description
                "Configure the default route preference for routes learned from this neighbor";
            leaf ebgp {
              type uint16 {
                range "0..255";
              }
            } //ebgp

            leaf ibgp {
              type uint16 {
                range "0..255";
              }
            } //ibgp

          } //container default-preference

          container description {
            description
                "Create a textual description for the neighbor";
            leaf description-string {
              type string {
                length "1..80";
              }
            } //description-string

          } //container description

          leaf disable-4byte-asn {
            type boolean;
            description
                "Enable/disable the advertisement of 4-byte ASN capability at the peer level";
          }

          leaf disable-capability-negotiation {
            type boolean;
            description
                "Configure capability negotiation for BGP peer";
          }

          leaf disable-client-reflect {
            type boolean;
            description
                "Enable/disable the reflection of routes by the route reflector at the peer 
                 level";
          }

          container disable-communities {
            description
                "Configure BGP to disable sending communities";
            leaf standard {
              type boolean;
            } //standard

            leaf extended {
              type boolean;
            } //extended

            leaf large {
              type boolean;
            } //large

          } //container disable-communities

          leaf disable-fast-external-failover {
            type boolean;
            description
                "Configure BGP fast external failover";
          }

          container ebgp-default-reject-policy {
            description
                "Enable import/export of routes receive/sent from/to EBGP peers";
            leaf import {
              type boolean;
            } //import

            leaf export {
              type boolean;
            } //export

          } //container ebgp-default-reject-policy

          container ebgp-link-bandwidth {
            status "obsolete";
            description
                "Add Link Bandwidth Extended Community with static AS and bandwidth values";
            leaf-list family {
              type enumeration {
                enum ipv4;
                enum ipv6;
                enum label-ipv4;
              }
              max-elements 3;
            } //family

          } //container ebgp-link-bandwidth

          container enable-origin-validation {
            description
                "Enable/Disable Origin Validation for the bgp family";
            leaf ipv4 {
              type boolean;
              description
                  "keyword - provision support of the specific family";
            } //ipv4

            leaf ipv6 {
              type boolean;
              description
                  "keyword - provision support of the specific family";
            } //ipv6

            leaf label-ipv4 {
              type boolean;
              description
                  "keyword - provision support of the specific family";
            } //label-ipv4

          } //container enable-origin-validation

          leaf enable-peer-tracking {
            type boolean;
            description
                "Enable/disable BGP peer tracking";
          }

          leaf enforce-first-as {
            type boolean;
            description
                "Enable/Disable First AS capability";
          }

          container export {
            description
                "Export route policies used to determine which routes are advertised to this 
                 neighbor";
            leaf-list policy-name {
              type string;
              max-elements 15;
              description
                  "Attribute policy-name for export";
            } //policy-name

            leaf plcy-or-long-expr {
              type string {
                length "1..255";
              }
              description
                  "Attribute plcy-or-long-expr for export";
            } //plcy-or-long-expr

            leaf-list plcy-or-expr {
              type string {
                length "1..64";
              }
              max-elements 14;
              description
                  "Attribute plcy-or-expr for export";
            } //plcy-or-expr

          } //container export

          container extended-nh-encoding {
            description
                "Configure the family for extended next-hop encoding";
            leaf ipv4 {
              type boolean;
              description
                  "keyword - provision support of the specific family";
            } //ipv4

          } //container extended-nh-encoding

          container family {
            description
                "Configure the IP family capability";
            leaf ipv4 {
              type boolean;
              description
                  "keyword - provision support of the specific family";
            } //ipv4

            leaf ipv6 {
              type boolean;
              description
                  "keyword - provision support of the specific family";
            } //ipv6

            leaf mcast-ipv4 {
              type boolean;
              description
                  "keyword - provision support of the specific family";
            } //mcast-ipv4

            leaf flow-ipv6 {
              type boolean;
              description
                  "keyword - provision support of the specific family";
            } //flow-ipv6

            leaf flow-ipv4 {
              type boolean;
              description
                  "keyword - provision support of the specific family";
            } //flow-ipv4

            leaf mcast-ipv6 {
              type boolean;
              description
                  "keyword - provision support of the specific family";
            } //mcast-ipv6

            leaf label-ipv4 {
              type boolean;
              description
                  "keyword - provision support of the specific family";
            } //label-ipv4

          } //container family

          leaf flowspec-validate {
            type boolean;
            status "obsolete";
            description
                "Enable/Disable Flowspec Validation";
          }

          container hold-time {
            description
                "Configure BGP hold time for the neighbor";
            leaf seconds {
              type string;
              description
                  "0|[3..65535]";
            } //seconds

            leaf min {
              type string;
            } //min

          } //container hold-time

          container import {
            description
                "Import route policies used to determine which routes are accepted from this 
                 neighbor";
            leaf-list policy-name {
              type string;
              max-elements 15;
              description
                  "Attribute policy-name for import";
            } //policy-name

            leaf plcy-or-long-expr {
              type string {
                length "1..255";
              }
              description
                  "Attribute plcy-or-long-expr for import";
            } //plcy-or-long-expr

            leaf-list plcy-or-expr {
              type string {
                length "1..64";
              }
              max-elements 14;
              description
                  "Attribute plcy-or-expr for import";
            } //plcy-or-expr

          } //container import

          leaf initial-send-delay-zero {
            type boolean;
            description
                "Enable/Disable Bypassing of Min Route Advertisement Timer countdown before 
                 sending BGP update";
          }

          container keepalive {
            description
                "Configure BGP keepalive timer for the neighbor";
            leaf seconds {
              type uint32 {
                range "0..21845";
              }
              default 30;
            } //seconds

          } //container keepalive

          container label-preference {
            description
                "Configure the route preference for labeled routes learned from this neighbor";
            leaf value {
              type uint16 {
                range "1..255";
              }
            } //value

          } //container label-preference

          container local-address {
            description
                "Local IP address used by the neighbor when communicating with BGP peers";
            leaf ip-int-name-ip-address-ipv6-address {
              type string;
            } //ip-int-name-ip-address-ipv6-address

          } //container local-address

          container local-as {
            description
                "Add/remove a BGP virtual AS number for the neighbor";
            leaf as-number {
              type uint32 {
                range "1..4294967295";
              }
            } //as-number

            leaf private {
              type boolean;
            } //private

            leaf no-prepend-global-as {
              type boolean;
            } //no-prepend-global-as

          } //container local-as

          container local-preference {
            description
                "Configure BGP local-preference attribute in incoming routes from this neighbor 
                 if not specified";
            leaf local-preference {
              type uint32;
            } //local-preference

          } //container local-preference

          container loop-detect {
            description
                "Configure (neighbor level) how the BGP peer session handles loop detection in 
                 the AS Path";
            leaf drop-peer-discard-route-ignore-loop-off {
              type enumeration {
                enum drop-peer;
                enum discard-route;
                enum ignore-loop;
                enum off;
              }
              description
                  "keywords";
            } //drop-peer-discard-route-ignore-loop-off

          } //container loop-detect

          container loop-detect-threshold {
            description
                "Limit the number of times global ASN appears in a received AS path";
            leaf loop-detect-threshold {
              type uint32 {
                range "0..15";
              }
              description
                  "[0..15]";
            } //loop-detect-threshold

          } //container loop-detect-threshold

          container med-out {
            description
                "Enable/disable (neighbor level) advertising the Multi-Exit Discriminator (MED)";
            leaf number {
              type uint32;
            } //number

            leaf igp-cost {
              type boolean;
            } //igp-cost

          } //container med-out

          container min-route-advertisement {
            description
                "Minimum interval (neighbor level) at which a given prefix is advertised to a 
                 peer";
            leaf seconds {
              type uint16 {
                range "1..255";
              }
              description
                  "[1..255]";
            } //seconds

          } //container min-route-advertisement

          container multihop {
            description
                "TTL value (neighbor level) entered in the IP header of packets sent to a peer";
            leaf ttl-value {
              type uint8 {
                range "1..255";
              }
            } //ttl-value

          } //container multihop

          leaf multipath-eligible {
            type boolean;
            description
                "Enable/disable multipath eligibility";
          }

          leaf next-hop-self {
            type boolean;
            description
                "Configure the neighbor to always set the nexthop path attribute to itself when 
                 advertising to a peer";
          }

          leaf passive {
            type boolean;
            description
                "Enable/disable passive mode for the BGP neighbor";
          }

          leaf path-mtu-discovery {
            type boolean;
            description
                "Enable/Disable Path MTU Discovery";
          }

          container peer-as {
            description
                "Configure (neighbor level) the AS number for the remote peer";
            leaf as-number {
              type uint32 {
                range "1..4294967295";
              }
            } //as-number

          } //container peer-as

          container preference {
            description
                "Configure the route preference for routes learned from this neighbor";
            leaf preference {
              type uint16 {
                range "1..255";
              }
            } //preference

          } //container preference

          list prefix-limit {
            key "family";
            description
                "Maximum number of routes BGP can learn from this neighbor";
            leaf family-limit {
              type uint64 {
                range "1..4294967295";
              }
              description
                  "Attribute family limit for prefix-limit";
            } //family-limit

            leaf log-only {
              type boolean;
            } //log-only

            leaf threshold {
              type uint32 {
                range "1..100";
              }
            } //threshold

            leaf idle-timeout {
              type boolean;
            } //idle-timeout

            leaf minutes {
              type int32 {
                range "1..1024";
              }
            } //minutes

            leaf forever {
              type boolean;
            } //forever

            leaf family {
              type enumeration {
                enum ipv4;
                enum ipv6;
                enum mcast-ipv4;
                enum flow-ipv4;
                enum flow-ipv6;
                enum mcast-ipv6;
                enum label-ipv4;
              }
            } //family

            leaf post-import {
              type boolean;
            } //post-import

          } //list prefix-limit

          container remove-private {
            description
                "Remove private AS numbers from the AS Path before advertising to this neighbor";
            leaf limited {
              type boolean;
              description
                  "keyword";
            } //limited

            leaf skip-peer-as {
              type boolean;
              description
                  "keyword";
            } //skip-peer-as

            leaf replace {
              type boolean;
              description
                  "keyword";
            } //replace

          } //container remove-private

          container send-default {
            description
                "Configure default route";
            leaf ipv4 {
              type boolean;
              description
                  "keyword - provision support of the specific family";
            } //ipv4

            leaf ipv6 {
              type boolean;
              description
                  "keyword - provision support of the specific family";
            } //ipv6

            leaf export-policy {
              type string;
              description
                  "Attribute export-policy for send-default";
            } //export-policy

          } //container send-default

          leaf shutdown {
            type boolean;
            description
                "Administratively enable/disable the BGP neighbor";
          }

          leaf split-horizon {
            type boolean;
            description
                "Configure split horizon for the peer";
          }

          leaf third-party-nexthop {
            type boolean;
            description
                "Enable third party next-hop processing";
          }

          container ttl-security {
            description
                "Configure TTL security parameters for incoming packet";
            leaf min-ttl-value {
              type int32 {
                range "1..255";
              }
              description
                  "[1..255], minimum TTL value";
            } //min-ttl-value

            leaf log {
              type uint32 {
                range "101..199";
              }
            } //log

          } //container ttl-security

          container type {
            description
                "Configure this neighbor as type internal or external";
            leaf internal-external {
              type enumeration {
                enum internal;
                enum external;
              }
              description
                  "keywords";
            } //internal-external

          } //container type

          container error-handling {
            description
                "Enable/Disable Error Handling";
            leaf update-fault-tolerance {
              type boolean;
              description
                  "Enable/Disable update-fault-tolerance";
            }

          } //container error-handling

          container graceful-restart {
            presence
                "Enable/disable graceful-restart for a specific BGP peer.";
            leaf enable-notification {
              type boolean;
              description
                  "Enable/Disable NOTIFICATION-triggered graceful restart";
            }

            container restart-time {
              description
                  "Configure BGP graceful restart time";
              leaf time {
                type uint32 {
                  range "0..4095";
                }
              } //time

            } //container restart-time

            container stale-routes-time {
              description
                  "Configure BGP graceful restart stale routes time period";
              leaf time {
                type uint32 {
                  range "1..3600";
                }
              } //time

            } //container stale-routes-time

            container long-lived {
              presence
                  "Enable/disable long-lived graceful-restart for BGP peer";
              container advertise-stale-to-all-neighbors {
                description
                    "Enable/Disable BGP long-lived graceful restart advertise stale routes to 
                     neighbors";
                leaf without-no-export {
                  type boolean;
                  description
                      "keyword - Advertise stale routes to neighbors with the addition of the 
                       LLGR_STALE community";
                } //without-no-export

              } //container advertise-stale-to-all-neighbors

              container advertised-stale-time {
                description
                    "Configure BGP long-lived graceful restart advertised stale routes time period";
                leaf seconds {
                  type uint32 {
                    range "0..16777215";
                  }
                } //seconds

              } //container advertised-stale-time

              container forwarding-bits-set {
                description
                    "Configure F bit behavior for each AFI/SAFI";
                leaf forwarding-bits-set-id {
                  type enumeration {
                    enum all;
                    enum non-fwd;
                  }
                } //forwarding-bits-set-id

              } //container forwarding-bits-set

              container helper-override-restart-time {
                description
                    "Configure BGP long-lived graceful restart helper override restart time period";
                leaf second {
                  type uint32 {
                    range "0..4095";
                  }
                } //second

              } //container helper-override-restart-time

              container helper-override-stale-time {
                description
                    "Configure BGP long-lived graceful restart helper override stale routes time 
                     period";
                leaf seconds {
                  type uint32 {
                    range "0..16777215";
                  }
                } //seconds

              } //container helper-override-stale-time

              list family {
                key "family-id";
                description
                    "Configure Family specific long-lived graceful-restart parameters for BGP peer";
                leaf family-id {
                  type enumeration {
                    enum ipv4;
                    enum ipv6;
                    enum label-ipv4;
                    enum flow-ipv4;
                    enum flow-ipv6;
                  }
                } //family-id

                container advertised-stale-time {
                  description
                      "Configure BGP long-lived graceful restart advertised stale routes time period 
                       for this Family";
                  leaf seconds {
                    type uint32 {
                      range "0..16777215";
                    }
                  } //seconds

                } //container advertised-stale-time

                container helper-override-stale-time {
                  description
                      "Configure BGP long-lived graceful restart helper override stale routes time 
                       period per family";
                  leaf seconds {
                    type uint32 {
                      range "0..16777215";
                    }
                  } //seconds

                } //container helper-override-stale-time

              } //list family

            } //container long-lived

          } //container graceful-restart

          container link-bandwidth {
            description
                "Link Bandwidth Extended Community with static AS and bandwidth values";
            container accept-from-ebgp {
              description
                  "Configure families for accept-from-ebgp";
              leaf-list family {
                type enumeration {
                  enum ipv4;
                  enum ipv6;
                  enum label-ipv4;
                }
                max-elements 3;
              } //family

            } //container accept-from-ebgp

            container add-to-received-ebgp {
              description
                  "Add Link Bandwidth Extended Community with static AS and bandwidth values";
              leaf-list family {
                type enumeration {
                  enum ipv4;
                  enum ipv6;
                  enum label-ipv4;
                }
                max-elements 3;
              } //family

            } //container add-to-received-ebgp

            container aggregate-used-paths {
              description
                  "Configure families for aggregate-used-paths";
              leaf-list family {
                type enumeration {
                  enum ipv4;
                  enum ipv6;
                  enum label-ipv4;
                }
                max-elements 3;
              } //family

            } //container aggregate-used-paths

            container send-to-ebgp {
              description
                  "Configure families for send-to-ebgp";
              leaf-list family {
                type enumeration {
                  enum ipv4;
                  enum ipv6;
                  enum label-ipv4;
                }
                max-elements 3;
              } //family

            } //container send-to-ebgp

          } //container link-bandwidth

          container monitor {
            presence
                "Configure BMP Monitoring";
            container route-monitoring {
              description
                  "Configure when BMP messages are send";
              leaf pre-policy {
                type boolean;
              } //pre-policy

              leaf post-policy {
                type boolean;
              } //post-policy

            } //container route-monitoring

            leaf shutdown {
              type boolean;
              description
                  "Enable or disable BMP monitoring station";
            }

            container station {
              description
                  "Configure list of BMP stations";
              leaf-list name {
                type string {
                  length "1..32";
                }
                max-elements 8;
              } //name

              leaf all {
                type boolean;
              } //all

            } //container station

          } //container monitor

        } //list neighbor

      } //list group

      container monitor {
        presence
            "Configure BMP Monitoring";
        container route-monitoring {
          description
              "Configure when BMP messages are send";
          leaf pre-policy {
            type boolean;
          } //pre-policy

          leaf post-policy {
            type boolean;
          } //post-policy

        } //container route-monitoring

        leaf shutdown {
          type boolean;
          description
              "Enable or disable BMP monitoring station";
        }

        container station {
          description
              "Configure list of BMP stations";
          leaf-list name {
            type string {
              length "1..32";
            }
            max-elements 8;
          } //name

          leaf all {
            type boolean;
          } //all

        } //container station

      } //container monitor

      container multi-path {
        description
            "Configure multi-path";
        container ipv4 {
          description
              "Configure ipv4 multi-path maximum-paths";
          leaf max-paths {
            type string;
            description
                "Attribute max-paths for ipv4";
          } //max-paths

          leaf ebgp {
            type string;
            description
                "Attribute ebgp-max-paths for ipv4";
          } //ebgp

          leaf ibgp {
            type string;
            description
                "Attribute ibgp-max-paths for ipv4";
          } //ibgp

          leaf restrict {
            type enumeration {
              enum same-neighbor-as;
              enum exact-as-path;
            }
          } //restrict

          leaf unequal-cost {
            type boolean;
          } //unequal-cost

        } //container ipv4

        container ipv6 {
          description
              "Configure ipv6 multi-path maximum-paths";
          leaf max-paths {
            type string;
            description
                "Attribute max-paths for ipv6";
          } //max-paths

          leaf ebgp {
            type string;
            description
                "Attribute ebgp-max-paths for ipv6";
          } //ebgp

          leaf ibgp {
            type string;
            description
                "Attribute ibgp-max-paths for ipv6";
          } //ibgp

          leaf restrict {
            type enumeration {
              enum same-neighbor-as;
              enum exact-as-path;
            }
          } //restrict

          leaf unequal-cost {
            type boolean;
          } //unequal-cost

        } //container ipv6

        container label-ipv4 {
          description
              "Configure label-ipv4 multi-path maximum-paths";
          leaf max-paths {
            type string;
            description
                "Attribute max-paths for label-ipv4";
          } //max-paths

          leaf ebgp {
            type string;
            description
                "Attribute ebgp-max-paths for label-ipv4";
          } //ebgp

          leaf ibgp {
            type string;
            description
                "Attribute ibgp-max-paths for label-ipv4";
          } //ibgp

          leaf restrict {
            type enumeration {
              enum same-neighbor-as;
              enum exact-as-path;
            }
          } //restrict

          leaf unequal-cost {
            type boolean;
          } //unequal-cost

        } //container label-ipv4

        container maximum-paths {
          description
              "Configure multi-path maximum-paths";
          leaf max-paths {
            type string;
            description
                "Attribute max-paths for maximum-paths";
          } //max-paths

          leaf ebgp {
            type string;
            description
                "Attribute ebgp-max-paths for maximum-paths";
          } //ebgp

          leaf ibgp {
            type string;
            description
                "Attribute ibgp-max-paths for maximum-paths";
          } //ibgp

          leaf restrict {
            type enumeration {
              enum same-neighbor-as;
              enum exact-as-path;
            }
          } //restrict

          leaf unequal-cost {
            type boolean;
          } //unequal-cost

        } //container maximum-paths

      } //container multi-path

      container next-hop-resolution {
        description
            "Configure Next-hop Resolution";
        container policy {
          description
              "Configure Next-hop Resolution policy";
          leaf policy-name {
            type string;
            description
                "Attribute policy-name for policy";
          } //policy-name

        } //container policy

        leaf use-bgp-routes {
          type boolean;
          description
              "Enable/Disable Use BGP routes to resolve BGP nexthop";
        }

      } //container next-hop-resolution

      container rib-management {
        description
            "Configure RIB Management";
        container ipv4 {
          description
              "Configure RIB Management for IPv4";
          container leak-import {
            description
                "Configure RIB leak import policies";
            leaf-list policy-name {
              type string;
              max-elements 15;
              description
                  "Attribute policy-name for leak-import";
            } //policy-name

            leaf plcy-or-long-expr {
              type string {
                length "1..255";
              }
              description
                  "Attribute plcy-or-long-expr for leak-import";
            } //plcy-or-long-expr

            leaf-list plcy-or-expr {
              type string {
                length "1..64";
              }
              max-elements 14;
              description
                  "Attribute plcy-or-expr for leak-import";
            } //plcy-or-expr

          } //container leak-import

          container route-table-import {
            description
                "Enables/Disables import of routes from RTM into RIB";
            leaf policy-name {
              type string;
              description
                  "Attribute policy-name for route-table-import";
            } //policy-name

          } //container route-table-import

        } //container ipv4

        container ipv6 {
          description
              "Configure RIB Management for IPv6";
          container leak-import {
            description
                "Configure RIB leak import policies";
            leaf-list policy-name {
              type string;
              max-elements 15;
              description
                  "Attribute policy-name for leak-import";
            } //policy-name

            leaf plcy-or-long-expr {
              type string {
                length "1..255";
              }
              description
                  "Attribute plcy-or-long-expr for leak-import";
            } //plcy-or-long-expr

            leaf-list plcy-or-expr {
              type string {
                length "1..64";
              }
              max-elements 14;
              description
                  "Attribute plcy-or-expr for leak-import";
            } //plcy-or-expr

          } //container leak-import

          container route-table-import {
            description
                "Enables/Disables import of routes from RTM into RIB";
            leaf policy-name {
              type string;
              description
                  "Attribute policy-name for route-table-import";
            } //policy-name

          } //container route-table-import

        } //container ipv6

        container label-ipv4 {
          description
              "Configure RIB Management for label-ipv4";
          container leak-import {
            description
                "Configure RIB leak import policies";
            leaf-list policy-name {
              type string;
              max-elements 15;
              description
                  "Attribute policy-name for leak-import";
            } //policy-name

            leaf plcy-or-long-expr {
              type string {
                length "1..255";
              }
              description
                  "Attribute plcy-or-long-expr for leak-import";
            } //plcy-or-long-expr

            leaf-list plcy-or-expr {
              type string {
                length "1..64";
              }
              max-elements 14;
              description
                  "Attribute plcy-or-expr for leak-import";
            } //plcy-or-expr

          } //container leak-import

          container route-table-import {
            description
                "Enables/Disables import of routes from RTM into RIB";
            leaf policy-name {
              type string;
              description
                  "Attribute policy-name for route-table-import";
            } //policy-name

          } //container route-table-import

        } //container label-ipv4

      } //container rib-management

    } //container bgp

  } //grouping alu-conf-svc-vprn-bgp-r13

} //module  alu-conf-svc-vprn-bgp-r13
