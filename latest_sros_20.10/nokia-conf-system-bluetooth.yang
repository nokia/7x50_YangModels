submodule nokia-conf-system-bluetooth {

    yang-version "1.1";

    belongs-to nokia-conf { prefix "conf"; }

    import ietf-yang-types                { prefix "yang"; }
    import nokia-sros-yang-extensions     { prefix "sros-ext"; }
    import nokia-types-card               { prefix "types-card"; }
    import nokia-types-sros               { prefix "types-sros"; }

    include nokia-conf-groups;

    sros-ext:sros-major-release "rel20";

    organization "Nokia";

    contact
        "Nokia SR OS Support
         Web: <http://www.nokia.com>";

    description
        "Nokia YANG Data model to configure system bluetooth on SR OS based routers.

         Copyright 2016 Nokia. All rights reserved. Reproduction of this document
         is authorized on the condition that the foregoing copyright notice is included.

         This nokia-conf-system-bluetooth YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-09-16";

    grouping conf-system-bluetooth {
        container bluetooth {
            description "Enter the bluetooth context";

            leaf passkey {
                type string {
                    length "6";
                    pattern "[0-9]+" {
                        error-message "passkey can only contain digits";
                    }
                }
                default "123456";
                description "Bluetooth passkey";
            }

            leaf admin-state {
                type types-sros:admin-state;
                default "disable";
                description "Specifies the desired administrative state of the bluetooth module.";
            }

            leaf advertising-timeout {
                type uint32 {
                    range "30..3600";
                }
                units "seconds";
                description "Bluetooth advertising timeout";
            }

            leaf power-mode {
                type enumeration {
                    enum "manual"                       { value 1; }
                    enum "automatic"                    { value 2; }
                }
                default "automatic";
                description "Bluetooth module(s) power mode.";
            }

            leaf pairing-button {
                type boolean;
                default "false";
                description "Enable the pairing button";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            leaf power {
                status obsolete;
                type enumeration {
                    enum "manual"                       { value 1; }
                    enum "automatic"                    { value 2; }
                }
                description "Bluetooth module power state";
            }

            list device {
                key "mac-address";
                max-elements 5;
                description "Enter the device list instance";

                leaf mac-address {
                    type yang:mac-address;
                    description "Bluetooth client device MAC address";
                }

                leaf description {
                    type types-sros:description;
                    description "Text description";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list device

            list module {
                key "cpm-slot";
                description "Enter the module list instance";

                leaf cpm-slot {
                    type types-card:cpm-card-slot;
                    description "CPM slot on which the module resides";
                }

                leaf provisioned-identifier {
                    type types-sros:display-string {
                        length "1..32";
                        pattern ".*\\S.*" {
                            error-message "provisioned-identifier must not be all spaces";
                        }
                    }
                    description "Bluetooth module ID";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list module

        } // container bluetooth

    } // grouping conf-system-bluetooth

}
