submodule nokia-state-submgt-gtp {

    yang-version "1.1";

    belongs-to nokia-state { prefix "state"; }

    import ietf-yang-types                { prefix "yang"; }
    import nokia-sros-yang-extensions     { prefix "sros-ext"; }
    import nokia-types-cellular           { prefix "types-cellular"; }
    import nokia-types-sros               { prefix "types-sros"; }
    import nokia-types-wlangw             { prefix "types-wlangw"; }


    sros-ext:sros-major-release "rel21";

    organization "Nokia";

    contact
        "Nokia SR OS Support
         Web: <http://www.nokia.com>";

    description
        "Nokia YANG Data model with operational state for subscriber management gtp on SR OS based routers.

         Copyright 2016 Nokia. All rights reserved. Reproduction of this document
         is authorized on the condition that the foregoing copyright notice is included.

         This nokia-state-submgt-gtp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-10-07";

    grouping state-submgt-gtp {
        container gtp {
            description "Enter the gtp context";

            container statistics {
                description "Enter the statistics context";

                leaf rx-packets {
                    type yang:counter64;
                    description "Total number of GTP control-plane packets received.";
                }

                leaf tx-packets {
                    type yang:counter64;
                    description "Total Number of GTP control-plane packets sent.";
                }

                container connections {
                    description "Enter the connections context";

                    leaf mme-peers {
                        type yang:gauge32;
                        description "Number of MME peers";
                    }

                    leaf enodeb-peers {
                        type yang:gauge32;
                        description "Number of ENODE-B peers";
                    }

                    leaf s11-sessions {
                        type yang:gauge32;
                        description "Number of S11 sessions";
                    }

                    leaf s11-idle-sessions {
                        type yang:gauge32;
                        description "Number of S11 idle sessions";
                    }

                    leaf mobile-gateway-peers {
                        type yang:gauge32;
                        description "Number of mobile gateway (GGS or PGW) peerings active for GTP uplink";
                    }

                    leaf uplink-sessions {
                        type yang:gauge32;
                        description "Number of uplink sessions";
                    }

                    leaf current-held-uplinks {
                        type yang:gauge32;
                        description "Number of uplinks in hold";
                    }

                } // container connections

                container path-management {
                    description "Enter the path-management context";

                    leaf tx-echo-requests {
                        type yang:counter64;
                        description "Number of echo requests transmitted.";
                    }

                    leaf tx-echo-responses {
                        type yang:counter64;
                        description "Number of echo responses transmitted.";
                    }

                    leaf rx-echo-requests {
                        type yang:counter64;
                        description "Number of echo requests received.";
                    }

                    leaf rx-echo-responses {
                        type yang:counter64;
                        description "Number of echo responses received.";
                    }

                    leaf path-faults {
                        type yang:counter64;
                        description "Number of path faults detected.";
                    }

                    leaf path-restarts {
                        type yang:counter64;
                        description "Number of path restarts.";
                    }

                } // container path-management

                container errors {
                    description "Enter the errors context";

                    leaf tx-errors {
                        type yang:counter64;
                        description "All other transmission errors.";
                    }

                    leaf tx-discarded-packets {
                        type yang:counter64;
                        description "Number of 'GTP version not supported' packets and 'responses with error cause' packets.";
                    }

                    leaf rx-errors {
                        type yang:counter64;
                        description "Total number of errors during hadling received packets.";
                    }

                    leaf rx-version-not-supported {
                        type yang:counter64;
                        description "Received GTP version not supported message.";
                    }

                    leaf rx-zero-teid-responses {
                        type yang:counter64;
                        description "Received response message with TEID 0.";
                    }

                    leaf rx-invalid-packet-length {
                        type yang:counter64;
                        description "Number of packets received with an invalid packet length.";
                    }

                    leaf rx-unknown-packets {
                        type yang:counter64;
                        description "Number of packets received that could not be recognized.";
                    }

                    leaf rx-missing-ie-packets {
                        type yang:counter64;
                        description "Number of packets received that contain missing IEs.";
                    }

                    leaf rx-bad-udp-headers {
                        type yang:counter64;
                        description "Number of packets received with incorrect UDP headers.";
                    }

                    leaf rx-discarded-packets {
                        type yang:counter64;
                        description "Number of discarded packets received.";
                    }

                    leaf rx-udp-checksum-errors {
                        type yang:counter64;
                        description "Number of packets received with failed UDP checksums.";
                    }

                    leaf rx-invalid-teid {
                        type yang:counter64;
                        description "Number of packets received with an invalid teid.";
                    }

                } // container errors

                container gtpv1 {
                    description "Enter the gtpv1 context";

                    leaf tx-create-pdp-context-requests {
                        type yang:counter64;
                        description "Number of PDP context requests transmitted.";
                    }

                    leaf tx-create-pdp-context-responses {
                        type yang:counter64;
                        description "Number of create PDP context responses transmitted.";
                    }

                    leaf tx-delete-pdp-context-requests {
                        type yang:counter64;
                        description "Number of delete PDP context requests transmitted.";
                    }

                    leaf tx-delete-pdp-context-responses {
                        type yang:counter64;
                        description "Number of delete PDP context responses transmitted.";
                    }

                    leaf rx-create-pdp-context-requests {
                        type yang:counter64;
                        description "Number of create PDP context requests received.";
                    }

                    leaf rx-create-pdp-context-responses {
                        type yang:counter64;
                        description "Number of create PDP context responses received.";
                    }

                    leaf rx-delete-pdp-context-requests {
                        type yang:counter64;
                        description "Number of delete PDP context requests received.";
                    }

                    leaf rx-delete-pdp-context-responses {
                        type yang:counter64;
                        description "Number of delete PDP context responses received.";
                    }

                } // container gtpv1

                container gtpv2 {
                    description "Enter the gtpv2 context";

                    leaf tx-create-session-requests {
                        type yang:counter64;
                        description "Number of create session requests transmitted.";
                    }

                    leaf tx-create-session-responses {
                        type yang:counter64;
                        description "Number of create session responses transmitted.";
                    }

                    leaf tx-delete-session-requests {
                        type yang:counter64;
                        description "Number of delete session requests transmitted.";
                    }

                    leaf tx-delete-session-responses {
                        type yang:counter64;
                        description "Number of delete session responses transmitted.";
                    }

                    leaf tx-delete-bearer-requests {
                        type yang:counter64;
                        description "Number of delete bearer requests transmitted.";
                    }

                    leaf tx-delete-bearer-responses {
                        type yang:counter64;
                        description "Number of delete bearer responses transmitted.";
                    }

                    leaf tx-create-bearer-responses {
                        type yang:counter64;
                        description "Number of create bearer responses transmitted.";
                    }

                    leaf tx-update-bearer-responses {
                        type yang:counter64;
                        description "Number of update bearer responses transmitted.";
                    }

                    leaf tx-modify-bearer-requests {
                        type yang:counter64;
                        description "Number of modify bearer requests transmitted.";
                    }

                    leaf tx-modify-bearer-responses {
                        type yang:counter64;
                        description "Number of modify bearer responses transmitted.";
                    }

                    leaf tx-change-notification-responses {
                        type yang:counter64;
                        description "Number of change notification responses transmitted.";
                    }

                    leaf tx-release-access-bearer-responses {
                        type yang:counter64;
                        description "Number of release access bearer responses transmitted.";
                    }

                    leaf tx-downlink-notifications {
                        type yang:counter64;
                        description "Number of downlink notifications transmitted.";
                    }

                    leaf tx-stop-paging-indications {
                        type yang:counter64;
                        description "Number of stop downlink indications transmitted.";
                    }

                    leaf rx-create-session-requests {
                        type yang:counter64;
                        description "Number of create session requests received.";
                    }

                    leaf rx-create-session-responses {
                        type yang:counter64;
                        description "Number of create session responses received.";
                    }

                    leaf rx-delete-session-requests {
                        type yang:counter64;
                        description "Number of delete session requests received.";
                    }

                    leaf rx-delete-session-responses {
                        type yang:counter64;
                        description "Number of delete session responses received.";
                    }

                    leaf rx-delete-bearer-requests {
                        type yang:counter64;
                        description "Number of delete bearer requests received.";
                    }

                    leaf rx-delete-bearer-responses {
                        type yang:counter64;
                        description "Number of delete bearer responses received.";
                    }

                    leaf rx-create-bearer-requests {
                        type yang:counter64;
                        description "Number of create bearer responses received.";
                    }

                    leaf rx-update-bearer-requests {
                        type yang:counter64;
                        description "Number of update bearer responses received.";
                    }

                    leaf rx-modify-bearer-requests {
                        type yang:counter64;
                        description "Number of modify bearer requests received.";
                    }

                    leaf rx-modify-bearer-responses {
                        type yang:counter64;
                        description "Number of modify bearer responses received.";
                    }

                    leaf rx-change-notification-requests {
                        type yang:counter64;
                        description "Number of change notification requests received.";
                    }

                    leaf rx-release-access-bearer-requests {
                        type yang:counter64;
                        description "Number of release access bearer requests received.";
                    }

                    leaf rx-downlink-notification-ack {
                        type yang:counter64;
                        description "Number of downlink notification ACK received.";
                    }

                    leaf rx-downlink-notification-failure {
                        type yang:counter64;
                        description "Number of downlink notification failures received.";
                    }

                } // container gtpv2

                container gtp-u {
                    description "Enter the gtp-u context";

                    leaf rx-error-indications {
                        type yang:counter64;
                        description "Number of GTP-U error indications received.";
                    }

                    leaf tx-error-indications {
                        type yang:counter64;
                        description "Number of GTP-U error indications transmitted.";
                    }

                    leaf tx-end-markers {
                        type yang:counter64;
                        description "Number of end markers transmitted.";
                    }

                } // container gtp-u

            } // container statistics

            container uplink {
                description "Enter the uplink context";

                list pdp-context {
                    key "imsi apn";
                    description "Enter the pdp-context list instance";

                    leaf imsi {
                        type types-cellular:imsi;
                        description "International Mobile Subscriber Identity";
                    }

                    leaf apn {
                        type types-cellular:apn;
                        description "Access point name";
                    }

                    leaf interface-type {
                        type types-wlangw:mobile-gateway-connection;
                        description "Interface type";
                    }

                    container ggsn {
                        description "Enter the ggsn context";

                        leaf data-address {
                            type types-sros:ip-address;
                            description "IP address";
                        }

                        leaf data-teid {
                            type uint32;
                            description "Data Transport Endpoint Identifier (TEID)";
                        }

                        leaf control-address {
                            type types-sros:ip-address;
                            description "Control IP address";
                        }

                        leaf control-teid {
                            type uint32;
                            description "Control Transport Endpoint Identifier (TEID)";
                        }

                    } // container ggsn

                    container local {
                        description "Enter the local context";

                        leaf data-teid {
                            type uint32;
                            description "Data Transport Endpoint Identifier (TEID)";
                        }

                        leaf router {
                            type types-sros:router-instance;
                            description "Router";
                        }

                        leaf control-address {
                            type types-sros:ip-address;
                            description "Control IP address";
                        }

                        leaf control-teid {
                            type uint32;
                            description "Control Transport Endpoint Identifier (TEID)";
                        }

                    } // container local

                    container qos {
                        description "Enter the qos context";

                        leaf uplink-gbr {
                            type uint32;
                            units "kilobps";
                            description "Uplink Guaranteed Bit Rate";
                        }

                        leaf uplink-mbr {
                            type uint32;
                            units "kilobps";
                            description "Uplink Maximum Bit Rate";
                        }

                        leaf downlink-gbr {
                            type uint32;
                            units "kilobps";
                            description "Downlinklink Guaranteed Bit Rate";
                        }

                        leaf downlink-mbr {
                            type uint32;
                            units "kilobps";
                            description "Downlink Maximum Bit Rate";
                        }

                        leaf qci {
                            type uint32;
                            description "QoS Class ID";
                        }

                        leaf arp {
                            type uint32;
                            description "Allocation/Retention Priority";
                        }

                        leaf uplink-ambr {
                            type uint32;
                            units "kilobps";
                            description "Uplink Aggregate Maximum Bit Rate";
                        }

                        leaf downlink-ambr {
                            type uint32;
                            units "kilobps";
                            description "Downlink Aggregate Maximum Bit Rate";
                        }

                    } // container qos

                    container charging-characteristics {
                        description "Enter the charging-characteristics context";

                        leaf roaming {
                            type boolean;
                        }

                        leaf bit0 {
                            type boolean;
                            description "Set bit 0 in charging characteristics information element (IE) for home UE";
                        }

                        leaf bit1 {
                            type boolean;
                            description "Set bit 1 in charging characteristics information element (IE) for home UE";
                        }

                        leaf bit2 {
                            type boolean;
                            description "Set bit 2 in charging characteristics information element (IE) for home UE";
                        }

                        leaf bit3 {
                            type boolean;
                            description "Set bit 3 in charging characteristics information element (IE) for home UE";
                        }

                        leaf bit4 {
                            type boolean;
                            description "Set bit 4 in charging characteristics information element (IE) for home UE";
                        }

                        leaf bit5 {
                            type boolean;
                            description "Set bit 5 in charging characteristics information element (IE) for home UE";
                        }

                        leaf bit6 {
                            type boolean;
                            description "Set bit 6 in charging characteristics information element (IE) for home UE";
                        }

                        leaf bit7 {
                            type boolean;
                            description "Set bit 7 in charging characteristics information element (IE) for home UE";
                        }

                        leaf bit8 {
                            type boolean;
                            description "Set bit 8 in charging characteristics information element (IE) for home UE";
                        }

                        leaf bit9 {
                            type boolean;
                            description "Set bit 9 in charging characteristics information element (IE) for home UE";
                        }

                        leaf bit10 {
                            type boolean;
                            description "Set bit 10 in charging characteristics information element (IE) for home UE";
                        }

                        leaf bit11 {
                            type boolean;
                            description "Set bit 11 in charging characteristics information element (IE) for home UE";
                        }

                        leaf bit12 {
                            type boolean;
                            description "Set bit 12 in charging characteristics information element (IE) for home UE";
                        }

                        leaf bit13 {
                            type boolean;
                            description "Set bit 13 in charging characteristics information element (IE) for home UE";
                        }

                        leaf bit14 {
                            type boolean;
                            description "Set bit 14 in charging characteristics information element (IE) for home UE";
                        }

                        leaf bit15 {
                            type boolean;
                            description "Set bit 15 in charging characteristics information element (IE) for home UE";
                        }

                    } // container charging-characteristics

                } // list pdp-context

                list pdn-session {
                    key "imsi apn";
                    description "Enter the pdn-session list instance";

                    leaf imsi {
                        type types-cellular:imsi;
                        description "International Mobile Subscriber Identity";
                    }

                    leaf apn {
                        type types-cellular:apn;
                        description "Access point name";
                    }

                    leaf interface-type {
                        type types-wlangw:mobile-gateway-connection;
                        description "Interface type";
                    }

                    container pgw {
                        description "Enter the pgw context";

                        leaf control-address {
                            type types-sros:ip-address;
                            description "Control IP address";
                        }

                        leaf control-teid {
                            type uint32;
                            description "Control Transport Endpoint Identifier (TEID)";
                        }

                    } // container pgw

                    container local {
                        description "Enter the local context";

                        leaf router {
                            type types-sros:router-instance;
                            description "Router";
                        }

                        leaf control-address {
                            type types-sros:ip-address;
                            description "Control IP address";
                        }

                        leaf control-teid {
                            type uint32;
                            description "Control Transport Endpoint Identifier (TEID)";
                        }

                    } // container local

                    container qos {
                        description "Enter the qos context";

                        leaf uplink-ambr {
                            type uint32;
                            units "kilobps";
                            description "Uplink Aggregate Maximum Bit Rate";
                        }

                        leaf downlink-ambr {
                            type uint32;
                            units "kilobps";
                            description "Downlink Aggregate Maximum Bit Rate";
                        }

                    } // container qos

                    container charging-characteristics {
                        description "Enter the charging-characteristics context";

                        leaf roaming {
                            type boolean;
                        }

                        leaf bit0 {
                            type boolean;
                            description "Set bit 0 in charging characteristics information element (IE) for home UE";
                        }

                        leaf bit1 {
                            type boolean;
                            description "Set bit 1 in charging characteristics information element (IE) for home UE";
                        }

                        leaf bit2 {
                            type boolean;
                            description "Set bit 2 in charging characteristics information element (IE) for home UE";
                        }

                        leaf bit3 {
                            type boolean;
                            description "Set bit 3 in charging characteristics information element (IE) for home UE";
                        }

                        leaf bit4 {
                            type boolean;
                            description "Set bit 4 in charging characteristics information element (IE) for home UE";
                        }

                        leaf bit5 {
                            type boolean;
                            description "Set bit 5 in charging characteristics information element (IE) for home UE";
                        }

                        leaf bit6 {
                            type boolean;
                            description "Set bit 6 in charging characteristics information element (IE) for home UE";
                        }

                        leaf bit7 {
                            type boolean;
                            description "Set bit 7 in charging characteristics information element (IE) for home UE";
                        }

                        leaf bit8 {
                            type boolean;
                            description "Set bit 8 in charging characteristics information element (IE) for home UE";
                        }

                        leaf bit9 {
                            type boolean;
                            description "Set bit 9 in charging characteristics information element (IE) for home UE";
                        }

                        leaf bit10 {
                            type boolean;
                            description "Set bit 10 in charging characteristics information element (IE) for home UE";
                        }

                        leaf bit11 {
                            type boolean;
                            description "Set bit 11 in charging characteristics information element (IE) for home UE";
                        }

                        leaf bit12 {
                            type boolean;
                            description "Set bit 12 in charging characteristics information element (IE) for home UE";
                        }

                        leaf bit13 {
                            type boolean;
                            description "Set bit 13 in charging characteristics information element (IE) for home UE";
                        }

                        leaf bit14 {
                            type boolean;
                            description "Set bit 14 in charging characteristics information element (IE) for home UE";
                        }

                        leaf bit15 {
                            type boolean;
                            description "Set bit 15 in charging characteristics information element (IE) for home UE";
                        }

                    } // container charging-characteristics

                    container user-location-information {
                        description "Enter the user-location-information context";

                        container cgi {
                            description "Enter the cgi context";

                            leaf mcc {
                                type string;
                                description "Mobile Country Code";
                            }

                            leaf mnc {
                                type string;
                                description "Mobile Network Code";
                            }

                            leaf lac {
                                type string;
                                description "Location Area Code";
                            }

                            leaf ci {
                                type string;
                                description "Cell Identity";
                            }

                        } // container cgi

                        container sai {
                            description "Enter the sai context";

                            leaf mcc {
                                type string;
                                description "Mobile Country Code";
                            }

                            leaf mnc {
                                type string;
                                description "Mobile Network Code";
                            }

                            leaf lac {
                                type string;
                                description "Location Area Code";
                            }

                            leaf sac {
                                type string;
                                description "Service Area Code";
                            }

                        } // container sai

                        container rai {
                            description "Enter the rai context";

                            leaf mcc {
                                type string;
                                description "Mobile Country Code";
                            }

                            leaf mnc {
                                type string;
                                description "Mobile Network Code";
                            }

                            leaf lac {
                                type string;
                                description "Location Area Code";
                            }

                            leaf rac {
                                type string;
                                description "Routing Area Code";
                            }

                        } // container rai

                        container tai {
                            description "Enter the tai context";

                            leaf mcc {
                                type string;
                                description "Mobile Country Code";
                            }

                            leaf mnc {
                                type string;
                                description "Mobile Network Code";
                            }

                            leaf tac {
                                type string;
                                description "Tracking Area Code";
                            }

                        } // container tai

                        container ecgi {
                            description "Enter the ecgi context";

                            leaf mcc {
                                type string;
                                description "Mobile Country Code";
                            }

                            leaf mnc {
                                type string;
                                description "Mobile Network Code";
                            }

                            leaf eci {
                                type string;
                                description "E-UTRAN Cell Identifier";
                            }

                        } // container ecgi

                    } // container user-location-information

                    list bearer {
                        key "bearer-id";
                        description "Enter the bearer list instance";

                        leaf bearer-id {
                            type uint32;
                            description "Identifier";
                        }

                        container pgw {
                            description "Enter the pgw context";

                            leaf data-address {
                                type types-sros:ip-address;
                                description "IP address";
                            }

                            leaf data-teid {
                                type uint32;
                                description "Data Transport Endpoint Identifier (TEID)";
                            }

                        } // container pgw

                        container local {
                            description "Enter the local context";

                            leaf data-teid {
                                type uint32;
                                description "Data Transport Endpoint Identifier (TEID)";
                            }

                        } // container local

                        container qos {
                            description "Enter the qos context";

                            leaf uplink-gbr {
                                type uint32;
                                units "kilobps";
                                description "Uplink Guaranteed Bit Rate";
                            }

                            leaf uplink-mbr {
                                type uint32;
                                units "kilobps";
                                description "Uplink Maximum Bit Rate";
                            }

                            leaf downlink-gbr {
                                type uint32;
                                units "kilobps";
                                description "Downlinklink Guaranteed Bit Rate";
                            }

                            leaf downlink-mbr {
                                type uint32;
                                units "kilobps";
                                description "Downlink Maximum Bit Rate";
                            }

                            leaf qci {
                                type uint32;
                                description "QoS Class ID";
                            }

                            leaf arp {
                                type uint32;
                                description "Allocation/Retention Priority";
                            }

                        } // container qos

                    } // list bearer

                } // list pdn-session

            } // container uplink

            container s11 {
                description "Enter the s11 context";

                list pdn-session {
                    key "imsi apn";
                    description "Enter the pdn-session list instance";

                    leaf imsi {
                        type types-cellular:imsi;
                        description "International Mobile Subscriber Identity";
                    }

                    leaf apn {
                        type types-cellular:apn;
                        description "Access point name";
                    }

                    container mme {
                        description "Enter the mme context";

                        leaf control-address {
                            type types-sros:ip-address;
                            description "Control IP address";
                        }

                        leaf control-teid {
                            type uint32;
                            description "Control Transport Endpoint Identifier (TEID)";
                        }

                    } // container mme

                    container local {
                        description "Enter the local context";

                        leaf router {
                            type types-sros:router-instance;
                            description "Router";
                        }

                        leaf control-address {
                            type types-sros:ip-address;
                            description "Control IP address";
                        }

                        leaf control-teid {
                            type uint32;
                            description "Control Transport Endpoint Identifier (TEID)";
                        }

                    } // container local

                    container qos {
                        description "Enter the qos context";

                        leaf uplink-ambr {
                            type uint32;
                            units "kilobps";
                            description "Uplink Aggregate Maximum Bit Rate";
                        }

                        leaf downlink-ambr {
                            type uint32;
                            units "kilobps";
                            description "Downlink Aggregate Maximum Bit Rate";
                        }

                    } // container qos

                    container charging-characteristics {
                        description "Enter the charging-characteristics context";

                        leaf bit0 {
                            type boolean;
                            description "Set bit 0 in charging characteristics information element (IE) for home UE";
                        }

                        leaf bit1 {
                            type boolean;
                            description "Set bit 1 in charging characteristics information element (IE) for home UE";
                        }

                        leaf bit2 {
                            type boolean;
                            description "Set bit 2 in charging characteristics information element (IE) for home UE";
                        }

                        leaf bit3 {
                            type boolean;
                            description "Set bit 3 in charging characteristics information element (IE) for home UE";
                        }

                        leaf bit4 {
                            type boolean;
                            description "Set bit 4 in charging characteristics information element (IE) for home UE";
                        }

                        leaf bit5 {
                            type boolean;
                            description "Set bit 5 in charging characteristics information element (IE) for home UE";
                        }

                        leaf bit6 {
                            type boolean;
                            description "Set bit 6 in charging characteristics information element (IE) for home UE";
                        }

                        leaf bit7 {
                            type boolean;
                            description "Set bit 7 in charging characteristics information element (IE) for home UE";
                        }

                        leaf bit8 {
                            type boolean;
                            description "Set bit 8 in charging characteristics information element (IE) for home UE";
                        }

                        leaf bit9 {
                            type boolean;
                            description "Set bit 9 in charging characteristics information element (IE) for home UE";
                        }

                        leaf bit10 {
                            type boolean;
                            description "Set bit 10 in charging characteristics information element (IE) for home UE";
                        }

                        leaf bit11 {
                            type boolean;
                            description "Set bit 11 in charging characteristics information element (IE) for home UE";
                        }

                        leaf bit12 {
                            type boolean;
                            description "Set bit 12 in charging characteristics information element (IE) for home UE";
                        }

                        leaf bit13 {
                            type boolean;
                            description "Set bit 13 in charging characteristics information element (IE) for home UE";
                        }

                        leaf bit14 {
                            type boolean;
                            description "Set bit 14 in charging characteristics information element (IE) for home UE";
                        }

                        leaf bit15 {
                            type boolean;
                            description "Set bit 15 in charging characteristics information element (IE) for home UE";
                        }

                    } // container charging-characteristics

                    container user-location-information {
                        description "Enter the user-location-information context";

                        container cgi {
                            description "Enter the cgi context";

                            leaf mcc {
                                type string;
                                description "Mobile Country Code";
                            }

                            leaf mnc {
                                type string;
                                description "Mobile Network Code";
                            }

                            leaf lac {
                                type string;
                                description "Location Area Code";
                            }

                            leaf ci {
                                type string;
                                description "Cell Identity";
                            }

                        } // container cgi

                        container sai {
                            description "Enter the sai context";

                            leaf mcc {
                                type string;
                                description "Mobile Country Code";
                            }

                            leaf mnc {
                                type string;
                                description "Mobile Network Code";
                            }

                            leaf lac {
                                type string;
                                description "Location Area Code";
                            }

                            leaf sac {
                                type string;
                                description "Service Area Code";
                            }

                        } // container sai

                        container rai {
                            description "Enter the rai context";

                            leaf mcc {
                                type string;
                                description "Mobile Country Code";
                            }

                            leaf mnc {
                                type string;
                                description "Mobile Network Code";
                            }

                            leaf lac {
                                type string;
                                description "Location Area Code";
                            }

                            leaf rac {
                                type string;
                                description "Routing Area Code";
                            }

                        } // container rai

                        container tai {
                            description "Enter the tai context";

                            leaf mcc {
                                type string;
                                description "Mobile Country Code";
                            }

                            leaf mnc {
                                type string;
                                description "Mobile Network Code";
                            }

                            leaf tac {
                                type string;
                                description "Tracking Area Code";
                            }

                        } // container tai

                        container ecgi {
                            description "Enter the ecgi context";

                            leaf mcc {
                                type string;
                                description "Mobile Country Code";
                            }

                            leaf mnc {
                                type string;
                                description "Mobile Network Code";
                            }

                            leaf eci {
                                type string;
                                description "E-UTRAN Cell Identifier";
                            }

                        } // container ecgi

                    } // container user-location-information

                    list bearer {
                        key "bearer-id";
                        description "Enter the bearer list instance";

                        leaf bearer-id {
                            type uint32;
                            description "Identifier";
                        }

                        container e-node-b {
                            description "Enter the e-node-b context";

                            leaf data-address {
                                type types-sros:ip-address;
                                description "IP address";
                            }

                            leaf data-teid {
                                type uint32;
                                description "Data Transport Endpoint Identifier (TEID)";
                            }

                        } // container e-node-b

                        container local {
                            description "Enter the local context";

                            leaf data-teid {
                                type uint32;
                                description "Data Transport Endpoint Identifier (TEID)";
                            }

                        } // container local

                        container qos {
                            description "Enter the qos context";

                            leaf uplink-gbr {
                                type uint32;
                                units "kilobps";
                                description "Uplink Guaranteed Bit Rate";
                            }

                            leaf uplink-mbr {
                                type uint32;
                                units "kilobps";
                                description "Uplink Maximum Bit Rate";
                            }

                            leaf downlink-gbr {
                                type uint32;
                                units "kilobps";
                                description "Downlinklink Guaranteed Bit Rate";
                            }

                            leaf downlink-mbr {
                                type uint32;
                                units "kilobps";
                                description "Downlink Maximum Bit Rate";
                            }

                            leaf qci {
                                type uint32;
                                description "QoS Class ID";
                            }

                            leaf arp {
                                type uint32;
                                description "Allocation/Retention Priority";
                            }

                        } // container qos

                    } // list bearer

                } // list pdn-session

            } // container s11

        } // container gtp

    } // grouping state-submgt-gtp

}
