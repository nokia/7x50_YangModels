submodule nokia-conf-oam-pm {

    yang-version "1.1";

    belongs-to nokia-conf { prefix "conf"; }

    import ietf-yang-types                { prefix "yang"; }
    import nokia-sros-yang-extensions     { prefix "sros-ext"; }
    import nokia-types-eth-cfm            { prefix "types-eth-cfm"; }
    import nokia-types-oam                { prefix "types-oam"; }
    import nokia-types-qos                { prefix "types-qos"; }
    import nokia-types-sros               { prefix "types-sros"; }

    include nokia-conf-groups;
    include nokia-conf-log;


    sros-ext:sros-major-release "rel21";

    organization "Nokia";

    contact
        "Nokia SR OS Support
         Web: <http://www.nokia.com>";

    description
        "Nokia YANG Data model to configure OAM-PM configuration on SR OS based routers.

         Copyright 2016 Nokia. All rights reserved. Reproduction of this document
         is authorized on the condition that the foregoing copyright notice is included.

         This nokia-conf-oam-pm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-03-15";

    grouping conf-oam-pm {
        container oam-pm {
            description "Enter the oam-pm context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list bin-group {
                key "bin-group-id";
                description "Enter the bin-group list instance";

                leaf bin-group-id {
                    type uint32 {
                        range "1..255";
                    }
                    description "Bin group identifier";
                }

                leaf admin-state {
                    type types-sros:admin-state;
                    sros-ext:auto-restart-to-modify;
                    description "Administrative state of the bin group";
                }

                leaf description {
                    type types-sros:description;
                    description "Text description";
                }

                leaf-list apply-groups {
                    type leafref {
                        path "../../../groups/group/name";
                    }
                    max-elements 8;
                    ordered-by user;
                    sros-ext:auto-restart-to-modify;
                    description "Apply a configuration group at this level";
                }

                leaf-list apply-groups-exclude {
                    type leafref {
                        path "../../../groups/group/name";
                    }
                    max-elements 8;
                    ordered-by user;
                    sros-ext:auto-restart-to-modify;
                    description "Exclude a configuration group at this level";
                }

                list bin-type {
                    key "bin-metric";
                    sros-ext:auto-restart-to-modify;
                    description "Enter the bin-type list instance";

                    leaf bin-metric {
                        type enumeration {
                            enum "fd"                           { value 1; }
                            enum "fdr"                          { value 2; }
                            enum "ifdv"                         { value 3; }
                        }
                        description "Frame Delay, Frame Delay Range, Inter-Frame Delay Variation";
                    }

                    leaf-list apply-groups {
                        type leafref {
                            path "../../../../groups/group/name";
                        }
                        max-elements 8;
                        ordered-by user;
                        sros-ext:auto-restart-to-modify;
                        description "Apply a configuration group at this level";
                    }

                    leaf-list apply-groups-exclude {
                        type leafref {
                            path "../../../../groups/group/name";
                        }
                        max-elements 8;
                        ordered-by user;
                        sros-ext:auto-restart-to-modify;
                        description "Exclude a configuration group at this level";
                    }

                    list delay-event {
                        key "direction";
                        sros-ext:auto-restart-to-modify;
                        description "Enter the delay-event list instance";

                        leaf direction {
                            type types-oam:direction;
                            description "Traffic flow direction of the OAM-PM test or metric";
                        }

                        leaf lowest-bin {
                            type uint32 {
                                range "0..9";
                            }
                            sros-ext:auto-restart-to-modify;
                            mandatory true;
                            description "The lowest OAM-PM delay bin to be used when applying a configured Raise or Clear delay threshold";
                        }

                        leaf raise-threshold {
                            type int32 {
                                range "1..864000";
                            }
                            sros-ext:auto-restart-to-modify;
                            mandatory true;
                            description "The OAM-PM raise threshold for excessive delay";
                        }

                        leaf clear-threshold {
                            type int32 {
                                range "0..863999";
                            }
                            sros-ext:auto-restart-to-modify;
                            description "The OAM-PM clear threshold for excessive delay";
                        }

                        leaf exclude-lowest-bin {
                            type int32 {
                                range "1..9";
                            }
                            sros-ext:auto-restart-to-modify;
                            description "Lowest bin to be excluded from the TCA count";
                        }

                        leaf-list apply-groups {
                            type leafref {
                                path "../../../../../groups/group/name";
                            }
                            max-elements 8;
                            ordered-by user;
                            sros-ext:auto-restart-to-modify;
                            description "Apply a configuration group at this level";
                        }

                        leaf-list apply-groups-exclude {
                            type leafref {
                                path "../../../../../groups/group/name";
                            }
                            max-elements 8;
                            ordered-by user;
                            sros-ext:auto-restart-to-modify;
                            description "Exclude a configuration group at this level";
                        }

                    } // list delay-event

                    list exclude-from-avg {
                        key "direction";
                        sros-ext:auto-restart-to-modify;
                        description "Enter the exclude-from-avg list instance";

                        leaf direction {
                            type types-oam:direction;
                            description "Traffic flow direction of the OAM-PM test or metric";
                        }

                        leaf bins {
                            type string {
                                length "1..39";
                                pattern "(all|(([0-9]|([0-9]-[0-9]))(,([0-9]|([0-9]-[0-9])))*))";
                            }
                            sros-ext:auto-restart-to-modify;
                            mandatory true;
                            description "Bin numbers to be excluded from the average calculation";
                        }

                        leaf-list apply-groups {
                            type leafref {
                                path "../../../../../groups/group/name";
                            }
                            max-elements 8;
                            ordered-by user;
                            sros-ext:auto-restart-to-modify;
                            description "Apply a configuration group at this level";
                        }

                        leaf-list apply-groups-exclude {
                            type leafref {
                                path "../../../../../groups/group/name";
                            }
                            max-elements 8;
                            ordered-by user;
                            sros-ext:auto-restart-to-modify;
                            description "Exclude a configuration group at this level";
                        }

                    } // list exclude-from-avg

                    list bin {
                        key "bin-number";
                        sros-ext:auto-restart-to-modify;
                        description "Enter the bin list instance";

                        leaf bin-number {
                            type uint32 {
                                range "0..9";
                            }
                            description "The number of the bin";
                        }

                        leaf lower-bound {
                            type int64 {
                                range "0|1..4294967295";
                            }
                            units "microseconds";
                            sros-ext:auto-restart-to-modify;
                            description "The lower bound for the bin";
                        }

                        leaf-list apply-groups {
                            type leafref {
                                path "../../../../../groups/group/name";
                            }
                            max-elements 8;
                            ordered-by user;
                            sros-ext:auto-restart-to-modify;
                            description "Apply a configuration group at this level";
                        }

                        leaf-list apply-groups-exclude {
                            type leafref {
                                path "../../../../../groups/group/name";
                            }
                            max-elements 8;
                            ordered-by user;
                            sros-ext:auto-restart-to-modify;
                            description "Exclude a configuration group at this level";
                        }

                    } // list bin

                } // list bin-type

            } // list bin-group

            list session {
                key "session-name";
                description "Enter the session list instance";

                leaf session-name {
                    type types-sros:named-item;
                    description "OAM-PM session name";
                }

                leaf session-type {
                    type enumeration {
                        enum "proactive"                    { value 1; }
                        enum "on-demand"                    { value 2; }
                    }
                    sros-ext:immutable;
                    default "proactive";
                    description "The type of the specified session";
                }

                leaf bin-group {
                    type leafref {
                        path "../../bin-group/bin-group-id";
                    }
                    description "The bin group for the session";
                }

                leaf description {
                    type types-sros:description;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                choice test-family-choice {
                    mandatory true;
                    case ethernet-case {

                        container ethernet {
                            presence "Enable the ethernet context";
                            description "Enable the ethernet context";

                            leaf dest-mac {
                                type types-sros:mac-unicast-address;
                                description "The destination MAC address for the session";
                            }

                            leaf remote-mep {
                                type uint32 {
                                    range "1..8191";
                                }
                                description "The remote Maintenance association End Point (MEP) for the session";
                            }

                            leaf priority {
                                type uint32 {
                                    range "0..7";
                                }
                                default "0";
                                description "The priority and forwarding class for the session";
                            }

                            container source {
                                presence "Enable the source context";
                                description "Enable the source context";

                                leaf mep {
                                    type uint32 {
                                        range "1..8191";
                                    }
                                    mandatory true;
                                    description "The source Ethernet Maintenance association End Point (MEP) identifier";
                                }

                                leaf md-admin-name {
                                    type types-eth-cfm:admin-name;
                                    mandatory true;
                                    description "The source Ethernet Maintenance Domain (MD) name";
                                }

                                leaf ma-admin-name {
                                    type types-eth-cfm:admin-name;
                                    mandatory true;
                                    description "The source Ethernet Maintenance Association (MA) name";
                                }

                            } // container source

                            container dmm {
                                presence "Enable the dmm context";
                                description "Enable the dmm context";

                                leaf admin-state {
                                    type types-sros:admin-state;
                                    default "disable";
                                    description "Administrative state of the test";
                                }

                                leaf test-id {
                                    type uint32 {
                                        range "0..2147483647";
                                    }
                                    mandatory true;
                                    description "The test identifier";
                                }

                                leaf test-duration {
                                    type uint32 {
                                        range "1..86400";
                                    }
                                    units "seconds";
                                    description "The duration of an on-demand test";
                                }

                                leaf interval {
                                    type uint32 {
                                        range "100|1000|10000";
                                    }
                                    units "milliseconds";
                                    description "The elapsed time between transmission PDUs for the specified session's test";
                                }

                                leaf data-tlv-size {
                                    type uint32 {
                                        range "0|3..2000";
                                    }
                                    units "octets";
                                    default "0";
                                    description "The size of the pad TLV in the frames sent for the test";
                                }

                                leaf delay-template {
                                    type types-sros:named-item-64;
                                    description "Reference to a streaming delay template for the test";
                                }

                                leaf-list apply-groups {
                                    type leafref {
                                        path "../../../../../groups/group/name";
                                    }
                                    max-elements 8;
                                    ordered-by user;
                                    description "Apply a configuration group at this level";
                                }

                                leaf-list apply-groups-exclude {
                                    type leafref {
                                        path "../../../../../groups/group/name";
                                    }
                                    max-elements 8;
                                    ordered-by user;
                                    description "Exclude a configuration group at this level";
                                }

                            } // container dmm

                            container lmm {
                                presence "Enable the lmm context";
                                description "Enable the lmm context";

                                leaf admin-state {
                                    type types-sros:admin-state;
                                    default "disable";
                                    description "Administrative state of the test";
                                }

                                leaf test-id {
                                    type uint32 {
                                        range "0..2147483647";
                                    }
                                    mandatory true;
                                    description "The test identifier";
                                }

                                leaf test-duration {
                                    type uint32 {
                                        range "1..86400";
                                    }
                                    units "seconds";
                                    description "The duration of an on-demand test";
                                }

                                leaf interval {
                                    type uint32 {
                                        range "100|1000|10000";
                                    }
                                    units "milliseconds";
                                    description "The elapsed time between transmission PDUs for the specified session's test";
                                }

                                leaf fc-collection {
                                    type boolean;
                                    default "false";
                                    description "Enable collection of per-forwarding class counters";
                                }

                                leaf-list apply-groups {
                                    type leafref {
                                        path "../../../../../groups/group/name";
                                    }
                                    max-elements 8;
                                    ordered-by user;
                                    description "Apply a configuration group at this level";
                                }

                                leaf-list apply-groups-exclude {
                                    type leafref {
                                        path "../../../../../groups/group/name";
                                    }
                                    max-elements 8;
                                    ordered-by user;
                                    description "Exclude a configuration group at this level";
                                }

                                container availability {
                                    description "Enter the availability context";

                                    leaf admin-state {
                                        type types-sros:admin-state;
                                        default "disable";
                                        description "Administrative state of availability statistics";
                                    }

                                    leaf flr-threshold {
                                        type types-sros:percent;
                                        default "50";
                                        description "The Frame Loss Ratio threshold for the test";
                                    }

                                    leaf hli-force-count {
                                        type boolean;
                                        default "false";
                                        description "Increment HLI/CHLI counters regardless of availability";
                                    }

                                    container timing {
                                        description "Enter the timing context";

                                        leaf frames-per-delta-t {
                                            type uint32 {
                                                range "1..50";
                                            }
                                            description "The number of frames to send in one MEF-35 'delta_t' also known as 'Small Time Interval'";
                                        }

                                        leaf consec-delta-t {
                                            type uint32 {
                                                range "2..10";
                                            }
                                            default "10";
                                            description "The number of consecutive MEF-35 'delta_t's which constitute a MEF-35 'Availability Window'";
                                        }

                                        leaf chli-threshold {
                                            type uint32 {
                                                range "1..9";
                                            }
                                            default "5";
                                            description "The MEF-35 Consecutive High Loss Interval (CHLI) threshold";
                                        }

                                    } // container timing

                                } // container availability

                                container loss-events {
                                    description "Enter the loss-events context";

                                    list avg-flr-event {
                                        key "direction";
                                        description "Enter the avg-flr-event list instance";

                                        leaf direction {
                                            type enumeration {
                                                enum "forward"                      { value 1; }
                                                enum "backward"                     { value 2; }
                                            }
                                            description "Traffic flow direction";
                                        }

                                        leaf raise-threshold {
                                            type decimal64 {
                                                range "0.000..100.000";
                                                fraction-digits 3;
                                            }
                                            units "percent";
                                            mandatory true;
                                            description "The raise threshold for the average Frame Loss Ratio (FLR)";
                                        }

                                        leaf clear-threshold {
                                            type decimal64 {
                                                range "0.000..99.999";
                                                fraction-digits 3;
                                            }
                                            units "percent";
                                            description "The clear threshold for the average Frame Loss Ratio (FLR)";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list avg-flr-event

                                    list chli-event {
                                        key "direction";
                                        description "Enter the chli-event list instance";

                                        leaf direction {
                                            type enumeration {
                                                enum "forward"                      { value 1; }
                                                enum "backward"                     { value 2; }
                                                enum "aggregate"                    { value 3; }
                                            }
                                            description "Traffic flow direction";
                                        }

                                        leaf raise-threshold {
                                            type int32 {
                                                range "1..864000";
                                            }
                                            mandatory true;
                                            description "Raise threshold";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list chli-event

                                    list hli-event {
                                        key "direction";
                                        description "Enter the hli-event list instance";

                                        leaf direction {
                                            type enumeration {
                                                enum "forward"                      { value 1; }
                                                enum "backward"                     { value 2; }
                                                enum "aggregate"                    { value 3; }
                                            }
                                            description "Traffic flow direction";
                                        }

                                        leaf raise-threshold {
                                            type int32 {
                                                range "1..864000";
                                            }
                                            mandatory true;
                                            description "Raise threshold";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list hli-event

                                    list unavailability-event {
                                        key "direction";
                                        description "Enter the unavailability-event list instance";

                                        leaf direction {
                                            type enumeration {
                                                enum "forward"                      { value 1; }
                                                enum "backward"                     { value 2; }
                                                enum "aggregate"                    { value 3; }
                                            }
                                            description "Traffic flow direction";
                                        }

                                        leaf raise-threshold {
                                            type int32 {
                                                range "1..864000";
                                            }
                                            mandatory true;
                                            description "Raise threshold";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list unavailability-event

                                    list undet-availability-event {
                                        key "direction";
                                        description "Enter the undet-availability-event list instance";

                                        leaf direction {
                                            type enumeration {
                                                enum "forward"                      { value 1; }
                                                enum "backward"                     { value 2; }
                                                enum "aggregate"                    { value 3; }
                                            }
                                            description "Traffic flow direction";
                                        }

                                        leaf raise-threshold {
                                            type int32 {
                                                range "1..864000";
                                            }
                                            mandatory true;
                                            description "Raise threshold";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list undet-availability-event

                                    list undet-unavailability-event {
                                        key "direction";
                                        description "Enter the undet-unavailability-event list instance";

                                        leaf direction {
                                            type enumeration {
                                                enum "forward"                      { value 1; }
                                                enum "backward"                     { value 2; }
                                                enum "aggregate"                    { value 3; }
                                            }
                                            description "Traffic flow direction";
                                        }

                                        leaf raise-threshold {
                                            type int32 {
                                                range "1..864000";
                                            }
                                            mandatory true;
                                            description "Raise threshold";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list undet-unavailability-event

                                } // container loss-events

                            } // container lmm

                            container slm {
                                presence "Enable the slm context";
                                description "Enable the slm context";

                                leaf admin-state {
                                    type types-sros:admin-state;
                                    default "disable";
                                    description "Administrative state of the test";
                                }

                                leaf test-id {
                                    type uint32 {
                                        range "0..2147483647";
                                    }
                                    mandatory true;
                                    description "The test identifier";
                                }

                                leaf test-duration {
                                    type uint32 {
                                        range "1..86400";
                                    }
                                    units "seconds";
                                    description "The duration of an on-demand test";
                                }

                                leaf interval {
                                    type uint32 {
                                        range "100|1000";
                                    }
                                    units "milliseconds";
                                    description "The elapsed time between transmission PDUs for the specified session's test";
                                }

                                leaf data-tlv-size {
                                    type uint32 {
                                        range "0|3..2000";
                                    }
                                    units "octets";
                                    default "0";
                                    description "The size of the pad TLV in the frames sent for the test";
                                }

                                leaf flr-threshold {
                                    type types-sros:percent;
                                    default "50";
                                    description "The Frame Loss Ratio threshold for the test";
                                }

                                leaf hli-force-count {
                                    type boolean;
                                    default "false";
                                    description "Increment HLI/CHLI counters regardless of availability";
                                }

                                leaf-list apply-groups {
                                    type leafref {
                                        path "../../../../../groups/group/name";
                                    }
                                    max-elements 8;
                                    ordered-by user;
                                    description "Apply a configuration group at this level";
                                }

                                leaf-list apply-groups-exclude {
                                    type leafref {
                                        path "../../../../../groups/group/name";
                                    }
                                    max-elements 8;
                                    ordered-by user;
                                    description "Exclude a configuration group at this level";
                                }

                                container timing {
                                    description "Enter the timing context";

                                    leaf frames-per-delta-t {
                                        type uint32 {
                                            range "1..50";
                                        }
                                        description "The number of frames to send in one MEF-35 'delta_t' also known as 'Small Time Interval'";
                                    }

                                    leaf consec-delta-t {
                                        type uint32 {
                                            range "2..10";
                                        }
                                        default "10";
                                        description "The number of consecutive MEF-35 'delta_t's which constitute a MEF-35 'Availability Window'";
                                    }

                                    leaf chli-threshold {
                                        type uint32 {
                                            range "1..9";
                                        }
                                        default "5";
                                        description "The MEF-35 Consecutive High Loss Interval (CHLI) threshold";
                                    }

                                } // container timing

                                container loss-events {
                                    description "Enter the loss-events context";

                                    list avg-flr-event {
                                        key "direction";
                                        description "Enter the avg-flr-event list instance";

                                        leaf direction {
                                            type enumeration {
                                                enum "forward"                      { value 1; }
                                                enum "backward"                     { value 2; }
                                            }
                                            description "Traffic flow direction";
                                        }

                                        leaf raise-threshold {
                                            type decimal64 {
                                                range "0.000..100.000";
                                                fraction-digits 3;
                                            }
                                            units "percent";
                                            mandatory true;
                                            description "The raise threshold for the average Frame Loss Ratio (FLR)";
                                        }

                                        leaf clear-threshold {
                                            type decimal64 {
                                                range "0.000..99.999";
                                                fraction-digits 3;
                                            }
                                            units "percent";
                                            description "The clear threshold for the average Frame Loss Ratio (FLR)";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list avg-flr-event

                                    list chli-event {
                                        key "direction";
                                        description "Enter the chli-event list instance";

                                        leaf direction {
                                            type enumeration {
                                                enum "forward"                      { value 1; }
                                                enum "backward"                     { value 2; }
                                                enum "aggregate"                    { value 3; }
                                            }
                                            description "Traffic flow direction";
                                        }

                                        leaf raise-threshold {
                                            type int32 {
                                                range "1..864000";
                                            }
                                            mandatory true;
                                            description "Raise threshold";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list chli-event

                                    list hli-event {
                                        key "direction";
                                        description "Enter the hli-event list instance";

                                        leaf direction {
                                            type enumeration {
                                                enum "forward"                      { value 1; }
                                                enum "backward"                     { value 2; }
                                                enum "aggregate"                    { value 3; }
                                            }
                                            description "Traffic flow direction";
                                        }

                                        leaf raise-threshold {
                                            type int32 {
                                                range "1..864000";
                                            }
                                            mandatory true;
                                            description "Raise threshold";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list hli-event

                                    list unavailability-event {
                                        key "direction";
                                        description "Enter the unavailability-event list instance";

                                        leaf direction {
                                            type enumeration {
                                                enum "forward"                      { value 1; }
                                                enum "backward"                     { value 2; }
                                                enum "aggregate"                    { value 3; }
                                            }
                                            description "Traffic flow direction";
                                        }

                                        leaf raise-threshold {
                                            type int32 {
                                                range "1..864000";
                                            }
                                            mandatory true;
                                            description "Raise threshold";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list unavailability-event

                                    list undet-availability-event {
                                        key "direction";
                                        description "Enter the undet-availability-event list instance";

                                        leaf direction {
                                            type enumeration {
                                                enum "forward"                      { value 1; }
                                                enum "backward"                     { value 2; }
                                                enum "aggregate"                    { value 3; }
                                            }
                                            description "Traffic flow direction";
                                        }

                                        leaf raise-threshold {
                                            type int32 {
                                                range "1..864000";
                                            }
                                            mandatory true;
                                            description "Raise threshold";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list undet-availability-event

                                    list undet-unavailability-event {
                                        key "direction";
                                        description "Enter the undet-unavailability-event list instance";

                                        leaf direction {
                                            type enumeration {
                                                enum "forward"                      { value 1; }
                                                enum "backward"                     { value 2; }
                                                enum "aggregate"                    { value 3; }
                                            }
                                            description "Traffic flow direction";
                                        }

                                        leaf raise-threshold {
                                            type int32 {
                                                range "1..864000";
                                            }
                                            mandatory true;
                                            description "Raise threshold";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list undet-unavailability-event

                                } // container loss-events

                            } // container slm

                        } // container ethernet

                    }
                    case ip-case {

                        container ip {
                            presence "Enable the ip context";
                            description "Enable the ip context";

                            leaf allow-egress-remark-dscp {
                                type boolean;
                                default "false";
                                description "Allow DSCP modification by egress QoS policy";
                            }

                            leaf destination {
                                type types-sros:ip-unicast-address;
                                description "The destination IP address for the session";
                            }

                            leaf destination-udp-port {
                                type types-sros:tcp-udp-port-non-zero;
                                description "The destination UDP port for the session";
                            }

                            leaf do-not-fragment {
                                type boolean;
                                default "false";
                                description "The IPv4 packet header Don't Fragment (DF) field for the session";
                            }

                            leaf dscp {
                                type union {
                                    type types-qos:dscp-name;
                                    type types-oam:dscp-resolve;
                                }
                                default "resolve";
                                description "DSCP value configured to the DSCP name";
                            }

                            leaf fc {
                                type types-oam:forwarding-class;
                                default "be";
                                description "The forwarding class for the session";
                            }

                            leaf pattern {
                                type types-oam:padding-pattern;
                                default "0";
                                description "The pattern used to fill the packet padding field for the session";
                            }

                            leaf profile {
                                type enumeration {
                                    enum "in"                           { value 1; }
                                    enum "out"                          { value 2; }
                                }
                                default "out";
                                description "The profile for the session";
                            }

                            leaf router-instance {
                                type string;
                                default "Base";
                                description "The router for the session";
                            }

                            leaf source {
                                type types-sros:ip-unicast-address;
                                description "The source IP address for the session";
                            }

                            leaf source-udp-port {
                                type types-sros:tcp-udp-port-non-zero {
                                    range "64374..64383";
                                }
                                description "The source UDP port for the session";
                            }

                            leaf ttl {
                                type uint32 {
                                    range "1..255";
                                }
                                default "255";
                                description "The Time-To-Live value for the session";
                            }

                            container forwarding {
                                presence "Enable the forwarding context";
                                description "Enable the forwarding context";

                                choice forwarding-choice {
                                    mandatory true;
                                    case next-hop-case {

                                        leaf next-hop {
                                            type types-sros:ip-unicast-address;
                                            description "IP-address for forwarding";
                                        }

                                    }
                                    case interface-case {

                                        leaf interface {
                                            type types-sros:interface-name;
                                            description "The name of the interface to be used";
                                        }

                                    }
                                    case bypass-routing-case {

                                        leaf bypass-routing {
                                            type empty;
                                            description "Bypass the routing table when sending test packets";
                                        }

                                    }
                                }
                            } // container forwarding

                            container twamp-light {
                                presence "Enable the twamp-light context";
                                description "Enable the twamp-light context";

                                leaf admin-state {
                                    type types-sros:admin-state;
                                    default "disable";
                                    description "Administrative state of the test";
                                }

                                leaf test-id {
                                    type uint32 {
                                        range "0..2147483647";
                                    }
                                    mandatory true;
                                    description "The test identifier";
                                }

                                leaf test-duration {
                                    type uint32 {
                                        range "1..86400";
                                    }
                                    units "seconds";
                                    description "The duration of an on-demand test";
                                }

                                leaf interval {
                                    type uint32 {
                                        range "100|1000|10000";
                                    }
                                    units "milliseconds";
                                    description "The elapsed time between transmission PDUs for the specified session's test";
                                }

                                leaf pad-size {
                                    type uint32 {
                                        range "0..2000";
                                    }
                                    units "octets";
                                    default "0";
                                    description "The amount of padding in each packet sent for the TWAMP-Light test";
                                }

                                leaf record-stats {
                                    type enumeration {
                                        enum "delay"                        { value 1; }
                                        enum "loss"                         { value 2; }
                                        enum "delay-and-loss"               { value 3; }
                                    }
                                    default "delay";
                                    description "The type of statistics recorded for the TWAMP-Light test";
                                }

                                leaf delay-template {
                                    type types-sros:named-item-64;
                                    description "Reference to a streaming delay template for the test";
                                }

                                leaf-list apply-groups {
                                    type leafref {
                                        path "../../../../../groups/group/name";
                                    }
                                    max-elements 8;
                                    ordered-by user;
                                    description "Apply a configuration group at this level";
                                }

                                leaf-list apply-groups-exclude {
                                    type leafref {
                                        path "../../../../../groups/group/name";
                                    }
                                    max-elements 8;
                                    ordered-by user;
                                    description "Exclude a configuration group at this level";
                                }

                                container loss {
                                    description "Enter the loss context";

                                    leaf flr-threshold {
                                        type types-sros:percent;
                                        default "50";
                                        description "The Frame Loss Ratio threshold for the test";
                                    }

                                    leaf hli-force-count {
                                        type boolean;
                                        default "false";
                                        description "Increment HLI/CHLI counters regardless of availability";
                                    }

                                    container timing {
                                        description "Enter the timing context";

                                        leaf frames-per-delta-t {
                                            type uint32 {
                                                range "1..50";
                                            }
                                            description "The number of frames to send in one MEF-35 'delta_t' also known as 'Small Time Interval'";
                                        }

                                        leaf consec-delta-t {
                                            type uint32 {
                                                range "2..10";
                                            }
                                            default "10";
                                            description "The number of consecutive MEF-35 'delta_t's which constitute a MEF-35 'Availability Window'";
                                        }

                                        leaf chli-threshold {
                                            type uint32 {
                                                range "1..9";
                                            }
                                            default "5";
                                            description "The MEF-35 Consecutive High Loss Interval (CHLI) threshold";
                                        }

                                    } // container timing

                                } // container loss

                                container loss-events {
                                    description "Enter the loss-events context";

                                    list avg-flr-event {
                                        key "direction";
                                        description "Enter the avg-flr-event list instance";

                                        leaf direction {
                                            type enumeration {
                                                enum "forward"                      { value 1; }
                                                enum "backward"                     { value 2; }
                                            }
                                            description "Traffic flow direction";
                                        }

                                        leaf raise-threshold {
                                            type decimal64 {
                                                range "0.000..100.000";
                                                fraction-digits 3;
                                            }
                                            units "percent";
                                            mandatory true;
                                            description "The raise threshold for the average Frame Loss Ratio (FLR)";
                                        }

                                        leaf clear-threshold {
                                            type decimal64 {
                                                range "0.000..99.999";
                                                fraction-digits 3;
                                            }
                                            units "percent";
                                            description "The clear threshold for the average Frame Loss Ratio (FLR)";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list avg-flr-event

                                    list chli-event {
                                        key "direction";
                                        description "Enter the chli-event list instance";

                                        leaf direction {
                                            type enumeration {
                                                enum "forward"                      { value 1; }
                                                enum "backward"                     { value 2; }
                                                enum "aggregate"                    { value 3; }
                                            }
                                            description "Traffic flow direction";
                                        }

                                        leaf raise-threshold {
                                            type int32 {
                                                range "1..864000";
                                            }
                                            mandatory true;
                                            description "Raise threshold";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list chli-event

                                    list hli-event {
                                        key "direction";
                                        description "Enter the hli-event list instance";

                                        leaf direction {
                                            type enumeration {
                                                enum "forward"                      { value 1; }
                                                enum "backward"                     { value 2; }
                                                enum "aggregate"                    { value 3; }
                                            }
                                            description "Traffic flow direction";
                                        }

                                        leaf raise-threshold {
                                            type int32 {
                                                range "1..864000";
                                            }
                                            mandatory true;
                                            description "Raise threshold";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list hli-event

                                    list unavailability-event {
                                        key "direction";
                                        description "Enter the unavailability-event list instance";

                                        leaf direction {
                                            type enumeration {
                                                enum "forward"                      { value 1; }
                                                enum "backward"                     { value 2; }
                                                enum "aggregate"                    { value 3; }
                                            }
                                            description "Traffic flow direction";
                                        }

                                        leaf raise-threshold {
                                            type int32 {
                                                range "1..864000";
                                            }
                                            mandatory true;
                                            description "Raise threshold";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list unavailability-event

                                    list undet-availability-event {
                                        key "direction";
                                        description "Enter the undet-availability-event list instance";

                                        leaf direction {
                                            type enumeration {
                                                enum "forward"                      { value 1; }
                                                enum "backward"                     { value 2; }
                                                enum "aggregate"                    { value 3; }
                                            }
                                            description "Traffic flow direction";
                                        }

                                        leaf raise-threshold {
                                            type int32 {
                                                range "1..864000";
                                            }
                                            mandatory true;
                                            description "Raise threshold";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list undet-availability-event

                                    list undet-unavailability-event {
                                        key "direction";
                                        description "Enter the undet-unavailability-event list instance";

                                        leaf direction {
                                            type enumeration {
                                                enum "forward"                      { value 1; }
                                                enum "backward"                     { value 2; }
                                                enum "aggregate"                    { value 3; }
                                            }
                                            description "Traffic flow direction";
                                        }

                                        leaf raise-threshold {
                                            type int32 {
                                                range "1..864000";
                                            }
                                            mandatory true;
                                            description "Raise threshold";
                                        }

                                        leaf clear-threshold {
                                            type int32 {
                                                range "0..863999";
                                            }
                                            description "Clear threshold";
                                        }

                                        leaf-list apply-groups {
                                            type leafref {
                                                path "../../../../../../../groups/group/name";
                                            }
                                            max-elements 8;
                                            ordered-by user;
                                            description "Apply a configuration group at this level";
                                        }

                                        leaf-list apply-groups-exclude {
                                            type leafref {
                                                path "../../../../../../../groups/group/name";
                                            }
                                            max-elements 8;
                                            ordered-by user;
                                            description "Exclude a configuration group at this level";
                                        }

                                    } // list undet-unavailability-event

                                } // container loss-events

                            } // container twamp-light

                        } // container ip

                    }
                    case mpls-case {

                        container mpls {
                            presence "Enable the mpls context";
                            description "Enter the mpls context";

                            leaf dscp {
                                type types-qos:dscp-name;
                                default "be";
                                description "The Differentiated Services Code Point (DSCP) for the session";
                            }

                            leaf fc {
                                type types-oam:forwarding-class;
                                default "be";
                                description "The forwarding class for the session";
                            }

                            leaf pattern {
                                type types-oam:padding-pattern;
                                default "0";
                                description "Pattern value repeated to fill padding field of packet";
                            }

                            leaf profile {
                                type enumeration {
                                    enum "in"                           { value 1; }
                                    enum "out"                          { value 2; }
                                }
                                default "out";
                                description "The Quality of Service profile for the session";
                            }

                            leaf ttl {
                                type uint32 {
                                    range "1..255";
                                }
                                default "255";
                                description "The MPLS Time-To-Live value for the session";
                            }

                            container lsp {
                                description "Enter the lsp context";

                                choice lsp-choice {
                                    case mpls-tp-static-case {

                                        container mpls-tp-static {
                                            presence "Enable the mpls-tp-static context";
                                            description "Enter the mpls-tp-static context";

                                            leaf lsp {
                                                type types-sros:named-item-64;
                                                description "The LSP to be tested";
                                            }

                                        } // container mpls-tp-static

                                    }
                                    case rsvp-case {

                                        container rsvp {
                                            presence "Enable the rsvp context";
                                            description "Enter the rsvp context";

                                            leaf lsp {
                                                type types-sros:named-item-64;
                                                description "The LSP to be tested";
                                            }

                                            leaf udp-return-object {
                                                type types-sros:ip-unicast-address;
                                                description "The destination IP address used by the far end of the test to send a response";
                                            }

                                        } // container rsvp

                                    }
                                    case rsvp-auto-case {

                                        container rsvp-auto {
                                            presence "Enable the rsvp-auto context";
                                            description "Enter the rsvp-auto context";

                                            leaf lsp-template {
                                                type types-sros:named-item;
                                                description "The LSP template used to identify the LSP to be tested";
                                            }

                                            leaf from {
                                                type types-sros:ipv4-unicast-address;
                                                description "An IPv4 address used (with the LSP template) to identify the LSP to be tested";
                                            }

                                            leaf to {
                                                type types-sros:ipv4-unicast-address;
                                                description "An IPv4 address used (with the LSP template) to identify the LSP to be tested";
                                            }

                                            leaf udp-return-object {
                                                type types-sros:ip-unicast-address;
                                                description "The destination IP address used by the far end of the test to send a response";
                                            }

                                        } // container rsvp-auto

                                    }
                                }
                            } // container lsp

                            container dm {
                                presence "Enable the dm context";
                                description "Enter the dm context";

                                leaf admin-state {
                                    type types-sros:admin-state;
                                    default "disable";
                                    description "Administrative state of the MPLS DM test";
                                }

                                leaf test-id {
                                    type uint32 {
                                        range "0..67108863";
                                    }
                                    mandatory true;
                                    description "Used to identify query and response messages belonging to the test";
                                }

                                leaf interval {
                                    type uint32 {
                                        range "1000|2000|3000|4000|5000|6000|7000|8000|9000|10000";
                                    }
                                    units "milliseconds";
                                    default "1000";
                                    description "The elapsed time between query messages sent for the test";
                                }

                                leaf pad-tlv-size {
                                    type uint32 {
                                        range "0|2..257";
                                    }
                                    units "octets";
                                    default "0";
                                    description "The size of the pad TLV in the query messages sent for the test";
                                }

                                leaf reflect-pad {
                                    type boolean;
                                    default "false";
                                    description "Whether or not to copy the pad TLV in each query to the response";
                                }

                                leaf test-duration {
                                    type uint32 {
                                        range "1..86400";
                                    }
                                    units "seconds";
                                    description "The duration of an on-demand test";
                                }

                                leaf delay-template {
                                    type types-sros:named-item-64;
                                    description "Reference to a streaming delay template for the test";
                                }

                                leaf-list apply-groups {
                                    type leafref {
                                        path "../../../../../groups/group/name";
                                    }
                                    max-elements 8;
                                    ordered-by user;
                                    description "Apply a configuration group at this level";
                                }

                                leaf-list apply-groups-exclude {
                                    type leafref {
                                        path "../../../../../groups/group/name";
                                    }
                                    max-elements 8;
                                    ordered-by user;
                                    description "Exclude a configuration group at this level";
                                }

                            } // container dm

                        } // container mpls

                    }
                }
                list measurement-interval {
                    key "duration";
                    description "Enter the measurement-interval list instance";

                    leaf duration {
                        type types-oam:measurement-interval-duration;
                        description "The duration of the measurement interval";
                    }

                    leaf accounting-policy {
                        type leafref {
                            path "../../../../log/accounting-policy/policy-id";
                        }
                        description "The accounting policy for the measurement interval";
                    }

                    leaf boundary-type {
                        type enumeration {
                            enum "clock-aligned"                { value 1; }
                            enum "test-relative"                { value 2; }
                        }
                        default "clock-aligned";
                        description "Alignment of the start of the measurement interval";
                    }

                    leaf clock-offset {
                        type uint32 {
                            range "0..86399";
                        }
                        units "seconds";
                        default "0";
                        description "The offset for a clock-aligned measurement interval (must be less than the selected duration)";
                    }

                    leaf intervals-stored {
                        type uint32 {
                            range "1..96";
                        }
                        description "The maximum number of intervals stored for the measurement interval";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container threshold-cross-alerts {
                        description "Enter the threshold-cross-alerts context";

                        leaf admin-state {
                            type types-sros:admin-state;
                            default "disable";
                            description "Administrative state of TCAs for measurement interval";
                        }

                        leaf delay-events {
                            type boolean;
                            default "false";
                            description "Enable or disable delay TCAs for the measurement interval";
                        }

                        leaf loss-events {
                            type boolean;
                            default "false";
                            description "Enable or disable loss TCAs for the measurement interval";
                        }

                    } // container threshold-cross-alerts

                } // list measurement-interval

            } // list session

            container streaming {
                description "Enter the streaming context";

                list delay-template {
                    key "delay-template-name";
                    description "Enter the delay-template list instance";

                    leaf delay-template-name {
                        type types-sros:named-item-64;
                        description "Streaming delay template name";
                    }

                    leaf admin-state {
                        type types-sros:admin-state;
                        default "disable";
                        description "Administrative state of the delay template";
                    }

                    leaf description {
                        type types-sros:description;
                        description "Text description";
                    }

                    leaf sample-window {
                        type uint32 {
                            range "10..60";
                        }
                        units "seconds";
                        default "60";
                        description "Sample window duration for the template";
                    }

                    leaf window-integrity {
                        type uint32 {
                            range "1..100";
                        }
                        units "percent";
                        default "50";
                        description "Measurements for the sample window validity";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list fd-avg {
                        key "direction";
                        description "Add a list entry for fd-avg";

                        leaf direction {
                            type types-oam:direction;
                            description "Traffic flow direction of the OAM-PM test or metric";
                        }

                    } // list fd-avg

                    list ifdv-avg {
                        key "direction";
                        description "Add a list entry for ifdv-avg";

                        leaf direction {
                            type types-oam:direction;
                            description "Traffic flow direction of the OAM-PM test or metric";
                        }

                    } // list ifdv-avg

                } // list delay-template

            } // container streaming

        } // container oam-pm

    } // grouping conf-oam-pm

}
