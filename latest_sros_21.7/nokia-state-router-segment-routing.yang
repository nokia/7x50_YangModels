submodule nokia-state-router-segment-routing {

    yang-version "1.1";

    belongs-to nokia-state { prefix "state"; }

    import nokia-sros-yang-extensions     { prefix "sros-ext"; }
    import nokia-types-sr-mpls            { prefix "types-sr-mpls"; }
    import nokia-types-sros               { prefix "types-sros"; }

    include nokia-state-router;


    sros-ext:sros-major-release "rel21";

    organization "Nokia";

    contact
        "Nokia SR OS Support
         Web: <http://www.nokia.com>";

    description
        "Nokia YANG Data model with operational state for segment routing management on SR OS based routers.

         Copyright 2016 Nokia. All rights reserved. Reproduction of this document
         is authorized on the condition that the foregoing copyright notice is included.

         This nokia-state-router-segment-routing YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-06-16";

    grouping state-router-segment-routing {
        container segment-routing {
            description "Enter the segment-routing context";

            container sr-policies {
                description "Enter the sr-policies context";

                leaf ttm-preferences {
                    type uint32;
                    description "Specifies the TTM preferences used for sr-policy tunnels.";
                }

                leaf binding-sids-allocated {
                    type uint32;
                    description "Specifies the binding-sids allocated.";
                }

                leaf static-local-policies {
                    type uint32;
                    description "Specifies the static local policies.";
                }

                leaf active-static-local-policies {
                    type uint32;
                    description "Specifies the active static local policies.";
                }

                leaf static-non-local-policies {
                    type uint32;
                    description "Specifies the static non-local policies.";
                }

                leaf bgp-policies {
                    type uint32;
                    description "Specifies the bgp policies.";
                }

                leaf active-bgp-policies {
                    type uint32;
                    description "Specifies the active bgp policies.";
                }

                list sr-path {
                    key "head-end color endpoint owner preference distinguisher";
                    description "Enter the sr-path list instance";

                    leaf head-end {
                        type types-sros:ip-address;
                        description "Head end address of the segment route path.";
                    }

                    leaf color {
                        type uint32;
                        description "Determines the set of traffic flows that would be steered by this policy.";
                    }

                    leaf endpoint {
                        type types-sros:ip-address;
                        description "Destination of the source-routed path.";
                    }

                    leaf owner {
                        type enumeration {
                            enum "none"                         { value 0; }
                            enum "bgp"                          { value 1; }
                            enum "static"                       { value 2; }
                            enum "nsp"                          { value 3; }
                        }
                        description "Owner of the segment routing policy instance.";
                    }

                    leaf preference {
                        type uint32;
                        description "Indicates the preference value of this static policy.";
                    }

                    leaf distinguisher {
                        type uint32;
                        description "Is required if the head-end of the policy is not local.";
                    }

                    leaf tunnel-id {
                        type uint32;
                        description "Specifies the tunnel-id used by the segment routing path.";
                    }

                    leaf active {
                        type boolean;
                        description "Indicates whether segment routing path is active.";
                    }

                    leaf path-age {
                        type uint32;
                        description "Specifies the age of the segment routing path.";
                    }

                    leaf re-evaluations {
                        type uint32;
                        description "Specifies the number of re-evaluations for segment routing path.";
                    }

                    leaf active-path-changes {
                        type uint32;
                        description "Specifies the number of active path changes for segment routing path.";
                    }

                    leaf re-evaluation-reason {
                        type enumeration {
                            enum "none"                         { value 0; }
                            enum "route-add"                    { value 1; }
                            enum "route-mod"                    { value 2; }
                            enum "route-del"                    { value 3; }
                            enum "tunnel-down"                  { value 4; }
                            enum "sr-failure"                   { value 5; }
                            enum "route-audit"                  { value 6; }
                            enum "admin-no-shut"                { value 7; }
                        }
                        description "Specifies the reason for the last re-evaluation of the segment routing path.";
                    }

                    leaf binding-sid {
                        type types-sros:mpls-label-or-zero;
                        description "Specifies the number of active path changes for segment routing path.";
                    }

                    leaf origin-address {
                        type types-sros:ip-address;
                        description "Address of the originating bgp router-id.";
                    }

                    leaf origin-asn {
                        type uint32;
                        description
                            "Specifies the ASN of the node/controller signalling the candidate path
                             when it has a BGP session to the headend.";
                    }

                    leaf maintenance-policy {
                        type types-sros:named-item-or-empty;
                        description "Specifes the  maintenance-policy for the sr-path.";
                    }

                    list sr-path-seg-list {
                        key "seg-list-index";
                        description "Enter the sr-path-seg-list list instance";

                        leaf seg-list-index {
                            type uint32 {
                                range "1..32";
                            }
                            description "Index for identifying a particular segment list";
                        }

                        leaf weight {
                            type uint32;
                            description "Specifies the relative weight of the segment list associated with a static policy.";
                        }

                        leaf segments {
                            type uint32;
                            description "Specifies the number of segments in the routing path.";
                        }

                        leaf sbfd-state {
                            type enumeration {
                                enum "down"                         { value 0; }
                                enum "up"                           { value 1; }
                            }
                            description "Specifies the s-bfd state for the routing path.";
                        }

                        leaf sbfd-transitions {
                            type uint32;
                            description "Specifies the s-bfd transitions for the routing path.";
                        }

                        list segment {
                            key "segment-index";
                            description "Enter the segment list instance";

                            leaf segment-index {
                                type uint32 {
                                    range "1..11";
                                }
                                description "Index for identifying a particular segment list";
                            }

                            leaf label {
                                type uint32;
                                description "Specifies the label used by the segment in the segment routing path.";
                            }

                            leaf segment-state {
                                type enumeration {
                                    enum "not-applicable"               { value 0; }
                                    enum "resolved-up"                  { value 1; }
                                    enum "resolved-down"                { value 2; }
                                }
                                description "Specifies the state of the segemnt.";
                            }

                        } // list segment

                    } // list sr-path-seg-list

                } // list sr-path

                list sr-policy-ingress-statistics {
                    key "color endpoint";
                    description "Enter the sr-policy-ingress-statistics list instance";

                    leaf color {
                        type uint32;
                        description "Determines the set of traffic flows that would be steered by this policy.";
                    }

                    leaf endpoint {
                        type types-sros:ip-address;
                        description "Destination of the source-routed path.";
                    }

                    leaf tunnel-id {
                        type uint32;
                        description "Specifies the tunnel-id used by the segment routing path.";
                    }

                    leaf binding-sid {
                        type types-sros:mpls-label-or-zero;
                        description "Specifies the number of active path changes for segment routing path.";
                    }

                    leaf packet-count {
                        type uint64;
                        description "Specifies the packets received.";
                    }

                    leaf byte-count {
                        type uint64;
                        description "Specifies the bytes received.";
                    }

                } // list sr-policy-ingress-statistics

                list sr-policy-egress-statistics {
                    key "color endpoint segment-index";
                    description "Enter the sr-policy-egress-statistics list instance";

                    leaf color {
                        type uint32;
                        description "Determines the set of traffic flows that would be steered by this policy.";
                    }

                    leaf endpoint {
                        type types-sros:ip-address;
                        description "Destination of the source-routed path.";
                    }

                    leaf segment-index {
                        type uint32 {
                            range "1..11";
                        }
                        description "Index into identifying a particular segment.";
                    }

                    leaf tunnel-id {
                        type uint32;
                        description "Specifies the tunnel-id used by the segment routing path.";
                    }

                    leaf binding-sid {
                        type types-sros:mpls-label-or-zero;
                        description "Specifies the number of active path changes for segment routing path.";
                    }

                    leaf packet-count {
                        type uint64;
                        description "Specifies the packets received.";
                    }

                    leaf byte-count {
                        type uint64;
                        description "Specifies the bytes received.";
                    }

                } // list sr-policy-egress-statistics

            } // container sr-policies

            container segment-routing-v6 {
                description "Enter the segment-routing-v6 context";

                list locator {
                    key "locator-name";
                    description "Enter the locator list instance";

                    leaf locator-name {
                        type types-sros:named-item-64;
                        description "SRv6 locator name";
                    }

                } // list locator

                container base-routing-instance {
                    description "Enter the base-routing-instance context";

                    list locator {
                        key "locator-name";
                        description "Enter the locator list instance";

                        leaf locator-name {
                            type leafref {
                                path "../../../locator/locator-name";
                            }
                            description "SRv6 locator name";
                        }

                        container function {
                            description "Enter the function context";

                            list end {
                                key "value";
                                description "Enter the end list instance";

                                leaf value {
                                    type uint32 {
                                        range "1..1048575";
                                    }
                                    description "SRv6 End SID function value";
                                }

                                leaf oper-value {
                                    type uint32;
                                    description "SRv6 function value.";
                                }

                                leaf status {
                                    type types-sros:srv6-error-status;
                                    description "specifies the current state of this function.";
                                }

                                leaf segment-identifier {
                                    type types-sros:ipv6-address;
                                    description "address used in the SRv6 packet.";
                                }

                            } // list end

                            list end-x {
                                key "value";
                                description "Enter the end-x list instance";

                                leaf value {
                                    type uint32 {
                                        range "1..1048575";
                                    }
                                    description "SRv6 End SID function value";
                                }

                                leaf oper-value {
                                    type uint32;
                                    description "SRv6 function value.";
                                }

                                leaf status {
                                    type types-sros:srv6-error-status;
                                    description "specifies the current state of this function.";
                                }

                                leaf segment-identifier {
                                    type types-sros:ipv6-address;
                                    description "address used in the SRv6 packet.";
                                }

                            } // list end-x

                            container end-dt4 {
                                description "Enter the end-dt4 context";

                                leaf oper-value {
                                    type uint32;
                                    description "SRv6 function value.";
                                }

                                leaf status {
                                    type types-sros:srv6-error-status;
                                    description "specifies the current state of this function.";
                                }

                                leaf segment-identifier {
                                    type types-sros:ipv6-address;
                                    description "address used in the SRv6 packet.";
                                }

                            } // container end-dt4

                            container end-dt6 {
                                description "Enter the end-dt6 context";

                                leaf oper-value {
                                    type uint32;
                                    description "SRv6 function value.";
                                }

                                leaf status {
                                    type types-sros:srv6-error-status;
                                    description "specifies the current state of this function.";
                                }

                                leaf segment-identifier {
                                    type types-sros:ipv6-address;
                                    description "address used in the SRv6 packet.";
                                }

                            } // container end-dt6

                            container end-dt46 {
                                description "Enter the end-dt46 context";

                                leaf oper-value {
                                    type uint32;
                                    description "SRv6 function value.";
                                }

                                leaf status {
                                    type types-sros:srv6-error-status;
                                    description "specifies the current state of this function.";
                                }

                                leaf segment-identifier {
                                    type types-sros:ipv6-address;
                                    description "address used in the SRv6 packet.";
                                }

                            } // container end-dt46

                        } // container function

                    } // list locator

                } // container base-routing-instance

            } // container segment-routing-v6

        } // container segment-routing

    } // grouping state-router-segment-routing

}
