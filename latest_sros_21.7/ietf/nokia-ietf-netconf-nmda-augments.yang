module nokia-ietf-netconf-nmda-augments {

  yang-version 1.1;

  namespace "urn:nokia.com:sros:ns:yang:sr:ietf-netconf-nmda-augments";

  prefix ncds-augs;

  import ietf-netconf-nmda { prefix ncds; }
  import nokia-ietf-netconf-augments { prefix nc-augs; }

  description "This YANG module defines augmentations to the standard NETCONF nmda RPCs.";

  revision "2020-12-23" {
    description "Initial revision.";
  }


  augment /ncds:get-data/ncds:input {
    uses nc-augs:nokia-configuration-region;
  }


}
