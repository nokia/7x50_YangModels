module nokia-oper-global {

    yang-version "1.1";

    namespace "urn:nokia.com:sros:ns:yang:sr:oper-global";

    prefix "oper-global";

    import nokia-conf                     { prefix "conf"; }
    import nokia-sros-yang-extensions     { prefix "sros-ext"; }
    import nokia-state                    { prefix "state"; }
    import nokia-types-eth-cfm            { prefix "types-eth-cfm"; }
    import nokia-types-operation          { prefix "types-operation"; }
    import nokia-types-sros               { prefix "types-sros"; }

    sros-ext:sros-major-release "rel21";

    organization "Nokia";

    contact
        "Nokia SR OS Support
         Web: <http://www.nokia.com>";

    description
        "Nokia YANG Data model for Nokia global operations on SR OS based routers.

         Copyright 2016 Nokia. All rights reserved. Reproduction of this document
         is authorized on the condition that the foregoing copyright notice is included.

         This nokia-oper-global YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-10-15";

    container global-operations {
        config false;
        description "Enter the global-operations context";

        action md-cli-raw-command {
            description "Trigger MD-CLI command.";

            input {

                leaf md-cli-input-line {
                    type string;
                    mandatory true;
                    description "MD-CLI command to be executed";
                }

            }
            output {

                leaf operation-id {
                    type types-operation:operation-id;
                    description "Operation ID";
                }

                leaf start-time {
                    type types-operation:operation-timestamp;
                    description "Time when the operation execution started";
                }

                leaf results-path {
                    type types-operation:operation-path;
                    description "Path to the operation results formatted as xpath";
                }

                container results {

                    leaf md-cli-output-block {
                        type string;
                        description "Output of executed MD-CLI command";
                    }

                } // container results

                leaf status {
                    type types-operation:operation-status;
                    description "Operation status";
                }

                leaf-list error-message {
                    type types-operation:operation-message;
                    description "Error messages reported during operation execution";
                }

                leaf-list warning-message {
                    type types-operation:operation-message;
                    description "Warning messages reported during operation execution";
                }

                leaf-list info-message {
                    type types-operation:operation-message;
                    description "Info messages reported during operation execution";
                }

                leaf end-time {
                    type types-operation:operation-timestamp;
                    description "Time when the operation execution completed";
                }

            }
        }

        container oam {
            description "Enter the oam context";

            container eth-cfm {
                description "Enter the eth-cfm context";

                action linktrace {
                    description "Initiate a linktrace test";

                    input {

                        leaf asynchronous {
                            type types-operation:operation-asynchronous;
                            description "Control execution type of the operation";
                        }

                        leaf retention-timeout {
                            type types-operation:operation-timeout;
                            description "Timeout for operation data retention in global operation table.";
                        }

                        leaf destination {
                            type union {
                                type types-sros:mac-unicast-address-no-zero;
                                type types-eth-cfm:mep-id-type;
                            }
                            mandatory true;
                            description "Destination MAC address or remote MEP ID of the peer";
                        }

                        leaf md-admin-name {
                            type leafref {
                                path "/state:state/state:eth-cfm/state:domain/state:md-admin-name";
                            }
                            mandatory true;
                            description "Domain name";
                        }

                        leaf ma-admin-name {
                            type leafref {
                                path "/state:state/state:eth-cfm/state:domain[state:md-admin-name=current()/../md-admin-name]/state:association/state:ma-admin-name";
                            }
                            mandatory true;
                            description "Association name";
                        }

                        leaf mep-id {
                            type types-eth-cfm:mep-id-type;
                            mandatory true;
                            description "Local Maintenance Association Endpoint (MEP) ID";
                        }

                        leaf ttl {
                            type uint32 {
                                range "0..255";
                            }
                            default "64";
                            description "Time to live for a returned linktrace";
                        }

                    }
                    output {

                        leaf operation-id {
                            type types-operation:operation-id;
                            description "Operation ID";
                        }

                        leaf start-time {
                            type types-operation:operation-timestamp;
                            description "Time when the operation execution started";
                        }

                        leaf results-path {
                            type types-operation:operation-path;
                            description "Path to the operation results formatted as xpath";
                        }

                        leaf status {
                            type types-operation:operation-status;
                            description "Operation status";
                        }

                        leaf-list error-message {
                            type types-operation:operation-message;
                            description "Error messages reported during operation execution";
                        }

                        leaf-list warning-message {
                            type types-operation:operation-message;
                            description "Warning messages reported during operation execution";
                        }

                        leaf-list info-message {
                            type types-operation:operation-message;
                            description "Info messages reported during operation execution";
                        }

                        leaf end-time {
                            type types-operation:operation-timestamp;
                            description "Time when the operation execution completed";
                        }

                    }
                }

                action loopback {
                    description "Initiate a loopback test";

                    input {

                        leaf asynchronous {
                            type types-operation:operation-asynchronous;
                            description "Control execution type of the operation";
                        }

                        leaf execution-timeout {
                            type types-operation:operation-timeout;
                            description "Timeout for operation execution.";
                        }

                        leaf retention-timeout {
                            type types-operation:operation-timeout;
                            description "Timeout for operation data retention in global operation table.";
                        }

                        leaf destination {
                            type union {
                                type types-sros:mac-unicast-address-no-zero;
                                type enumeration {
                                    enum "multicast"                    { value 0; }
                                }
                                type types-eth-cfm:mep-id-type;
                            }
                            mandatory true;
                            description "Destination MAC address or remote MEP ID of the peer";
                        }

                        leaf md-admin-name {
                            type leafref {
                                path "/state:state/state:eth-cfm/state:domain/state:md-admin-name";
                            }
                            mandatory true;
                            description "Domain name";
                        }

                        leaf ma-admin-name {
                            type leafref {
                                path "/state:state/state:eth-cfm/state:domain[state:md-admin-name=current()/../md-admin-name]/state:association/state:ma-admin-name";
                            }
                            mandatory true;
                            description "Association name";
                        }

                        leaf mep-id {
                            type types-eth-cfm:mep-id-type;
                            mandatory true;
                            description "Local Maintenance Association Endpoint (MEP) ID";
                        }

                        leaf send-count {
                            type int32 {
                                range "1..1024";
                            }
                            default "1";
                            description "Number of loopback messages to send";
                        }

                        leaf size {
                            type uint32 {
                                range "0..1500";
                            }
                            units "bytes";
                            default "0";
                            description "Data portion size of the data TLV, octet string allowed";
                        }

                        leaf priority {
                            type int32 {
                                range "0..7";
                            }
                            description "Frame priority that can be manipulated by QoS policies";
                        }

                        leaf lbm-padding {
                            type uint32 {
                                range "0|3..9778";
                            }
                            default "0";
                            description "Data portion size of the data TLV, no octet string";
                        }

                        leaf timeout {
                            type uint32 {
                                range "1..10";
                            }
                            units "seconds";
                            default "5";
                            description "Wait time for a reply to a sent message request";
                        }

                        leaf interval {
                            type uint32 {
                                range "0..600";
                            }
                            units "deciseconds";
                            default "0";
                            description "Time between probes within the test run";
                        }

                    }
                    output {

                        leaf operation-id {
                            type types-operation:operation-id;
                            description "Operation ID";
                        }

                        leaf start-time {
                            type types-operation:operation-timestamp;
                            description "Time when the operation execution started";
                        }

                        leaf results-path {
                            type types-operation:operation-path;
                            description "Path to the operation results formatted as xpath";
                        }

                        leaf status {
                            type types-operation:operation-status;
                            description "Operation status";
                        }

                        leaf-list error-message {
                            type types-operation:operation-message;
                            description "Error messages reported during operation execution";
                        }

                        leaf-list warning-message {
                            type types-operation:operation-message;
                            description "Warning messages reported during operation execution";
                        }

                        leaf-list info-message {
                            type types-operation:operation-message;
                            description "Info messages reported during operation execution";
                        }

                        leaf end-time {
                            type types-operation:operation-timestamp;
                            description "Time when the operation execution completed";
                        }

                    }
                }

            } // container eth-cfm

            container service-activation-testhead {
                description "Start or stop Service Activation Testhead service test";

                list service-test {
                    key "service-test-name";
                    description "Service test name";

                    leaf service-test-name {
                        type leafref {
                            path "/state:state/state:test-oam/state:service-activation-testhead/state:service-test/state:test-name";
                        }
                        description "The name of the Service Test to be started or stopped";
                    }

                    action start {
                        description "Start OAM Service Activation Testhead Service Test";

                        output {

                            leaf operation-id {
                                type types-operation:operation-id;
                                description "Operation ID";
                            }

                            leaf start-time {
                                type types-operation:operation-timestamp;
                                description "Time when the operation execution started";
                            }

                            leaf results-path {
                                type types-operation:operation-path;
                                description "Path to the operation results formatted as xpath";
                            }

                            leaf status {
                                type types-operation:operation-status;
                                description "Operation status";
                            }

                            leaf-list error-message {
                                type types-operation:operation-message;
                                description "Error messages reported during operation execution";
                            }

                            leaf-list warning-message {
                                type types-operation:operation-message;
                                description "Warning messages reported during operation execution";
                            }

                            leaf-list info-message {
                                type types-operation:operation-message;
                                description "Info messages reported during operation execution";
                            }

                            leaf end-time {
                                type types-operation:operation-timestamp;
                                description "Time when the operation execution completed";
                            }

                        }
                    }

                    action stop {
                        description "Stop OAM Service Activation Testhead Service Test";

                        output {

                            leaf operation-id {
                                type types-operation:operation-id;
                                description "Operation ID";
                            }

                            leaf start-time {
                                type types-operation:operation-timestamp;
                                description "Time when the operation execution started";
                            }

                            leaf results-path {
                                type types-operation:operation-path;
                                description "Path to the operation results formatted as xpath";
                            }

                            leaf status {
                                type types-operation:operation-status;
                                description "Operation status";
                            }

                            leaf-list error-message {
                                type types-operation:operation-message;
                                description "Error messages reported during operation execution";
                            }

                            leaf-list warning-message {
                                type types-operation:operation-message;
                                description "Warning messages reported during operation execution";
                            }

                            leaf-list info-message {
                                type types-operation:operation-message;
                                description "Info messages reported during operation execution";
                            }

                            leaf end-time {
                                type types-operation:operation-timestamp;
                                description "Time when the operation execution completed";
                            }

                        }
                    }

                } // list service-test

            } // container service-activation-testhead

        } // container oam

    } // container global-operations

}
