submodule nokia-conf-svc-vprn-isis {

    yang-version "1.1";

    belongs-to nokia-conf { prefix "conf"; }

    import ietf-yang-types                { prefix "yang"; }
    import nokia-sros-yang-extensions     { prefix "sros-ext"; }
    import nokia-types-igp                { prefix "types-igp"; }
    import nokia-types-isis               { prefix "types-isis"; }
    import nokia-types-sros               { prefix "types-sros"; }

    include nokia-conf-groups;
    include nokia-conf-policy-options;
    include nokia-conf-routing-options;
    include nokia-conf-system;
    include nokia-conf-system-security;


    sros-ext:sros-major-release "rel21";

    organization "Nokia";

    contact
        "Nokia SR OS Support
         Web: <http://www.nokia.com>";

    description
        "Nokia YANG Data model to configure vprn isis protocol attributes on SR OS based routers.

         Copyright 2016 Nokia. All rights reserved. Reproduction of this document
         is authorized on the condition that the foregoing copyright notice is included.

         This nokia-conf-svc-vprn-isis YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-06-18";

    grouping conf-svc-vprn-isis {
        list isis {
            key "isis-instance";
            description "Enter the isis list instance";

            leaf isis-instance {
                type int32 {
                    range "0..127";
                }
                description "Instance ID for IS-IS instance";
            }

            leaf authentication-keychain {
                type leafref {
                    path "../../../../system/security/keychains/keychain/keychain-name";
                }
                description "The keychain used to sign and/or authenticate.";
            }

            leaf authentication-key {
                type types-sros:encrypted-leaf {
                    length "1..366";
                }
                description "Authentication key to verify PDUs sent by neighboring routers";
            }

            leaf authentication-type {
                type types-isis:auth-type;
                description "Authentication type";
            }

            leaf csnp-authentication {
                type boolean;
                default "true";
                description "Authenticate individual IS-IS protocol packets of complete sequence number PDU (CSNP) type";
            }

            leaf psnp-authentication {
                type boolean;
                default "true";
                description "Authenticate individual IS-IS protocol packets of partial sequence number PDU (PSNP) type";
            }

            leaf admin-state {
                type types-sros:admin-state;
                default "disable";
                description "Administrative state of the IS-IS instance";
            }

            leaf advertise-passive-only {
                type boolean;
                default "false";
                description "Advertise prefixes that belong to passive interfaces";
            }

            leaf advertise-router-capability {
                type enumeration {
                    enum "area"                         { value 2; }
                    enum "as"                           { value 3; }
                }
                description "Advertise router capabilities to neighbors";
            }

            leaf all-l1isis {
                type yang:mac-address;
                default "01:80:C2:00:00:14";
                description "Destination MAC address for all L1 IS-IS routers";
            }

            leaf all-l2isis {
                type yang:mac-address;
                default "01:80:C2:00:00:15";
                description "Destination MAC address for all L2 IS-IS routers";
            }

            leaf authentication-check {
                type boolean;
                default "true";
                description "Perform authentication check to reject PDUs that do not match the type or key requirements";
            }

            leaf default-route-tag {
                type uint32 {
                    range "1..max";
                }
                description "Route tag for default route";
            }

            leaf hello-authentication {
                type boolean;
                default "true";
                description "Authenticate individual IS-IS protocol packets of Hello type";
            }

            leaf ignore-attached-bit {
                type boolean;
                default "false";
                description "Ignore attached bit on received L1 LSPs to disable installation of default routes";
            }

            leaf ignore-lsp-errors {
                type boolean;
                default "false";
                description "Ignore LSP packets with errors";
            }

            leaf ignore-narrow-metric {
                type boolean;
                default "false";
                description "Ignore links with narrow metrics when wide-metrics support is enabled";
            }

            leaf iid-tlv {
                type boolean;
                default "false";
                description "Use IID TLVs with IS-IS multi-instance (MI)";
            }

            leaf ipv4-multicast-routing {
                type types-isis:routing-topology;
                default "native";
                description "IS-IS topology for IPv4 multicast routing";
            }

            leaf ipv4-routing {
                type boolean;
                default "true";
                description "Support IPv4 routing for IS-IS instance";
            }

            leaf ipv6-routing {
                type types-isis:routing-topology;
                default "false";
                description "Routing topology for IPv6";
            }

            leaf hello-padding {
                type types-isis:hello-padding-type;
                description "Padding on IS-IS Hello packets";
            }

            leaf level-capability {
                type types-isis:level;
                description "Routing level for instance";
            }

            leaf lsp-lifetime {
                type uint32 {
                    range "350..65535";
                }
                units "seconds";
                sros-ext:manual-restart-to-modify;
                default "1200";
                description "Amount of time during which an LSP is considered valid";
            }

            leaf lsp-minimum-remaining-lifetime {
                type uint32 {
                    range "350..65535";
                }
                units "seconds";
                description "Minimum value for the Remaining Lifetime of an LSP";
            }

            leaf lsp-mtu-size {
                type types-isis:lsp-buffer-ext-size;
                units "bytes";
                sros-ext:manual-restart-to-modify;
                default "1492";
                description "LSP MTU size";
            }

            leaf mru-mismatch-detection {
                type boolean;
                default "false";
                description "Enable detection of MRU mismatch";
            }

            leaf overload-export-interlevel {
                type boolean;
                default "false";
                description "Advertise the inter-level routes when router is overloaded";
            }

            leaf overload-export-external {
                type boolean;
                default "false";
                description "Advertise the external routes when router is in overloaded";
            }

            leaf poi-tlv {
                type boolean;
                default "false";
                description "Purge Originator Identification TLV";
            }

            leaf prefix-attributes-tlv {
                type boolean;
                default "false";
                description "Use IS-IS Prefix Attributes TLV to exchange extended IPv4 and IPv6 reachability information";
            }

            leaf reference-bandwidth {
                type types-sros:reference-bandwidth-ext;
                units "kilobps";
                description "Reference bandwidth for bandwidth relative costing";
            }

            leaf router-id {
                type types-igp:router-id;
                sros-ext:auto-restart-to-modify;
                description "Unique router ID for the ISIS instance";
            }

            leaf standard-multi-instance {
                type boolean;
                default "false";
                description "Enable RFC standards compliant multi-instance behavior";
            }

            leaf strict-adjacency-check {
                type boolean;
                default "false";
                description "Enable strict checking of address families for IS-IS adjacencies";
            }

            leaf suppress-attached-bit {
                type boolean;
                default "false";
                description "Allow IS-IS to suppress setting the attached bit on LSPs";
            }

            leaf system-id {
                type types-igp:system-id;
                sros-ext:auto-restart-to-modify;
                sros-ext:manual-restart-to-modify;
                description "System ID";
            }

            leaf-list export-policy {
                type leafref {
                    path "../../../../policy-options/policy-statement/name";
                }
                max-elements 5;
                ordered-by user;
                description "Configure names of export policies to be used for determining which routes are exported from the routing table to this IGP.";
            }

            leaf-list import-policy {
                type leafref {
                    path "../../../../policy-options/policy-statement/name";
                }
                max-elements 5;
                ordered-by user;
                description "Configure names of import policies to be used for determining which routes are imported from this IGP to the routing table.";
            }

            leaf-list area-address {
                type types-isis:area-address;
                max-elements 3;
                description "Area address portion of NSAP address";
            }

            leaf-list apply-groups {
                type leafref {
                    path "../../../../groups/group/name";
                }
                max-elements 8;
                ordered-by user;
                description "Apply a configuration group at this level";
            }

            leaf-list apply-groups-exclude {
                type leafref {
                    path "../../../../groups/group/name";
                }
                max-elements 8;
                ordered-by user;
                description "Exclude a configuration group at this level";
            }

            container export-limit {
                presence "Enable the export-limit context";
                description "Enable the export-limit context";

                leaf number {
                    type uint32 {
                        range "1..max";
                    }
                    mandatory true;
                    description "Maximum number of routes or prefixes to be exported into IGP instance from route table";
                }

                leaf log-percent {
                    type uint32 {
                        range "1..100";
                    }
                    description "Export limit at which warning a log message and SNMP notification are sent";
                }

            } // container export-limit

            container graceful-restart {
                presence "Enable the graceful-restart context";
                description "Enable the graceful-restart context";

                leaf helper-mode {
                    type boolean;
                    default "true";
                    description "Enable graceful restart helper for IS-IS";
                }

            } // container graceful-restart

            container multi-topology {
                presence "Enable the multi-topology context";
                description "Enable the multi-topology context";

                leaf ipv6-unicast {
                    type boolean;
                    default "false";
                    description "Support multi-topology TLVs";
                }

                leaf ipv4-multicast {
                    type boolean;
                    default "false";
                    description "Support IPv4 topology (MT3)";
                }

            } // container multi-topology

            container multicast-import {
                description "Enter the multicast-import context";

                leaf ipv4 {
                    type boolean;
                    default "false";
                    description "Submit IPv4 routes into the multicast RPF of the RTM";
                }

            } // container multicast-import

            container overload {
                presence "Enable the overload context";
                description "Enable the overload context";

                leaf max-metric {
                    type boolean;
                    default "false";
                    description "Advertise transit links with maximum metric instead of setting overload bit";
                }

            } // container overload

            container overload-on-boot {
                presence "Enable the overload-on-boot context";
                description "Enable the overload-on-boot context";

                leaf timeout {
                    type uint32 {
                        range "60..1800";
                    }
                    units "seconds";
                    description "Time during which the router operates in overload state after reboot";
                }

                leaf max-metric {
                    type boolean;
                    default "false";
                    description "Advertise transit links with maximum metric instead of setting overload bit";
                }

            } // container overload-on-boot

            container prefix-limit {
                presence "Enable the prefix-limit context";
                description "Enable the prefix-limit context";

                leaf limit {
                    type uint32 {
                        range "1..max";
                    }
                    mandatory true;
                    description "Maximum number of prefixes for IS-IS instance";
                }

                leaf log-only {
                    type boolean;
                    default "false";
                    description "Send warning message at specified threshold or when limit is reached, without going into overload";
                }

                leaf warning-threshold {
                    type uint32 {
                        range "0..100";
                    }
                    units "percent";
                    default "0";
                    description "Threshold value to trigger a warning message to be sent";
                }

                leaf overload-timeout {
                    type types-igp:overload-timeout;
                    default "forever";
                    description "Time router remains in overload after prefix limit is exceeded before restarting";
                }

            } // container prefix-limit

            container lsp-refresh {
                description "Enter the lsp-refresh context";

                leaf interval {
                    type uint32 {
                        range "150..65535";
                    }
                    units "seconds";
                    default "600";
                    description "Refresh timer interval";
                }

                leaf half-lifetime {
                    type boolean;
                    default "true";
                    description "Set the refresh interval to always be half the LSP lifetime";
                }

            } // container lsp-refresh

            container rib-priority {
                description "Enter the rib-priority context";

                container high {
                    description "Enter the high context";

                    choice type {
                        case prefix-list {

                            leaf prefix-list {
                                type leafref {
                                    path "../../../../../../policy-options/prefix-list/name";
                                }
                                description "List used to select routes processed at higher priority through OSPF route calculation process";
                            }

                        }
                        case tag {

                            leaf tag {
                                type uint32 {
                                    range "1..max";
                                }
                                description "Value that matches IS-IS routes processed at higher priority through route calculation process";
                            }

                        }
                    }
                } // container high

            } // container rib-priority

            container timers {
                description "Enter the timers context";

                container spf-wait {
                    description "Enter the spf-wait context";

                    leaf spf-max-wait {
                        type uint32 {
                            range "10..120000";
                        }
                        units "milliseconds";
                        default "10000";
                        description "Maximum interval between two consecutive SPF calculations";
                    }

                    leaf spf-initial-wait {
                        type uint32 {
                            range "10..100000";
                        }
                        units "milliseconds";
                        default "1000";
                        description "Initial SPF calculation delay after topology change";
                    }

                    leaf spf-second-wait {
                        type uint32 {
                            range "10..100000";
                        }
                        units "milliseconds";
                        default "1000";
                        description "Hold time between first and second SPF calculations";
                    }

                } // container spf-wait

                container lsp-wait {
                    description "Enter the lsp-wait context";

                    leaf lsp-max-wait {
                        type uint32 {
                            range "10..120000";
                        }
                        units "milliseconds";
                        default "5000";
                        description "Maximum time between two consecutive occurrences of LSP generation";
                    }

                    leaf lsp-initial-wait {
                        type uint32 {
                            range "10..100000";
                        }
                        units "milliseconds";
                        default "10";
                        description "Initial LSP generation delay";
                    }

                    leaf lsp-second-wait {
                        type uint32 {
                            range "10..100000";
                        }
                        units "milliseconds";
                        default "1000";
                        description "Delay between first and second LSP generation";
                    }

                } // container lsp-wait

            } // container timers

            container unicast-import {
                description "Enter the unicast-import context";

                leaf ipv4 {
                    type boolean;
                    default "true";
                    description "Submit IPv4 routes into unicast RTM";
                }

                leaf ipv6 {
                    type boolean;
                    default "true";
                    description "Submit IPv6 routes into unicast RTM";
                }

            } // container unicast-import

            container loopfree-alternate {
                presence "Enable the loopfree-alternate context";
                description "Enable the loopfree-alternate context";

                container exclude {
                    description "Enter the exclude context";

                    leaf-list prefix-policy {
                        type leafref {
                            path "../../../../../../policy-options/policy-statement/name";
                        }
                        max-elements 5;
                        ordered-by user;
                        description "Policy to exclude prefixes from LFA SPF calculation";
                    }

                } // container exclude

            } // container loopfree-alternate

            list interface {
                key "interface-name";
                description "Enter the interface list instance";

                leaf interface-name {
                    type types-sros:interface-name;
                    description "Router interface name.";
                }

                leaf admin-state {
                    type types-sros:admin-state;
                    default "enable";
                    description "Administrative state of the IS-IS interface";
                }

                leaf hello-authentication-key {
                    type types-sros:encrypted-leaf {
                        length "1..366";
                    }
                    description "Authentication key or hash string for Hello PDUs";
                }

                leaf hello-authentication-keychain {
                    type leafref {
                        path "../../../../../system/security/keychains/keychain/keychain-name";
                    }
                    description "Authentication keychain to use for the session.";
                }

                leaf hello-authentication-type {
                    type types-isis:auth-type;
                    description "Hello authentication type";
                }

                leaf hello-padding {
                    type types-isis:hello-padding-type;
                    description "Padding on IS-IS Hello packets";
                }

                leaf passive {
                    type boolean;
                    default "false";
                    description "Passive interface";
                }

                leaf csnp-interval {
                    type uint32 {
                        range "1..65535";
                    }
                    units "seconds";
                    default "10";
                    description "Time interval between successive CSN PDUs sent from interface";
                }

                leaf default-instance {
                    type boolean;
                    default "false";
                    description "Allow non-MI capable router to establish an adjacency and operate with a router in non-zero instance";
                }

                leaf hello-authentication {
                    type boolean;
                    default "true";
                    description "Authenticate individual IS-IS protocol packets of Hello type";
                }

                leaf interface-type {
                    type types-isis:interface-type;
                    description "Interface type to broadcast, point-to-point, or to be default";
                }

                leaf ipv4-multicast {
                    type boolean;
                    default "true";
                    description "Enable IPv4 multicast routing for the interface";
                }

                leaf ipv6-unicast {
                    type boolean;
                    default "true";
                    description "Enable IPv6 unicast routing for the interface";
                }

                leaf level-capability {
                    type types-isis:level;
                    description "IS-IS levels for this interface";
                }

                leaf load-balancing-weight {
                    type uint32;
                    description "Load balancing weight";
                }

                leaf lsp-pacing-interval {
                    type uint32 {
                        range "0..65535";
                    }
                    units "milliseconds";
                    default "100";
                    description "Interval for sending LSPs from interface";
                }

                leaf retransmit-interval {
                    type uint32 {
                        range "1..65535";
                    }
                    units "seconds";
                    default "5";
                    description "Minimum time between LSP PDU retransmissions on point-to-point interface";
                }

                leaf tag {
                    type uint32 {
                        range "1..max";
                    }
                    description "Route tag for IP address of interface";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                container loopfree-alternate {
                    description "Enter the loopfree-alternate context";

                    leaf exclude {
                        type boolean;
                        default "false";
                        description "Enable/disable Loopfree Alternative at interface level.";
                    }

                    container policy-map {
                        presence "Enable the policy-map context";
                        description "Enter the policy-map context";

                        leaf route-nh-template {
                            type leafref {
                                path "../../../../../../../routing-options/route-next-hop-policy/template/template-name";
                            }
                            mandatory true;
                            description "Route next hop policy template that is applied to interface";
                        }

                    } // container policy-map

                } // container loopfree-alternate

                container mesh-group {
                    presence "Enable the mesh-group context";
                    description "Enable the mesh-group context";

                    choice type {
                        case value {

                            leaf value {
                                type int32 {
                                    range "1..2000000000";
                                }
                                description "Mesh group for the interface";
                            }

                        }
                        case blocked {

                            leaf blocked {
                                type empty;
                                description "Prevent the interface from flooding LSPs";
                            }

                        }
                    }
                } // container mesh-group

                container bfd-liveness {
                    description "Enter the bfd-liveness context";

                    container ipv4 {
                        presence "Enable the ipv4 context";
                        description "Enable the ipv4 context";

                        leaf include-bfd-tlv {
                            type boolean;
                            default "false";
                            description "BFD-enabled TLV for IPv4 to include on this IS-IS interface";
                        }

                    } // container ipv4

                    container ipv6 {
                        presence "Enable the ipv6 context";
                        description "Enable the ipv6 context";

                        leaf include-bfd-tlv {
                            type boolean;
                            default "false";
                            description "BFD-enabled TLV for IPv4 to include on this IS-IS interface";
                        }

                    } // container ipv6

                } // container bfd-liveness

                list level {
                    key "level-number";
                    max-elements 2;
                    description "Enter the level list instance";

                    leaf level-number {
                        type enumeration {
                            enum "1"                            { value 1; }
                            enum "2"                            { value 2; }
                        }
                        description "ISIS protocol level number";
                    }

                    leaf hello-authentication-key {
                        type types-sros:encrypted-leaf {
                            length "1..366";
                        }
                        description "Authentication key for Hello PDUs";
                    }

                    leaf hello-authentication-keychain {
                        type leafref {
                            path "../../../../../../system/security/keychains/keychain/keychain-name";
                        }
                        description "Authentication keychain to use for the session.";
                    }

                    leaf hello-authentication-type {
                        type types-isis:auth-type;
                        description "Hello authentication enabled on the context";
                    }

                    leaf hello-padding {
                        type types-isis:hello-padding-type;
                        description "Padding on IS-IS Hello packets";
                    }

                    leaf passive {
                        type boolean;
                        default "false";
                        description "Passive interface";
                    }

                    leaf hello-interval {
                        type uint32 {
                            range "1..20000";
                        }
                        units "seconds";
                        default "9";
                        description "Interval between Hello messages sent on this level";
                    }

                    leaf hello-multiplier {
                        type int32 {
                            range "2..100";
                        }
                        default "3";
                        description "Hello messages missed from neighbor before router declares adjacency down";
                    }

                    leaf ipv4-multicast-metric {
                        type types-isis:metric;
                        description "IS-IS interface metric applied for IPv4 multicast";
                    }

                    leaf ipv6-unicast-metric {
                        type types-isis:metric;
                        description "IS-IS interface metric applied for IPv6 unicast";
                    }

                    leaf metric {
                        type types-isis:metric;
                        description "IS-IS interface metric applied for IPv4 unicast";
                    }

                    leaf priority {
                        type uint32 {
                            range "0..127";
                        }
                        default "64";
                        description "Router to become the designated router on a multi-access network";
                    }

                    leaf sd-offset {
                        type types-isis:metric;
                        description "Value of the signal degrade offset";
                    }

                    leaf sf-offset {
                        type types-isis:metric;
                        description "Value of the signal fail offset";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // list level

            } // list interface

            list level {
                key "level-number";
                max-elements 2;
                description "Enter the level list instance";

                leaf level-number {
                    type enumeration {
                        enum "1"                            { value 1; }
                        enum "2"                            { value 2; }
                    }
                    description "ISIS protocol level number";
                }

                leaf authentication-keychain {
                    type leafref {
                        path "../../../../../system/security/keychains/keychain/keychain-name";
                    }
                    description "The keychain used to sign and/or authenticate.";
                }

                leaf authentication-key {
                    type types-sros:encrypted-leaf {
                        length "1..366";
                    }
                    description "Authentication key to verify PDUs sent on the interface";
                }

                leaf authentication-type {
                    type types-isis:auth-type;
                    description "Configure the authentication type to be used.";
                }

                leaf csnp-authentication {
                    type boolean;
                    default "true";
                    description "Enable/disable authentication on received ISIS protocol packets of type CSNP.";
                }

                leaf psnp-authentication {
                    type boolean;
                    default "true";
                    description "Enable/disable authentication on received ISIS protocol packets of type PSNP.";
                }

                leaf advertise-router-capability {
                    type boolean;
                    default "true";
                    description "Allow router advertisement capabilities";
                }

                leaf default-ipv4-multicast-metric {
                    type types-isis:metric;
                    default "10";
                    description "Default metric for IPv4 unicast";
                }

                leaf default-ipv6-unicast-metric {
                    type types-isis:metric;
                    default "10";
                    description "Default metric for IPv6 unicast";
                }

                leaf default-metric {
                    type types-isis:metric;
                    default "10";
                    description "Default metric";
                }

                leaf external-preference {
                    type uint32 {
                        range "1..255";
                    }
                    description "External route preference for IS-IS level";
                }

                leaf hello-authentication {
                    type boolean;
                    default "true";
                    description "Authenticate individual IS-IS protocol packets of Hello type";
                }

                leaf hello-padding {
                    type types-isis:hello-padding-type;
                    description "Padding on IS-IS Hello packets";
                }

                leaf loopfree-alternate-exclude {
                    type boolean;
                    default "false";
                    description "Exclude interface participating in specific IS-IS level in SPF LFA computation";
                }

                leaf lsp-mtu-size {
                    type types-isis:lsp-buffer-ext-size;
                    units "bytes";
                    sros-ext:manual-restart-to-modify;
                    default "1492";
                    description "LSP MTU size";
                }

                leaf preference {
                    type uint32 {
                        range "1..255";
                    }
                    description "External route preference at level";
                }

                leaf wide-metrics-only {
                    type boolean;
                    default "false";
                    description "Use wide metrics advertisements in the LSPs";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

            } // list level

            list link-group {
                key "link-group-name";
                description "Enter the link-group list instance";

                leaf link-group-name {
                    type types-sros:named-item;
                    description "Link group name for the IS-IS protocol";
                }

                leaf description {
                    type types-sros:very-long-description;
                    description "Text description";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                list level {
                    key "level-number";
                    max-elements 2;
                    description "Enter the level list instance";

                    leaf level-number {
                        type enumeration {
                            enum "1"                            { value 1; }
                            enum "2"                            { value 2; }
                        }
                        description "ISIS protocol level number";
                    }

                    leaf ipv4-multicast-metric-offset {
                        type types-isis:metric;
                        description "Offset value for the IPv4 multicast address family";
                    }

                    leaf ipv4-unicast-metric-offset {
                        type types-isis:metric;
                        description "Offset value for the IPv4 unicast address family";
                    }

                    leaf ipv6-unicast-metric-offset {
                        type types-isis:metric;
                        description "Offset value for the IPv6 unicast address family";
                    }

                    leaf oper-members {
                        type uint32 {
                            range "1..8";
                        }
                        description "Minimum number of operational links";
                    }

                    leaf revert-members {
                        type uint32 {
                            range "1..8";
                        }
                        description "Minimum number of operational links to return link group to normal state and remove offsets";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                    list member {
                        key "interface-name";
                        max-elements 8;
                        description "Add a list entry for member";

                        leaf interface-name {
                            type leafref {
                                path "../../../../interface/interface-name";
                            }
                            description "Router interface name for this link group";
                        }

                    } // list member

                } // list level

            } // list link-group

            list summary-address {
                key "ip-prefix";
                description "Enter the summary-address list instance";

                leaf ip-prefix {
                    type types-sros:ip-prefix;
                    description "Summary IP prefix";
                }

                leaf level-capability {
                    type types-isis:level;
                    description "IS-IS Level from which the prefix should be summarized";
                }

                leaf route-tag {
                    type uint32 {
                        range "1..max";
                    }
                    description "Route tag assigned to the summary address";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

            } // list summary-address

        } // list isis

    } // grouping conf-svc-vprn-isis

}
