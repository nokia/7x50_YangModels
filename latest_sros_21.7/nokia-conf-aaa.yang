submodule nokia-conf-aaa {

    yang-version "1.1";

    belongs-to nokia-conf { prefix "conf"; }

    import ietf-inet-types                { prefix "inet"; }
    import ietf-yang-types                { prefix "yang"; }
    import nokia-sros-yang-extensions     { prefix "sros-ext"; }
    import nokia-types-diameter           { prefix "types-diam"; }
    import nokia-types-nat                { prefix "types-nat"; }
    import nokia-types-radius             { prefix "types-radius"; }
    import nokia-types-sros               { prefix "types-sros"; }

    include nokia-conf-groups;
    include nokia-conf-python;
    include nokia-conf-redundancy;


    sros-ext:sros-major-release "rel21";

    organization "Nokia";

    contact
        "Nokia SR OS Support
         Web: <http://www.nokia.com>";

    description
        "Nokia YANG Data model to configure authentication, authorization and accounting on SR OS based routers.

         Copyright 2016 Nokia. All rights reserved. Reproduction of this document
         is authorized on the condition that the foregoing copyright notice is included.

         This nokia-conf-aaa YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-10-23";

    grouping conf-aaa {
        container aaa {
            description "Enter the aaa context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            container radius {
                description "Enter the radius context";

                leaf coa-port {
                    type inet:port-number {
                        range "1647|1700|1812|3799";
                    }
                    default "3799";
                    description "Radius CoA port";
                }

                list acct-on-off-group {
                    key "name";
                    max-elements 32;
                    description "Enter the acct-on-off-group list instance";

                    leaf name {
                        type types-sros:named-item;
                        description "Acct-on-off group name";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list acct-on-off-group

                list server-policy {
                    key "name";
                    max-elements 32;
                    description "Enter the server-policy list instance";

                    leaf name {
                        type types-sros:named-item;
                        description "RADIUS server policy name";
                    }

                    leaf description {
                        type types-sros:description;
                        description "Text description";
                    }

                    leaf python-policy {
                        type leafref {
                            path "../../../../python/python-policy/name";
                        }
                        description "Python policy to modify the RADIUS messages";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container servers {
                        description "Enter the servers context";

                        leaf timeout {
                            type types-sros:time-duration {
                                range "1..340";
                            }
                            units "seconds";
                            default "5";
                            description "Time until the next retry to the RADIUS server";
                        }

                        leaf retry-count {
                            type uint32 {
                                range "1..256";
                            }
                            default "3";
                            description "Number of retries for contacting the RADIUS server";
                        }

                        leaf hold-down-time {
                            type types-sros:time-duration {
                                range "30..86400";
                            }
                            units "seconds";
                            default "30";
                            description "Hold time before re-using a RADIUS server that was down";
                        }

                        leaf router-instance {
                            type string;
                            description "RADIUS routing instance";
                        }

                        leaf source-address {
                            type types-sros:ipv4-address;
                            description "Source address of RADIUS messages";
                        }

                        leaf ipv6-source-address {
                            type types-sros:ipv6-address;
                            description "Source address for IPv6 RADIUS datagrams";
                        }

                        leaf access-algorithm {
                            type types-radius:server-selection-algo;
                            description "Algorithm to access the set of RADIUS servers";
                        }

                        leaf stickiness {
                            type boolean;
                            default "true";
                            description "Allow stickiness in a multi-server application";
                        }

                        list server {
                            key "server-index";
                            max-elements 32;
                            description "Enter the server list instance";

                            leaf server-index {
                                type uint32 {
                                    range "1..16";
                                }
                                description "RADIUS server index";
                            }

                            leaf server-name {
                                type types-sros:named-item;
                                mandatory true;
                                description "RADIUS server name";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                        } // list server

                        container buffering {
                            description "Enter the buffering context";

                            container acct-start {
                                presence "Enable the acct-start context";
                                description "Enter the acct-start context";

                                leaf min {
                                    type types-sros:time-duration {
                                        range "1..3600";
                                    }
                                    units "seconds";
                                    mandatory true;
                                    description "Minimum time between accounting message resend attempts";
                                }

                                leaf max {
                                    type types-sros:time-duration {
                                        range "1..3600";
                                    }
                                    units "seconds";
                                    mandatory true;
                                    description "Maximum time between accounting message resend attempts";
                                }

                                leaf lifetime {
                                    type types-sros:time-duration {
                                        range "1..25";
                                    }
                                    units "hours";
                                    mandatory true;
                                    description "Time accounting message can be in retransmission buffer";
                                }

                            } // container acct-start

                            container acct-interim {
                                presence "Enable the acct-interim context";
                                description "Enable the acct-interim context";

                                leaf min {
                                    type types-sros:time-duration {
                                        range "1..3600";
                                    }
                                    units "seconds";
                                    mandatory true;
                                    description "Minimum time between accounting message resend attempts";
                                }

                                leaf max {
                                    type types-sros:time-duration {
                                        range "1..3600";
                                    }
                                    units "seconds";
                                    mandatory true;
                                    description "Maximum time between accounting message resend attempts";
                                }

                                leaf lifetime {
                                    type types-sros:time-duration {
                                        range "1..25";
                                    }
                                    units "hours";
                                    mandatory true;
                                    description "Time accounting message can be in retransmission buffer";
                                }

                            } // container acct-interim

                            container acct-stop {
                                presence "Enable the acct-stop context";
                                description "Enable the acct-stop context";

                                leaf min {
                                    type types-sros:time-duration {
                                        range "1..3600";
                                    }
                                    units "seconds";
                                    mandatory true;
                                    description "Minimum time between accounting message resend attempts";
                                }

                                leaf max {
                                    type types-sros:time-duration {
                                        range "1..3600";
                                    }
                                    units "seconds";
                                    mandatory true;
                                    description "Maximum time between accounting message resend attempts";
                                }

                                leaf lifetime {
                                    type types-sros:time-duration {
                                        range "1..25";
                                    }
                                    units "hours";
                                    mandatory true;
                                    description "Time accounting message can be in retransmission buffer";
                                }

                            } // container acct-stop

                        } // container buffering

                        container health-check {
                            description "Enter the health-check context";

                            leaf down-timeout {
                                type types-sros:time-duration {
                                    range "1..340";
                                }
                                units "seconds";
                                description "Wait time before declaring RADIUS server out-of-service";
                            }

                            container test-account {
                                description "Enter the test-account context";

                                leaf admin-state {
                                    type types-sros:admin-state;
                                    default "disable";
                                    description "Administrative state of the health check";
                                }

                                leaf interval {
                                    type types-sros:time-duration {
                                        range "1..60";
                                    }
                                    units "seconds";
                                    default "3";
                                    description "Time for health check";
                                }

                                leaf user-name {
                                    type types-sros:display-string {
                                        length "1..64";
                                    }
                                    description "Username to send access requests to probe RADIUS server";
                                }

                                leaf password {
                                    type types-sros:encrypted-leaf {
                                        length "1..115";
                                    }
                                    description "Password for health check";
                                }

                            } // container test-account

                        } // container health-check

                    } // container servers

                    container acct-on-off {
                        presence "Enable the acct-on-off context";
                        description "Enable the acct-on-off context";

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        choice mode {
                            case monitor {

                                leaf monitor {
                                    type leafref {
                                        path "../../../acct-on-off-group/name";
                                    }
                                    sros-ext:immutable;
                                    description "Accounting on/off group name";
                                }

                            }
                            case oper-state-change {

                                container oper-state-change {
                                    presence "Enable the oper-state-change context";
                                    description "Enable the oper-state-change context";

                                    leaf group {
                                        type leafref {
                                            path "../../../../acct-on-off-group/name";
                                        }
                                        sros-ext:immutable;
                                        description "Change of operational state for a group";
                                    }

                                } // container oper-state-change

                            }
                        }
                    } // container acct-on-off

                } // list server-policy

                list route-downloader {
                    key "name";
                    max-elements 1;
                    description "Enter the route-downloader list instance";

                    leaf name {
                        type types-sros:named-item;
                        description "RADIUS route downloader name";
                    }

                    leaf description {
                        type types-sros:description;
                        description "Text description";
                    }

                    leaf admin-state {
                        type types-sros:admin-state;
                        default "disable";
                        description "Administrative state of this Route Downloader";
                    }

                    leaf radius-server-policy {
                        type leafref {
                            path "../../server-policy/name";
                        }
                        description "Referenced RADIUS server policy";
                    }

                    leaf download-interval {
                        type uint32 {
                            range "1..1440";
                        }
                        units "minutes";
                        default "720";
                        description "Wait time between consecutive runs of the process";
                    }

                    leaf default-metric {
                        type uint32 {
                            range "0..254";
                        }
                        default "2";
                        description "Default metric of this route downloader";
                    }

                    leaf default-tag {
                        type uint32 {
                            range "0..4294967295";
                        }
                        default "0";
                        description "Default tag of this route downloader";
                    }

                    leaf max-routes {
                        type uint32 {
                            range "1..200000";
                        }
                        default "200000";
                        description "Maximum routes imported by this route downloader";
                    }

                    leaf base-user-name {
                        type types-sros:named-item;
                        description "Prefix of the username used as access requests";
                    }

                    leaf password {
                        type types-sros:encrypted-leaf {
                            length "1..71";
                        }
                        description "Route downloader password";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container retry-interval {
                        description "Enter the retry-interval context";

                        leaf min {
                            type uint32 {
                                range "1..1440";
                            }
                            units "minutes";
                            default "10";
                            description "Minimum duration of the retry interval";
                        }

                        leaf max {
                            type uint32 {
                                range "1..1440";
                            }
                            units "minutes";
                            default "20";
                            description "Maximum duration of the retry interval";
                        }

                    } // container retry-interval

                } // list route-downloader

                list l2tp-accounting-policy {
                    key "name";
                    max-elements 32;
                    description "Enter the l2tp-accounting-policy list instance";

                    leaf name {
                        type types-sros:named-item;
                        description "L2TP RADIUS accounting policy name";
                    }

                    leaf description {
                        type types-sros:description;
                        description "Text description";
                    }

                    leaf acct-tunnel-connection-fmt {
                        type types-sros:display-string {
                            length "1..253";
                            pattern "([^%]+|%[nsStTcC%])+";
                        }
                        default "%n";
                        description "Accounting tunnel connection ASCII specification";
                    }

                    leaf radius-server-policy {
                        type leafref {
                            path "../../server-policy/name";
                        }
                        description "Referenced RADIUS server policy";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container accounting-type {
                        description "Enter the accounting-type context";

                        leaf session {
                            type boolean;
                            default "true";
                            description "Enable per-session accounting";
                        }

                        leaf tunnel {
                            type boolean;
                            default "true";
                            description "Enable per-tunnel accounting";
                        }

                    } // container accounting-type

                    container include-radius-attribute {
                        description "Enter the include-radius-attribute context";

                        leaf calling-station-id {
                            type boolean;
                            default "false";
                            description "Include the calling station ID attribute";
                        }

                        leaf nas-identifier {
                            type boolean;
                            default "false";
                            description "Include the NAS-Identifier attribute";
                        }

                        container nas-port {
                            presence "Enable the nas-port context";
                            description "Enable the nas-port context";

                            leaf bit-spec {
                                type types-sros:binary-specification {
                                    pattern "([01]|(\\*[0123456789]+)?[oismpvc])+";
                                }
                                mandatory true;
                                description "RADIUS NAS-Port attribute";
                            }

                        } // container nas-port

                        container nas-port-id {
                            presence "Enable the nas-port-id context";
                            description "Enable the nas-port-id context";

                            leaf prefix-string {
                                type types-sros:string-not-all-spaces {
                                    length "1..8";
                                }
                                description "Prefix string added to RADIUS NAS port attribute";
                            }

                            leaf suffix {
                                type enumeration {
                                    enum "circuit-id"                   { value 1; }
                                    enum "remote-id"                    { value 2; }
                                }
                                description "NAS-Port-Id suffix";
                            }

                        } // container nas-port-id

                        container nas-port-type {
                            presence "Enable the nas-port-type context";
                            description "Enable the nas-port-type context";

                            leaf type {
                                type union {
                                    type enumeration {
                                        enum "rfc-aligned"                  { value 1000; }
                                    }
                                    type uint32 {
                                        range "0..255";
                                    }
                                }
                                default "rfc-aligned";
                                description "Value for RADIUS NAS-Port-Type attribute";
                            }

                        } // container nas-port-type

                    } // container include-radius-attribute

                } // list l2tp-accounting-policy

                list isa-policy {
                    key "name";
                    max-elements 8;
                    description "Enter the isa-policy list instance";

                    leaf name {
                        type types-sros:named-item;
                        description "ISA RADIUS policy name referenced by a NAT application";
                    }

                    leaf description {
                        type types-sros:description;
                        description "Text description";
                    }

                    leaf password {
                        type types-sros:encrypted-leaf {
                            length "1..42";
                        }
                        description "Password used in the RADIUS access requests";
                    }

                    leaf nas-ip-address-origin {
                        type enumeration {
                            enum "system-ip"                    { value 0; }
                            enum "isa-ip"                       { value 1; }
                        }
                        default "system-ip";
                        description "NAS-IP-Address attribute";
                    }

                    leaf python-policy {
                        type leafref {
                            path "../../../../python/python-policy/name";
                        }
                        description "Python policy used for modifying RADIUS messages";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container accounting {
                        description "Enter the accounting context";

                        container include-attributes {
                            description "Enter the include-attributes context";

                            leaf acct-delay-time {
                                type boolean;
                                default "false";
                                description "Include the Acct-Delay-Time attribute";
                            }

                            leaf acct-triggered-reason {
                                type boolean;
                                default "false";
                                description "Include the Alc-Acct-Triggered-Reason attribute";
                            }

                            leaf called-station-id {
                                type boolean;
                                default "false";
                                description "Include the Called-Station-Id attribute";
                            }

                            leaf calling-station-id {
                                type boolean;
                                default "false";
                                description "Include the Calling-Station-Id attribute";
                            }

                            leaf circuit-id {
                                type boolean;
                                default "false";
                                description "Include the Agent-Circuit-Id attribute";
                            }

                            leaf class {
                                type boolean;
                                default "false";
                                description "Include the Class attribute";
                            }

                            leaf dhcp-options {
                                type boolean;
                                default "false";
                                description "Include the Alc-ToServer-Dhcp-Options attribute";
                            }

                            leaf dhcp-vendor-class-id {
                                type boolean;
                                default "false";
                                description "Include the Alc-DHCP-Vendor-Class-Id attribute";
                            }

                            leaf frame-counters {
                                type boolean;
                                default "false";
                                description "Include Acct-Input-Packets and Acct-Output-Packets";
                            }

                            leaf framed-ip-address {
                                type boolean;
                                default "false";
                                description "Include the Framed-IP-Address attribute";
                            }

                            leaf framed-ip-netmask {
                                type boolean;
                                default "false";
                                description "Include the Framed-IP-Netmask attribute";
                            }

                            leaf framed-ipv6-prefix {
                                type boolean;
                                default "false";
                                description "Include the Framed-IPv6-Prefix attribute";
                            }

                            leaf hardware-timestamp {
                                type boolean;
                                default "false";
                                description "Include the Event-Timestamp attribute";
                            }

                            leaf ipv6-address {
                                type boolean;
                                default "false";
                                description "Include the Alc-Ipv6-Address attribute";
                            }

                            leaf mac-address {
                                type boolean;
                                default "false";
                                description "Include the Alc-Client-Hardware-Addr attribute";
                            }

                            leaf multi-session-id {
                                type boolean;
                                default "false";
                                description "Include the Acct-Multi-Session-Id attribute";
                            }

                            leaf nas-identifier {
                                type boolean;
                                default "false";
                                description "Include the NAS-Identifier attribute";
                            }

                            leaf nas-ip-address {
                                type boolean;
                                default "false";
                                description "Include the NAS-IP-Address attribute";
                            }

                            leaf nas-port {
                                type boolean;
                                default "false";
                                description "Include the NAS-Port attribute";
                            }

                            leaf nas-port-id {
                                type boolean;
                                default "false";
                                description "Include the NAS-Port-Id attribute";
                            }

                            leaf nas-port-type {
                                type boolean;
                                default "false";
                                description "Include the NAS-Port-Type attribute";
                            }

                            leaf nat-inside-service-id {
                                type boolean;
                                default "false";
                                description "Include NAT inside service ID in Alc-Serv-Id attribute";
                            }

                            leaf nat-outside-ip-address {
                                type boolean;
                                default "false";
                                description "Include the Alc-Nat-Outside-Ip-Addr attribute";
                            }

                            leaf nat-outside-service-id {
                                type boolean;
                                default "false";
                                description "Include NAT outside service ID in Alc-Serv-Id attribute";
                            }

                            leaf nat-port-range-block {
                                type boolean;
                                default "false";
                                description "Include the Alc-Nat-Port-Range attribute";
                            }

                            leaf nat-subscriber-string {
                                type boolean;
                                default "false";
                                description "Include the Alc-Subsc-ID-Str attribute";
                            }

                            leaf octet-counters {
                                type boolean;
                                default "false";
                                description "Include Acct-Input-Octets and Acct-Output-Octets";
                            }

                            leaf proxied-subscriber-data {
                                type boolean;
                                default "false";
                                description "Include subscriber data as RADIUS attributes";
                            }

                            leaf release-reason {
                                type boolean;
                                default "false";
                                description "Include reason in the Acct-Terminate-Cause attribute";
                            }

                            leaf remote-id {
                                type boolean;
                                default "false";
                                description "Include the Agent-Remote-Id attribute";
                            }

                            leaf rssi {
                                type boolean;
                                default "false";
                                description "Include the Alc-RSSI attribute";
                            }

                            leaf session-time {
                                type boolean;
                                default "false";
                                description "Include the Acct-Session-Time attribute";
                            }

                            leaf subscriber-id {
                                type boolean;
                                default "false";
                                description "Include the Alc-Subsc-ID-Str attribute";
                            }

                            leaf toserver-dhcp6-options {
                                type boolean;
                                default "false";
                                description "Include the Alc-ToServer-Dhcp6-Options attribute";
                            }

                            leaf ue-creation-type {
                                type boolean;
                                default "false";
                                description "Include the Alc-Wlan-Ue-Creation-Type attribute";
                            }

                            leaf user-name {
                                type boolean;
                                default "false";
                                description "Include the User-Name attribute";
                            }

                            leaf wlan-ssid-vlan {
                                type boolean;
                                default "false";
                                description "Include per-SSID VLAN in Alc-Wlan-SSID-VLAN attribute";
                            }

                            leaf xconnect-tunnel-local-ipv6-address {
                                type boolean;
                                default "false";
                                description "Include the Alc-Xconnect-Tunnel-Local-Ipv6 attribute";
                            }

                            leaf xconnect-tunnel-remote-ipv6-address {
                                type boolean;
                                default "false";
                                description "Include the Alc-Xconnect-Tunnel-Remote-Ipv6 attribute";
                            }

                            leaf xconnect-tunnel-service {
                                type boolean;
                                default "false";
                                description "Include the Alc-Xconnect-Tunnel-Service attribute";
                            }

                            leaf xconnect-tunnel-type {
                                type boolean;
                                default "false";
                                description "Include the Alc-Xconnect-Tunnel-Type attribute";
                            }

                            leaf xconnect-tunnel-home-address {
                                type boolean;
                                default "false";
                                description "Include the Alc-Xconnect-Tunnel-Home-Ipv6 attribute";
                            }

                            leaf millisecond-event-timestamp {
                                type boolean;
                                default "false";
                                description "Include the Alc-Millisecond-Event-Timestamp attribute";
                            }

                            leaf credit-control-quota {
                                type boolean;
                                default "false";
                                description "Add unconsumed volume quota to Alc-Credit-Control-Quota";
                            }

                        } // container include-attributes

                        container update-triggers {
                            description "Enter the update-triggers context";

                            leaf address-state {
                                type boolean;
                                default "false";
                                description "Send an Interim-Update when address allocated or freed";
                            }

                            leaf soft-quota-exhausted {
                                type boolean;
                                default "false";
                                description "Send interim update when soft volume quota is reached";
                            }

                        } // container update-triggers

                        container nat-periodic-update {
                            description "Enter the nat-periodic-update context";

                            leaf interval {
                                type types-sros:time-duration {
                                    range "1..72";
                                }
                                units "hours";
                                description "Interval for periodic RADIUS Interim-Update messages";
                            }

                            leaf rate-limit {
                                type union {
                                    type uint32 {
                                        range "1..100000";
                                    }
                                    type enumeration {
                                        enum "unlimited"                    { value 0; }
                                    }
                                }
                                units "packets per second";
                                default "unlimited";
                                description "Rate limit for periodic RADIUS Interim-Update messages";
                            }

                        } // container nat-periodic-update

                    } // container accounting

                    container authentication {
                        description "Enter the authentication context";

                        container include-attributes {
                            description "Enter the include-attributes context";

                            leaf called-station-id {
                                type boolean;
                                default "false";
                                description "Include the Called-Station-Id attribute";
                            }

                            leaf calling-station-id {
                                type boolean;
                                default "false";
                                description "Include the Calling-Station-Id attribute";
                            }

                            leaf circuit-id {
                                type boolean;
                                default "false";
                                description "Include the Agent-Circuit-Id attribute";
                            }

                            leaf toserver-dhcp-options {
                                type boolean;
                                default "false";
                                description "Include the Alc-ToServer-Dhcp-Options attribute";
                            }

                            leaf dhcp-vendor-class-id {
                                type boolean;
                                default "false";
                                description "Include the Alc-DHCP-Vendor-Class-Id attribute";
                            }

                            leaf framed-ip-address {
                                type boolean;
                                default "false";
                                description "Include the Framed-IP-Address attribute";
                            }

                            leaf ipv6-address {
                                type boolean;
                                default "false";
                                description "Include the IPv6-address attribute";
                            }

                            leaf mac-address {
                                type boolean;
                                default "false";
                                description "Include the Alc-Client-Hardware-Addr attribute";
                            }

                            leaf nas-identifier {
                                type boolean;
                                default "false";
                                description "Include the NAS-Identifier attribute";
                            }

                            leaf nas-ip-address {
                                type boolean;
                                default "true";
                                description "Include the NAS-IP-Address attribute";
                            }

                            leaf nas-port {
                                type boolean;
                                default "false";
                                description "Include the NAS-Port attribute";
                            }

                            leaf nas-port-id {
                                type boolean;
                                default "false";
                                description "Include the NAS-Port-Id attribute";
                            }

                            leaf nas-port-type {
                                type boolean;
                                default "false";
                                description "Include the NAS-Port-Type attribute";
                            }

                            leaf remote-id {
                                type boolean;
                                default "false";
                                description "Include the Agent-Remote-Id attribute";
                            }

                            leaf toserver-dhcp6-options {
                                type boolean;
                                default "false";
                                description "Include the Alc-ToServer-Dhcp6-Options attribute";
                            }

                            leaf wlan-ssid-vlan {
                                type boolean;
                                default "false";
                                description "Include per-SSID VLAN in Alc-Wlan-SSID-VLAN attribute";
                            }

                            leaf xconnect-tunnel-home-address {
                                type boolean;
                                default "false";
                                description "Include the Alc-Xconnect-Tunnel-Home-Ipv6 attribute";
                            }

                        } // container include-attributes

                    } // container authentication

                    container user-name {
                        description "Enter the user-name context";

                        leaf format {
                            type enumeration {
                                enum "mac"                          { value 1; }
                                enum "mac-ip"                       { value 2; }
                                enum "dhcp-vendor"                  { value 3; }
                                enum "circuit-id"                   { value 4; }
                            }
                            default "mac";
                            description "How user is represented when contacting RADIUS server";
                        }

                        leaf mac-format {
                            type types-nat:mac-format;
                            description "How the MAC address gets formatted";
                        }

                    } // container user-name

                    container servers {
                        description "Enter the servers context";

                        leaf source-address-range {
                            type types-sros:ipv4-unicast-address;
                            description "Starting IP address of the IP address range";
                        }

                        leaf timeout {
                            type types-sros:time-duration {
                                range "1..90";
                            }
                            units "seconds";
                            default "5";
                            description "Timeout for a response from the RADIUS server";
                        }

                        leaf total-tries {
                            type uint32 {
                                range "1..10";
                            }
                            default "3";
                            description "Maximum number of tries toward the same RADIUS server";
                        }

                        leaf router-instance {
                            type string;
                            description "The routing instance";
                        }

                        leaf access-algorithm {
                            type types-radius:isa-server-selection-algo;
                            description "Algorithm that accesses the RADIUS servers";
                        }

                        list server {
                            key "index";
                            max-elements 10;
                            description "Enter the server list instance";

                            leaf index {
                                type uint32 {
                                    range "1..10";
                                }
                                description "RADIUS server ID";
                            }

                            leaf admin-state {
                                type types-sros:admin-state;
                                default "disable";
                                description "Administrative state of the ISA RADIUS server";
                            }

                            leaf ip-address {
                                type types-sros:ipv4-unicast-address;
                                description "IP address of the RADIUS server";
                            }

                            leaf secret {
                                type types-sros:encrypted-leaf {
                                    length "1..115";
                                }
                                description "Secret key to access the RADIUS server";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            container purpose {
                                description "Enter the purpose context";

                                container accounting {
                                    presence "Enable the accounting context";
                                    description "Enable the accounting context";

                                    leaf udp-port {
                                        type types-sros:tcp-udp-port-non-zero;
                                        default "1813";
                                        description "ISA RADIUS server accounting UDP port";
                                    }

                                } // container accounting

                                container authentication {
                                    presence "Enable the authentication context";
                                    description "Enable the authentication context";

                                    leaf udp-port {
                                        type types-sros:tcp-udp-port-non-zero;
                                        default "1812";
                                        description "ISA RADIUS server authentication UDP port";
                                    }

                                } // container authentication

                                container coa {
                                    presence "Enable the coa context";
                                    description "Enable the coa context";

                                    leaf udp-port {
                                        type types-sros:tcp-udp-port-non-zero;
                                        default "3799";
                                        description "ISA RADIUS server change of authorization UDP port";
                                    }

                                } // container coa

                            } // container purpose

                        } // list server

                    } // container servers

                } // list isa-policy

            } // container radius

            container diameter {
                description "Enter the diameter context";

                list node {
                    key "origin-host";
                    max-elements 32;
                    description "Enter the node list instance";

                    leaf origin-host {
                        type types-diam:diam-fqdn;
                        description "Origin-Host AVP";
                    }

                    leaf description {
                        type types-sros:description;
                        description "Text description";
                    }

                    leaf origin-realm {
                        type types-diam:diam-fqdn;
                        sros-ext:immutable;
                        description "Origin-realm name";
                    }

                    leaf python-policy {
                        type leafref {
                            path "../../../../python/python-policy/name";
                        }
                        description "Python policy for received or sent Diameter messages";
                    }

                    leaf router-instance {
                        type string;
                        default "Base";
                        description "Router in which this node connects to its peers";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container connection {
                        description "Enter the connection context";

                        leaf timer {
                            type types-sros:time-duration {
                                range "1..1000";
                            }
                            units "seconds";
                            default "30";
                            description "Wait time before attempting reconnection to peer";
                        }

                        container ipv4 {
                            description "Enter the ipv4 context";

                            leaf local-address {
                                type types-sros:ipv4-unicast-address;
                                description "Local address of IPv4 TCP peer connection";
                            }

                            leaf allow-connections {
                                type boolean;
                                default "false";
                                description "Listen on local address for incoming peer connections";
                            }

                        } // container ipv4

                        container ipv6 {
                            description "Enter the ipv6 context";

                            leaf local-address {
                                type types-sros:ipv6-unicast-address;
                                description "Local address of IPv6 TCP peer connection";
                            }

                            leaf allow-connections {
                                type boolean;
                                default "false";
                                description "Listen on local address for incoming peer connections";
                            }

                        } // container ipv6

                    } // container connection

                    list peer {
                        key "index";
                        max-elements 5;
                        description "Enter the peer list instance";

                        leaf index {
                            type uint32 {
                                range "1..5";
                            }
                            description "Index of peer within the node";
                        }

                        leaf admin-state {
                            type types-sros:admin-state;
                            default "disable";
                            description "Administrative state of the Diameter peer";
                        }

                        leaf address {
                            type types-sros:ip-unicast-address;
                            description "Diameter peer address";
                        }

                        leaf destination-host {
                            type types-diam:diam-fqdn;
                            sros-ext:immutable;
                            mandatory true;
                            description "Destination-Host AVP string for Diameter messages";
                        }

                        leaf connection-timer {
                            type types-sros:time-duration {
                                range "1..1000";
                            }
                            units "seconds";
                            description "Wait time before attempting reconnection to peer";
                        }

                        leaf preference {
                            type uint32 {
                                range "1..100";
                            }
                            default "50";
                            description "Preference of this peer, lower is more preferred";
                        }

                        leaf watchdog-timer {
                            type types-sros:time-duration {
                                range "1..1000";
                            }
                            units "seconds";
                            description "Time between consecutive watchdog messages";
                        }

                        leaf default-peer {
                            type boolean;
                            default "false";
                            description "Use the peer as default route for realm-based routing";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        list route {
                            key "index";
                            max-elements 15;
                            description "Enter the route list instance";

                            leaf index {
                                type uint32 {
                                    range "1..15";
                                }
                                description "Static Diameter route ID";
                            }

                            leaf realm {
                                type types-diam:diam-fqdn;
                                sros-ext:immutable;
                                mandatory true;
                                description "Destination realm reachable via the static route";
                            }

                            leaf application {
                                type enumeration {
                                    enum "nasreq"                       { value 1; }
                                    enum "gy"                           { value 4; }
                                    enum "gx"                           { value 16777238; }
                                }
                                sros-ext:immutable;
                                mandatory true;
                                description "Diameter application to which the route applies";
                            }

                            leaf preference {
                                type uint32 {
                                    range "1..100";
                                }
                                default "50";
                                description "Static route preference; lower value is preferred";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                        } // list route

                    } // list peer

                } // list node

                list peer-policy {
                    status deprecated;
                    key "name";
                    max-elements 32;
                    description "Enter the peer-policy list instance";

                    leaf name {
                        status deprecated;
                        type types-sros:named-item;
                        description "Diameter peer policy name";
                    }

                    leaf description {
                        status deprecated;
                        type types-sros:description;
                        description "Text description";
                    }

                    leaf origin-host {
                        status deprecated;
                        type string {
                            length "1..80";
                        }
                        description "Origin-Host AVP sent in all Diameter messages";
                    }

                    leaf origin-realm {
                        status deprecated;
                        type string {
                            length "1..80";
                        }
                        description "Origin-Realm AVP sent in all Diameter messages";
                    }

                    leaf router-instance {
                        status deprecated;
                        type string;
                        default "Base";
                        description "Diameter peer policy router";
                    }

                    leaf ipv4-source-address {
                        status deprecated;
                        type types-sros:ipv4-unicast-address;
                        description "IPv4 source address for peering connection";
                    }

                    leaf ipv6-source-address {
                        status deprecated;
                        type types-sros:ipv6-unicast-address;
                        description "IPv6 source address for IPv6-reachable peering";
                    }

                    leaf watchdog-timer {
                        status deprecated;
                        type types-sros:time-duration {
                            range "1..1000";
                        }
                        units "seconds";
                        default "30";
                        description "Time between consecutive watchdog messages";
                    }

                    leaf connection-timer {
                        status deprecated;
                        type types-sros:time-duration {
                            range "1..1000";
                        }
                        units "seconds";
                        default "30";
                        description "Wait time before attempting reconnection to peer";
                    }

                    leaf transaction-timer {
                        status deprecated;
                        type types-sros:time-duration {
                            range "1..1000";
                        }
                        units "seconds";
                        default "30";
                        description "Timeout for base Diameter messages (DWR, CER, DPR)";
                    }

                    leaf vendor-support {
                        status deprecated;
                        type types-diam:diam-vendor-support;
                        default "three-gpp";
                        description "Vendor support announced in the capability exchange";
                    }

                    leaf python-policy {
                        status deprecated;
                        type leafref {
                            path "../../../../python/python-policy/name";
                        }
                        description "Name of python policy for Diameter processing";
                    }

                    leaf role {
                        status deprecated;
                        type enumeration {
                            enum "client"                       { value 0; }
                            enum "proxy"                        { value 1; }
                        }
                        sros-ext:immutable;
                        default "client";
                        description "Client or proxy role of a Diameter peer policy";
                    }

                    leaf-list apply-groups {
                        status deprecated;
                        type leafref {
                            path "../../../../groups/group/name";
                        }
                        max-elements 8;
                        ordered-by user;
                        description "Apply a configuration group at this level";
                    }

                    leaf-list apply-groups-exclude {
                        status deprecated;
                        type leafref {
                            path "../../../../groups/group/name";
                        }
                        max-elements 8;
                        ordered-by user;
                        description "Exclude a configuration group at this level";
                    }

                    container applications {
                        status deprecated;
                        description "Enter the applications context";

                        leaf gx {
                            status deprecated;
                            type boolean;
                            default "false";
                            description "Advertise Gx application support in CER messages";
                        }

                        leaf gy {
                            status deprecated;
                            type boolean;
                            default "false";
                            description "Advertise Gy application support in CER messages";
                        }

                        leaf nasreq {
                            status deprecated;
                            type boolean;
                            default "false";
                            description "Advertise NASREQ application support in CER messages";
                        }

                    } // container applications

                    list peer {
                        status deprecated;
                        key "peer-name";
                        max-elements 5;
                        description "Enter the peer list instance";

                        leaf peer-name {
                            status deprecated;
                            type types-sros:named-item;
                            description "Diameter peer name";
                        }

                        leaf admin-state {
                            status deprecated;
                            type types-sros:admin-state;
                            default "disable";
                            description "Administrative state of the peer";
                        }

                        leaf address {
                            status deprecated;
                            type types-sros:ip-unicast-address;
                            description "Diameter peer address";
                        }

                        leaf destination-host {
                            status deprecated;
                            type types-sros:string-not-all-spaces {
                                length "1..80";
                            }
                            description "Destination-Host AVP string for Diameter messages";
                        }

                        leaf destination-realm {
                            status deprecated;
                            type types-sros:string-not-all-spaces {
                                length "1..80";
                            }
                            description "Destination-Realm AVP string";
                        }

                        leaf watchdog-timer {
                            status deprecated;
                            type types-sros:time-duration {
                                range "1..1000";
                            }
                            units "seconds";
                            description "Time between consecutive watchdog messages";
                        }

                        leaf connection-timer {
                            status deprecated;
                            type types-sros:time-duration {
                                range "1..1000";
                            }
                            units "seconds";
                            description "Wait time before attempting reconnection to peer";
                        }

                        leaf transaction-timer {
                            status deprecated;
                            type types-sros:time-duration {
                                range "1..1000";
                            }
                            units "seconds";
                            description "Timeout for base Diameter messages (DWR, CER, DPR)";
                        }

                        leaf preference {
                            status deprecated;
                            type uint32 {
                                range "1..100";
                            }
                            default "50";
                            description "Peer preference of the Diameter peer policy";
                        }

                        leaf-list apply-groups {
                            status deprecated;
                            type leafref {
                                path "../../../../../groups/group/name";
                            }
                            max-elements 8;
                            ordered-by user;
                            description "Apply a configuration group at this level";
                        }

                        leaf-list apply-groups-exclude {
                            status deprecated;
                            type leafref {
                                path "../../../../../groups/group/name";
                            }
                            max-elements 8;
                            ordered-by user;
                            description "Exclude a configuration group at this level";
                        }

                        container transport {
                            status deprecated;
                            description "Enter the transport context";

                            leaf port-number {
                                status deprecated;
                                type uint32 {
                                    range "1..65535";
                                }
                                default "3868";
                                description "Transport protocol port number used toward policy peer";
                            }

                        } // container transport

                        container statistics {
                            status deprecated;
                            description "Enter the statistics context";

                        } // container statistics

                    } // list peer

                    container proxy {
                        status deprecated;
                        when "../role = 'proxy'";
                        description "Enter the proxy context";

                        leaf admin-state {
                            status deprecated;
                            type types-sros:admin-state;
                            default "disable";
                            description "Administrative state of Diameter proxy";
                        }

                        leaf router-instance {
                            status deprecated;
                            type string;
                            description "Routing context associated with Diameter proxy";
                        }

                        leaf local-address {
                            status deprecated;
                            type types-sros:ip-unicast-address;
                            description "Source IP address on which Diameter proxy listens";
                        }

                        container mcs-peer {
                            status deprecated;
                            presence "Enable the mcs-peer context";
                            description "Enter the mcs-peer context";

                            leaf address {
                                status deprecated;
                                type leafref {
                                    path "../../../../../../redundancy/multi-chassis/peer/ip-address";
                                }
                                sros-ext:immutable;
                                mandatory true;
                                description "MCS peer address";
                            }

                            leaf sync-tag {
                                status deprecated;
                                type types-sros:named-item;
                                sros-ext:immutable;
                                mandatory true;
                                description "Synchronization tag shared by MCS peers";
                            }

                            leaf-list apply-groups {
                                status deprecated;
                                type leafref {
                                    path "../../../../../../groups/group/name";
                                }
                                max-elements 8;
                                ordered-by user;
                                description "Apply a configuration group at this level";
                            }

                            leaf-list apply-groups-exclude {
                                status deprecated;
                                type leafref {
                                    path "../../../../../../groups/group/name";
                                }
                                max-elements 8;
                                ordered-by user;
                                description "Exclude a configuration group at this level";
                            }

                        } // container mcs-peer

                    } // container proxy

                } // list peer-policy

            } // container diameter

            container wpp {
                description "Enter the wpp context";

                leaf system-name {
                    type string {
                        length "1..16";
                    }
                    description "System name used in WPP protocol messages";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list portal-group {
                    key "group-name";
                    description "Enter the portal-group list instance";

                    leaf group-name {
                        type types-sros:named-item;
                        description "Portal group name";
                    }

                    leaf description {
                        type types-sros:description;
                        description "Text description";
                    }

                    leaf admin-state {
                        type types-sros:admin-state;
                        default "disable";
                        description "Administrative state of the portal group";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list portal {
                        key "router-instance name";
                        max-elements 8;
                        description "Add a list entry for portal";

                        leaf router-instance {
                            type string;
                            description "Router on which the portal is configured";
                        }

                        leaf name {
                            type types-sros:named-item;
                            description "Web portal server name";
                        }

                    } // list portal

                } // list portal-group

            } // container wpp

        } // container aaa

    } // grouping conf-aaa

}
