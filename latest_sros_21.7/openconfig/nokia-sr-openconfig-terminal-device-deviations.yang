module nokia-sr-openconfig-terminal-device-deviations {

    namespace "urn:nokia.com:sros:ns:yang:sr:openconfig_terminal_device_deviations";

    prefix "nokia-sr-oc-opt-term-devs";

    import nokia-sros-yang-extensions     { prefix "sros-ext"; }
    import openconfig-extensions          { prefix "oc-ext"; }
    import openconfig-if-ethernet         { prefix "oc-eth"; }
    import openconfig-lldp                { prefix "oc-lldp"; }
    import openconfig-platform            { prefix "oc-platform"; }
    import openconfig-platform-transceiver { prefix "oc-transceiver"; }
    import openconfig-terminal-device     { prefix "oc-opt-term"; }
    import openconfig-transport-types     { prefix "oc-opt-types"; }
    import openconfig-types               { prefix "oc-types"; }
    import openconfig-yang-types          { prefix "oc-yang"; }

    sros-ext:sros-major-release "rel21";

    organization "Nokia";

    contact
        "Nokia SR OS Support
         Web: <http://www.nokia.com>";

    description
        "This module contains the list of deviations against the openconfig-terminal-device
          module for the Nokia SR OS based routers.

         Copyright 2016 Nokia. All rights reserved. Reproduction of this document
         is authorized on the condition that the foregoing copyright notice is included.

         This nokia-sr-openconfig-terminal-device-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-05-09";

    deviation /oc-opt-term:terminal-device {
        deviate not-supported;
    }

    deviation /oc-platform:components/oc-platform:component/oc-opt-term:optical-channel {
        deviate not-supported;
    }

}
