module nokia-sr-openconfig-igmp-deviations {

    namespace "urn:nokia.com:sros:ns:yang:sr:openconfig_igmp_deviations";

    prefix "nokia-sr-oc-igmp-devs";

    import nokia-sros-yang-extensions     { prefix "sros-ext"; }
    import openconfig-acl                 { prefix "oc-acl"; }
    import openconfig-extensions          { prefix "oc-ext"; }
    import openconfig-igmp                { prefix "oc-igmp"; }
    import openconfig-igmp-types          { prefix "oc-igmp-types"; }
    import openconfig-interfaces          { prefix "oc-if"; }
    import openconfig-network-instance    { prefix "oc-netinst"; }
    import openconfig-routing-policy      { prefix "oc-rpol"; }
    import openconfig-types               { prefix "oc-types"; }

    sros-ext:sros-major-release "rel21";

    organization "Nokia";

    contact
        "Nokia SR OS Support
         Web: <http://www.nokia.com>";

    description
        "This module contains the list of deviations against the openconfig-igmp
          module for the Nokia SR OS based routers.

         Copyright 2016 Nokia. All rights reserved. Reproduction of this document
         is authorized on the condition that the foregoing copyright notice is included.

         This nokia-sr-openconfig-igmp-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-07-09";

    deviation /oc-netinst:network-instances/oc-netinst:network-instance/oc-netinst:protocols/oc-netinst:protocol/oc-netinst:igmp/oc-netinst:global/oc-netinst:ssm/oc-netinst:mappings/oc-netinst:mapping/oc-netinst:config/oc-netinst:ssm-ranges {
        description
            "List of accepted source specific multicast (SSM) address
             ranges.";
        deviate replace {
            type leafref {
                path /oc-acl:acl/oc-acl:acl-sets/oc-acl:acl-set/oc-acl:config/oc-acl:name;
            }
        }
    }

    deviation /oc-netinst:network-instances/oc-netinst:network-instance/oc-netinst:protocols/oc-netinst:protocol/oc-netinst:igmp/oc-netinst:global/oc-netinst:ssm/oc-netinst:mappings/oc-netinst:mapping/oc-netinst:state/oc-netinst:ssm-ranges {
        description
            "List of accepted source specific multicast (SSM) address
             ranges.";
        deviate replace {
            type leafref {
                path /oc-acl:acl/oc-acl:acl-sets/oc-acl:acl-set/oc-acl:config/oc-acl:name;
            }
        }
    }

    deviation /oc-netinst:network-instances/oc-netinst:network-instance/oc-netinst:protocols/oc-netinst:protocol/oc-netinst:igmp/oc-netinst:interfaces/oc-netinst:interface/oc-netinst:config/oc-netinst:query-interval {
        deviate replace {
            type uint16 {
                range 11..1024;
            }
        }
    }

    deviation /oc-netinst:network-instances/oc-netinst:network-instance/oc-netinst:protocols/oc-netinst:protocol/oc-netinst:igmp/oc-netinst:interfaces/oc-netinst:interface/oc-netinst:config/oc-netinst:filter-prefixes {
        description "List used to filter joins.";
        deviate replace {
            type leafref {
                path /oc-rpol:routing-policy/oc-rpol:policy-definitions/oc-rpol:policy-definition/oc-rpol:name;
            }
        }
    }

    deviation /oc-netinst:network-instances/oc-netinst:network-instance/oc-netinst:protocols/oc-netinst:protocol/oc-netinst:igmp/oc-netinst:interfaces/oc-netinst:interface/oc-netinst:state/oc-netinst:query-expires {
        deviate add {
            units seconds;
        }
    }

    deviation /oc-netinst:network-instances/oc-netinst:network-instance/oc-netinst:protocols/oc-netinst:protocol/oc-netinst:igmp/oc-netinst:interfaces/oc-netinst:interface/oc-netinst:state/oc-netinst:query-interval {
        deviate replace {
            type uint16 {
                range 11..1024;
            }
        }
    }

    deviation /oc-netinst:network-instances/oc-netinst:network-instance/oc-netinst:protocols/oc-netinst:protocol/oc-netinst:igmp/oc-netinst:interfaces/oc-netinst:interface/oc-netinst:state/oc-netinst:filter-prefixes {
        description "List used to filter joins.";
        deviate replace {
            type leafref {
                path /oc-rpol:routing-policy/oc-rpol:policy-definitions/oc-rpol:policy-definition/oc-rpol:name;
            }
        }
    }

}
