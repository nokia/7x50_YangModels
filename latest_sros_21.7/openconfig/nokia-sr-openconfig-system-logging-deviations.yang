module nokia-sr-openconfig-system-logging-deviations {

    namespace "urn:nokia.com:sros:ns:yang:sr:openconfig_system_logging_deviations";

    prefix "nokia-sr-oc-sys-log-devs";

    import nokia-sros-yang-extensions     { prefix "sros-ext"; }
    import openconfig-extensions          { prefix "oc-ext"; }
    import openconfig-inet-types          { prefix "oc-inet"; }
    import openconfig-system              { prefix "oc-sys"; }
    import openconfig-system-logging      { prefix "oc-sys-log"; }
    import openconfig-yang-types          { prefix "oc-yang"; }

    sros-ext:sros-major-release "rel21";

    organization "Nokia";

    contact
        "Nokia SR OS Support
         Web: <http://www.nokia.com>";

    description
        "This module contains the list of deviations against the openconfig-system-logging
          module for the Nokia SR OS based routers.

         Copyright 2016 Nokia. All rights reserved. Reproduction of this document
         is authorized on the condition that the foregoing copyright notice is included.

         This nokia-sr-openconfig-system-logging-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2018-11-21";

    deviation /oc-sys:system/oc-sys:logging/oc-sys:console/oc-sys:selectors/oc-sys:selector/oc-sys:config/oc-sys:facility {
        description "Specifies the facility, or class of messages to log";
        deviate replace {
            type identityref {
                base oc-sys-log:SYSLOG_FACILITY;
            }
        }
    }

    deviation /oc-sys:system/oc-sys:logging/oc-sys:console/oc-sys:selectors/oc-sys:selector/oc-sys:state/oc-sys:facility {
        description "Specifies the facility, or class of messages to log";
        deviate replace {
            type identityref {
                base oc-sys-log:SYSLOG_FACILITY;
            }
        }
    }

    deviation /oc-sys:system/oc-sys:logging/oc-sys:console/oc-sys:selectors/oc-sys:selector {
        deviate add {
            max-elements 98;
        }
    }

    deviation /oc-sys:system/oc-sys:logging/oc-sys:remote-servers/oc-sys:remote-server/oc-sys:config/oc-sys:host {
        deviate replace {
            type oc-inet:ip-address;
        }
    }

    deviation /oc-sys:system/oc-sys:logging/oc-sys:remote-servers/oc-sys:remote-server/oc-sys:state/oc-sys:host {
        deviate replace {
            type oc-inet:ip-address;
        }
    }

    deviation /oc-sys:system/oc-sys:logging/oc-sys:remote-servers/oc-sys:remote-server/oc-sys:selectors/oc-sys:selector/oc-sys:config/oc-sys:facility {
        description "Specifies the facility, or class of messages to log";
        deviate replace {
            type identityref {
                base oc-sys-log:SYSLOG_FACILITY;
            }
        }
    }

    deviation /oc-sys:system/oc-sys:logging/oc-sys:remote-servers/oc-sys:remote-server/oc-sys:selectors/oc-sys:selector/oc-sys:state/oc-sys:facility {
        description "Specifies the facility, or class of messages to log";
        deviate replace {
            type identityref {
                base oc-sys-log:SYSLOG_FACILITY;
            }
        }
    }

    deviation /oc-sys:system/oc-sys:logging/oc-sys:remote-servers/oc-sys:remote-server/oc-sys:selectors/oc-sys:selector {
        deviate add {
            max-elements 98;
        }
    }

    deviation /oc-sys:system/oc-sys:logging/oc-sys:remote-servers/oc-sys:remote-server {
        deviate add {
            max-elements 10;
        }
    }

}
