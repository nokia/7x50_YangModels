submodule nokia-conf-router-msdp {

    yang-version "1.1";

    belongs-to nokia-conf { prefix "conf"; }

    import nokia-sros-yang-extensions     { prefix "sros-ext"; }
    import nokia-types-sros               { prefix "types-sros"; }

    include nokia-conf-groups;
    include nokia-conf-policy-options;


    sros-ext:sros-major-release "rel21";

    organization "Nokia";

    contact
        "Nokia SR OS Support
         Web: <http://www.nokia.com>";

    description
        "Nokia YANG Data model to configure  The Multicast Source Discovery Protocol (MSDP) is used to connect multicast routing domains. on SR OS based routers.

         Copyright 2016 Nokia. All rights reserved. Reproduction of this document
         is authorized on the condition that the foregoing copyright notice is included.

         This nokia-conf-router-msdp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-09-16";

    grouping conf-router-msdp {
        container msdp {
            when "../router-name = 'Base'";
            presence "Enable the msdp context";
            description "Enable the msdp context";

            leaf active-source-limit {
                type int32 {
                    range "0..1000000";
                }
                description "The maximum number of source active messages that will be accepted by MSDP";
            }

            leaf admin-state {
                type types-sros:admin-state;
                default "enable";
                description "Administrative state of MSDP";
            }

            leaf-list export-policy {
                type leafref {
                    path "../../../policy-options/policy-statement/name";
                }
                max-elements 5;
                ordered-by user;
                description "Policies to export Source Active state from the Source Active list into MSDP";
            }

            leaf-list import-policy {
                type leafref {
                    path "../../../policy-options/policy-statement/name";
                }
                max-elements 5;
                ordered-by user;
                description "Policies to import Source Active state from the Source Active list into MSDP";
            }

            leaf local-address {
                type types-sros:ipv4-unicast-address;
                description "The local end of an MSDP session.";
            }

            leaf data-encapsulation {
                type boolean;
                default "true";
                description "Enable/Disable encapsulation of multicast data used by MSDP";
            }

            leaf rpf-table {
                type enumeration {
                    enum "rtable-m"                     { value 0; }
                    enum "rtable-u"                     { value 1; }
                    enum "both"                         { value 2; }
                }
                default "rtable-u";
                description "The route table(s) for RPF lookup.";
            }

            leaf source-active-cache-lifetime {
                type uint32 {
                    range "90..600";
                }
                units "seconds";
                default "90";
                description "Lifetime given to SA cache entries when created or refreshed";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container receive-message-rate {
                description "Enter the receive-message-rate context";

                leaf rate {
                    type uint32 {
                        range "10..10000";
                    }
                    description "The number of MSDP messages (including source active messages) that are read from the TCP session per seconds";
                }

                leaf time {
                    type uint32 {
                        range "1..600";
                    }
                    units "seconds";
                    description "Specifies the time that together with number defines the rate of MSDP messages (including source active messages) that are read from the TCP session within the configured number of seconds.";
                }

                leaf threshold {
                    type uint32 {
                        range "1..1000000";
                    }
                    description "The number of MSDP messages that can be processed before rate is set";
                }

            } // container receive-message-rate

            list group {
                key "name";
                description "Enter the group list instance";

                leaf name {
                    type types-sros:named-item;
                    description "The peer group name";
                }

                leaf active-source-limit {
                    type int32 {
                        range "0..1000000";
                    }
                    description "The maximum number of source active messages that will be accepted by MSDP";
                }

                leaf admin-state {
                    type types-sros:admin-state;
                    default "enable";
                    description "Administrative state of MSDP";
                }

                leaf-list export-policy {
                    type leafref {
                        path "../../../../policy-options/policy-statement/name";
                    }
                    max-elements 5;
                    ordered-by user;
                    description "Policies to export Source Active state from the Source Active list into MSDP";
                }

                leaf-list import-policy {
                    type leafref {
                        path "../../../../policy-options/policy-statement/name";
                    }
                    max-elements 5;
                    ordered-by user;
                    description "Policies to import Source Active state from the Source Active list into MSDP";
                }

                leaf local-address {
                    type types-sros:ipv4-unicast-address;
                    description "The local end of an MSDP session.";
                }

                leaf mode {
                    type enumeration {
                        enum "standard"                     { value 1; }
                        enum "mesh-group"                   { value 2; }
                    }
                    default "standard";
                    description "Topology of groups of peers";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container receive-message-rate {
                    description "Enter the receive-message-rate context";

                    leaf rate {
                        type uint32 {
                            range "10..10000";
                        }
                        description "The number of MSDP messages (including source active messages) that are read from the TCP session per seconds";
                    }

                    leaf time {
                        type uint32 {
                            range "1..600";
                        }
                        units "seconds";
                        description "Specifies the time that together with number defines the rate of MSDP messages (including source active messages) that are read from the TCP session within the configured number of seconds.";
                    }

                    leaf threshold {
                        type uint32 {
                            range "1..1000000";
                        }
                        description "The number of MSDP messages that can be processed before rate is set";
                    }

                } // container receive-message-rate

                list peer {
                    key "ip-address";
                    description "Enter the peer list instance";

                    leaf ip-address {
                        type types-sros:ipv4-unicast-address;
                        description "The local end of an MSDP session";
                    }

                    leaf active-source-limit {
                        type int32 {
                            range "0..1000000";
                        }
                        description "The maximum number of source active messages that will be accepted by MSDP";
                    }

                    leaf admin-state {
                        type types-sros:admin-state;
                        default "enable";
                        description "Administrative state of MSDP";
                    }

                    leaf-list export-policy {
                        type leafref {
                            path "../../../../../policy-options/policy-statement/name";
                        }
                        max-elements 5;
                        ordered-by user;
                        description "Policies to export Source Active state from the Source Active list into MSDP";
                    }

                    leaf-list import-policy {
                        type leafref {
                            path "../../../../../policy-options/policy-statement/name";
                        }
                        max-elements 5;
                        ordered-by user;
                        description "Policies to import Source Active state from the Source Active list into MSDP";
                    }

                    leaf local-address {
                        type types-sros:ipv4-unicast-address;
                        description "The local end of an MSDP session.";
                    }

                    leaf default-peer {
                        type boolean;
                        default "false";
                        description "Enable/Disable default peer as MSDP peer";
                    }

                    leaf authentication-key {
                        type types-sros:encrypted-leaf {
                            length "1..370";
                        }
                        description "The authentication key to be used for a specific MSDP peer group peering session";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container receive-message-rate {
                        description "Enter the receive-message-rate context";

                        leaf rate {
                            type uint32 {
                                range "10..10000";
                            }
                            description "The number of MSDP messages (including source active messages) that are read from the TCP session per seconds";
                        }

                        leaf time {
                            type uint32 {
                                range "1..600";
                            }
                            units "seconds";
                            description "Specifies the time that together with number defines the rate of MSDP messages (including source active messages) that are read from the TCP session within the configured number of seconds.";
                        }

                        leaf threshold {
                            type uint32 {
                                range "1..1000000";
                            }
                            description "The number of MSDP messages that can be processed before rate is set";
                        }

                    } // container receive-message-rate

                } // list peer

            } // list group

            list peer {
                key "ip-address";
                description "Enter the peer list instance";

                leaf ip-address {
                    type types-sros:ipv4-unicast-address;
                    description "The local end of an MSDP session";
                }

                leaf active-source-limit {
                    type int32 {
                        range "0..1000000";
                    }
                    description "The maximum number of source active messages that will be accepted by MSDP";
                }

                leaf admin-state {
                    type types-sros:admin-state;
                    default "enable";
                    description "Administrative state of MSDP";
                }

                leaf-list export-policy {
                    type leafref {
                        path "../../../../policy-options/policy-statement/name";
                    }
                    max-elements 5;
                    ordered-by user;
                    description "Policies to export Source Active state from the Source Active list into MSDP";
                }

                leaf-list import-policy {
                    type leafref {
                        path "../../../../policy-options/policy-statement/name";
                    }
                    max-elements 5;
                    ordered-by user;
                    description "Policies to import Source Active state from the Source Active list into MSDP";
                }

                leaf local-address {
                    type types-sros:ipv4-unicast-address;
                    description "The local end of an MSDP session.";
                }

                leaf default-peer {
                    type boolean;
                    default "false";
                    description "Enable/Disable default peer as MSDP peer";
                }

                leaf authentication-key {
                    type types-sros:encrypted-leaf {
                        length "1..370";
                    }
                    description "The authentication key to be used for a specific MSDP peering session";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container receive-message-rate {
                    description "Enter the receive-message-rate context";

                    leaf rate {
                        type uint32 {
                            range "10..10000";
                        }
                        description "The number of MSDP messages (including source active messages) that are read from the TCP session per seconds";
                    }

                    leaf time {
                        type uint32 {
                            range "1..600";
                        }
                        units "seconds";
                        description "Specifies the time that together with number defines the rate of MSDP messages (including source active messages) that are read from the TCP session within the configured number of seconds.";
                    }

                    leaf threshold {
                        type uint32 {
                            range "1..1000000";
                        }
                        description "The number of MSDP messages that can be processed before rate is set";
                    }

                } // container receive-message-rate

            } // list peer

            list source {
                key "ip-prefix";
                description "Enter the source list instance";

                leaf ip-prefix {
                    type types-sros:ipv4-unicast-prefix;
                    description "The IP address of the sources from which the source active messages would be accepted";
                }

                leaf active-source-limit {
                    type int32 {
                        range "0..1000000";
                    }
                    description "The maximum number of source active messages that will be accepted by MSDP source";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list source

        } // container msdp

    } // grouping conf-router-msdp

}
