module nokia-sr-openconfig-keychain-deviations {

    namespace "urn:nokia.com:sros:ns:yang:sr:openconfig-keychain-deviations";

    prefix "nokia-oc-keychain-devs";

    import nokia-sros-yang-extensions     { prefix "sros-ext"; }
    import openconfig-keychain            { prefix "oc-keychain"; }

    sros-ext:sros-major-release "rel26";
    organization "Nokia";
    contact
        "Nokia SR OS Support
         Web: <http://www.nokia.com>";
    description
        "This module contains the list of deviations against the openconfig-keychain
         module for the Nokia SR OS based routers.

         Copyright 2016 Nokia. All rights reserved. Reproduction of this document
         is authorized on the condition that the foregoing copyright notice is included.

         This nokia-sr-openconfig-keychain-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    deviation /oc-keychain:keychains {
        deviate not-supported;
    }

}
