module nokia-sr-openconfig-qos-deviations {

    namespace "urn:nokia.com:sros:ns:yang:sr:openconfig-qos-deviations";

    prefix "nokia-oc-qos-devs";

    import nokia-sros-yang-extensions     { prefix "sros-ext"; }
    import openconfig-extensions          { prefix "oc-ext"; }
    import openconfig-interfaces          { prefix "oc-if"; }
    import openconfig-qos                 { prefix "oc-qos"; }

    sros-ext:sros-major-release "rel26";
    organization "Nokia";
    contact
        "Nokia SR OS Support
         Web: <http://www.nokia.com>";
    description
        "This module contains the list of deviations against the openconfig-qos
         module for the Nokia SR OS based routers.

         Copyright 2016 Nokia. All rights reserved. Reproduction of this document
         is authorized on the condition that the foregoing copyright notice is included.

         This nokia-sr-openconfig-qos-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    deviation /oc-qos:qos/oc-qos:config {
        deviate not-supported;
    }

    deviation /oc-qos:qos/oc-qos:interfaces/oc-qos:interface/oc-qos:interface-id {
        deviate replace {
            type oc-if:interface-id;
        }
    }

    deviation /oc-qos:qos/oc-qos:interfaces/oc-qos:interface/oc-qos:config {
        deviate not-supported;
    }

    deviation /oc-qos:qos/oc-qos:interfaces/oc-qos:interface/oc-qos:state/oc-qos:interface-id {
        deviate not-supported;
    }

    deviation /oc-qos:qos/oc-qos:interfaces/oc-qos:interface/oc-qos:interface-ref/oc-qos:config {
        deviate delete {
            oc-ext:telemetry-on-change;
        }
    }

    deviation /oc-qos:qos/oc-qos:interfaces/oc-qos:interface/oc-qos:input/oc-qos:config {
        deviate not-supported;
    }

    deviation /oc-qos:qos/oc-qos:interfaces/oc-qos:interface/oc-qos:input/oc-qos:state/oc-qos:buffer-allocation-profile {
        deviate not-supported;
    }

    deviation /oc-qos:qos/oc-qos:interfaces/oc-qos:interface/oc-qos:input/oc-qos:state/oc-qos:multicast-buffer-allocation-profile {
        deviate not-supported;
    }

    deviation /oc-qos:qos/oc-qos:interfaces/oc-qos:interface/oc-qos:input/oc-qos:state/oc-qos:unicast-buffer-allocation-profile {
        deviate not-supported;
    }

    deviation /oc-qos:qos/oc-qos:interfaces/oc-qos:interface/oc-qos:input/oc-qos:classifiers {
        deviate not-supported;
    }

    deviation /oc-qos:qos/oc-qos:interfaces/oc-qos:interface/oc-qos:input/oc-qos:queues/oc-qos:queue/oc-qos:name {
        deviate replace {
            type string;
        }
    }

    deviation /oc-qos:qos/oc-qos:interfaces/oc-qos:interface/oc-qos:input/oc-qos:queues/oc-qos:queue/oc-qos:config {
        deviate not-supported;
    }

    deviation /oc-qos:qos/oc-qos:interfaces/oc-qos:interface/oc-qos:input/oc-qos:queues/oc-qos:queue/oc-qos:state/oc-qos:name {
        deviate not-supported;
    }

    deviation /oc-qos:qos/oc-qos:interfaces/oc-qos:interface/oc-qos:input/oc-qos:queues/oc-qos:queue/oc-qos:state/oc-qos:queue-management-profile {
        deviate not-supported;
    }

    deviation /oc-qos:qos/oc-qos:interfaces/oc-qos:interface/oc-qos:input/oc-qos:queues/oc-qos:queue/oc-qos:state/oc-qos:max-queue-len {
        deviate not-supported;
    }

    deviation /oc-qos:qos/oc-qos:interfaces/oc-qos:interface/oc-qos:input/oc-qos:queues/oc-qos:queue/oc-qos:state/oc-qos:avg-queue-len {
        deviate not-supported;
    }

    deviation /oc-qos:qos/oc-qos:interfaces/oc-qos:interface/oc-qos:input/oc-qos:queues/oc-qos:queue/oc-qos:state/oc-qos:ecn-marked-pkts {
        deviate not-supported;
    }

    deviation /oc-qos:qos/oc-qos:interfaces/oc-qos:interface/oc-qos:input/oc-qos:queues/oc-qos:queue/oc-qos:state/oc-qos:ecn-marked-octets {
        deviate not-supported;
    }

    deviation /oc-qos:qos/oc-qos:interfaces/oc-qos:interface/oc-qos:input/oc-qos:queues/oc-qos:queue/oc-qos:state/oc-qos:ecn-selected-pkts {
        deviate not-supported;
    }

    deviation /oc-qos:qos/oc-qos:interfaces/oc-qos:interface/oc-qos:input/oc-qos:queues/oc-qos:queue/oc-qos:state/oc-qos:ecn-selected-octets {
        deviate not-supported;
    }

    deviation /oc-qos:qos/oc-qos:interfaces/oc-qos:interface/oc-qos:input/oc-qos:queues {
        deviate replace {
            config false;
        }
    }

    deviation /oc-qos:qos/oc-qos:interfaces/oc-qos:interface/oc-qos:input/oc-qos:scheduler-policy {
        deviate not-supported;
    }

    deviation /oc-qos:qos/oc-qos:interfaces/oc-qos:interface/oc-qos:input/oc-qos:virtual-output-queues {
        deviate not-supported;
    }

    deviation /oc-qos:qos/oc-qos:interfaces/oc-qos:interface/oc-qos:input {
        deviate replace {
            config false;
        }
    }

    deviation /oc-qos:qos/oc-qos:interfaces/oc-qos:interface/oc-qos:output/oc-qos:config {
        deviate not-supported;
    }

    deviation /oc-qos:qos/oc-qos:interfaces/oc-qos:interface/oc-qos:output/oc-qos:state/oc-qos:buffer-allocation-profile {
        deviate not-supported;
    }

    deviation /oc-qos:qos/oc-qos:interfaces/oc-qos:interface/oc-qos:output/oc-qos:state/oc-qos:multicast-buffer-allocation-profile {
        deviate not-supported;
    }

    deviation /oc-qos:qos/oc-qos:interfaces/oc-qos:interface/oc-qos:output/oc-qos:state/oc-qos:unicast-buffer-allocation-profile {
        deviate not-supported;
    }

    deviation /oc-qos:qos/oc-qos:interfaces/oc-qos:interface/oc-qos:output/oc-qos:classifiers {
        deviate not-supported;
    }

    deviation /oc-qos:qos/oc-qos:interfaces/oc-qos:interface/oc-qos:output/oc-qos:queues/oc-qos:queue/oc-qos:name {
        deviate replace {
            type string;
        }
    }

    deviation /oc-qos:qos/oc-qos:interfaces/oc-qos:interface/oc-qos:output/oc-qos:queues/oc-qos:queue/oc-qos:config {
        deviate not-supported;
    }

    deviation /oc-qos:qos/oc-qos:interfaces/oc-qos:interface/oc-qos:output/oc-qos:queues/oc-qos:queue/oc-qos:state/oc-qos:name {
        deviate not-supported;
    }

    deviation /oc-qos:qos/oc-qos:interfaces/oc-qos:interface/oc-qos:output/oc-qos:queues/oc-qos:queue/oc-qos:state/oc-qos:queue-management-profile {
        deviate not-supported;
    }

    deviation /oc-qos:qos/oc-qos:interfaces/oc-qos:interface/oc-qos:output/oc-qos:queues/oc-qos:queue/oc-qos:state/oc-qos:max-queue-len {
        deviate not-supported;
    }

    deviation /oc-qos:qos/oc-qos:interfaces/oc-qos:interface/oc-qos:output/oc-qos:queues/oc-qos:queue/oc-qos:state/oc-qos:avg-queue-len {
        deviate not-supported;
    }

    deviation /oc-qos:qos/oc-qos:interfaces/oc-qos:interface/oc-qos:output/oc-qos:queues/oc-qos:queue/oc-qos:state/oc-qos:ecn-marked-pkts {
        deviate not-supported;
    }

    deviation /oc-qos:qos/oc-qos:interfaces/oc-qos:interface/oc-qos:output/oc-qos:queues/oc-qos:queue/oc-qos:state/oc-qos:ecn-marked-octets {
        deviate not-supported;
    }

    deviation /oc-qos:qos/oc-qos:interfaces/oc-qos:interface/oc-qos:output/oc-qos:queues/oc-qos:queue/oc-qos:state/oc-qos:ecn-selected-pkts {
        deviate not-supported;
    }

    deviation /oc-qos:qos/oc-qos:interfaces/oc-qos:interface/oc-qos:output/oc-qos:queues/oc-qos:queue/oc-qos:state/oc-qos:ecn-selected-octets {
        deviate not-supported;
    }

    deviation /oc-qos:qos/oc-qos:interfaces/oc-qos:interface/oc-qos:output/oc-qos:queues {
        deviate replace {
            config false;
        }
    }

    deviation /oc-qos:qos/oc-qos:interfaces/oc-qos:interface/oc-qos:output/oc-qos:scheduler-policy {
        deviate not-supported;
    }

    deviation /oc-qos:qos/oc-qos:interfaces/oc-qos:interface/oc-qos:output {
        deviate replace {
            config false;
        }
    }

    deviation /oc-qos:qos/oc-qos:interfaces {
        deviate replace {
            config false;
        }
    }

    deviation /oc-qos:qos/oc-qos:classifiers {
        deviate not-supported;
    }

    deviation /oc-qos:qos/oc-qos:forwarding-groups {
        deviate not-supported;
    }

    deviation /oc-qos:qos/oc-qos:queues {
        deviate not-supported;
    }

    deviation /oc-qos:qos/oc-qos:scheduler-policies {
        deviate not-supported;
    }

    deviation /oc-qos:qos/oc-qos:buffer-allocation-profiles {
        deviate not-supported;
    }

    deviation /oc-qos:qos/oc-qos:queue-management-profiles {
        deviate not-supported;
    }


}
