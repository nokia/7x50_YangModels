module nokia-sr-openconfig-mpls-rsvp-deviations {

    namespace "urn:nokia.com:sros:ns:yang:sr:openconfig-mpls-rsvp-deviations";

    prefix "nokia-oc-rsvp-devs";

    import nokia-sros-yang-extensions     { prefix "sros-ext"; }
    import openconfig-network-instance    { prefix "oc-netinst"; }

    sros-ext:sros-major-release "rel26";
    organization "Nokia";
    contact
        "Nokia SR OS Support
         Web: <http://www.nokia.com>";
    description
        "This module contains the list of deviations against the openconfig-mpls-rsvp
         module for the Nokia SR OS based routers.

         Copyright 2016 Nokia. All rights reserved. Reproduction of this document
         is authorized on the condition that the foregoing copyright notice is included.

         This nokia-sr-openconfig-mpls-rsvp-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    deviation /oc-netinst:network-instances/oc-netinst:network-instance/oc-netinst:mpls/oc-netinst:signaling-protocols/oc-netinst:rsvp-te/oc-netinst:sessions/oc-netinst:session/oc-netinst:state/oc-netinst:sender-tspec {
        deviate not-supported;
    }

    deviation /oc-netinst:network-instances/oc-netinst:network-instance/oc-netinst:mpls/oc-netinst:signaling-protocols/oc-netinst:rsvp-te/oc-netinst:neighbors {
        deviate not-supported;
    }

    deviation /oc-netinst:network-instances/oc-netinst:network-instance/oc-netinst:mpls/oc-netinst:signaling-protocols/oc-netinst:rsvp-te/oc-netinst:global/oc-netinst:graceful-restart/oc-netinst:config/oc-netinst:restart-time {
        deviate replace {
            type uint32 {
                range "1..300";
            }
        }
    }

    deviation /oc-netinst:network-instances/oc-netinst:network-instance/oc-netinst:mpls/oc-netinst:signaling-protocols/oc-netinst:rsvp-te/oc-netinst:global/oc-netinst:graceful-restart/oc-netinst:config/oc-netinst:recovery-time {
        deviate replace {
            type uint32 {
                range "1..1800";
            }
        }
    }

    deviation /oc-netinst:network-instances/oc-netinst:network-instance/oc-netinst:mpls/oc-netinst:signaling-protocols/oc-netinst:rsvp-te/oc-netinst:global/oc-netinst:graceful-restart/oc-netinst:state/oc-netinst:restart-time {
        deviate replace {
            type uint32 {
                range "1..300";
            }
        }
    }

    deviation /oc-netinst:network-instances/oc-netinst:network-instance/oc-netinst:mpls/oc-netinst:signaling-protocols/oc-netinst:rsvp-te/oc-netinst:global/oc-netinst:graceful-restart/oc-netinst:state/oc-netinst:recovery-time {
        deviate replace {
            type uint32 {
                range "1..1800";
            }
        }
    }

    deviation /oc-netinst:network-instances/oc-netinst:network-instance/oc-netinst:mpls/oc-netinst:signaling-protocols/oc-netinst:rsvp-te/oc-netinst:global/oc-netinst:soft-preemption/oc-netinst:config/oc-netinst:soft-preemption-timeout {
        deviate replace {
            type uint16 {
                range "1..1800";
            }
        }
    }

    deviation /oc-netinst:network-instances/oc-netinst:network-instance/oc-netinst:mpls/oc-netinst:signaling-protocols/oc-netinst:rsvp-te/oc-netinst:global/oc-netinst:soft-preemption/oc-netinst:state/oc-netinst:soft-preemption-timeout {
        deviate replace {
            type uint16 {
                range "1..1800";
            }
        }
    }

    deviation /oc-netinst:network-instances/oc-netinst:network-instance/oc-netinst:mpls/oc-netinst:signaling-protocols/oc-netinst:rsvp-te/oc-netinst:global/oc-netinst:hellos {
        deviate not-supported;
    }

    deviation /oc-netinst:network-instances/oc-netinst:network-instance/oc-netinst:mpls/oc-netinst:signaling-protocols/oc-netinst:rsvp-te/oc-netinst:global/oc-netinst:state/oc-netinst:counters/oc-netinst:rate-limited-messages {
        deviate not-supported;
    }

    deviation /oc-netinst:network-instances/oc-netinst:network-instance/oc-netinst:mpls/oc-netinst:signaling-protocols/oc-netinst:rsvp-te/oc-netinst:interface-attributes/oc-netinst:interface/oc-netinst:bandwidth-reservations/oc-netinst:bandwidth-reservation/oc-netinst:state/oc-netinst:priority {
        deviate replace {
            type union {
                type uint8 {
                    range "0..7";
                }
            }
        }
    }

    deviation /oc-netinst:network-instances/oc-netinst:network-instance/oc-netinst:mpls/oc-netinst:signaling-protocols/oc-netinst:rsvp-te/oc-netinst:interface-attributes/oc-netinst:interface/oc-netinst:bandwidth-reservations/oc-netinst:bandwidth-reservation/oc-netinst:state/oc-netinst:active-reservations-count {
        deviate not-supported;
    }

    deviation /oc-netinst:network-instances/oc-netinst:network-instance/oc-netinst:mpls/oc-netinst:signaling-protocols/oc-netinst:rsvp-te/oc-netinst:interface-attributes/oc-netinst:interface/oc-netinst:bandwidth-reservations/oc-netinst:bandwidth-reservation/oc-netinst:state/oc-netinst:highwater-mark {
        deviate not-supported;
    }

    deviation /oc-netinst:network-instances/oc-netinst:network-instance/oc-netinst:mpls/oc-netinst:signaling-protocols/oc-netinst:rsvp-te/oc-netinst:interface-attributes/oc-netinst:interface/oc-netinst:authentication/oc-netinst:config/oc-netinst:authentication-key {
        deviate replace {
            type string {
                length "1..51";
                pattern "(.{1,16})|(.{1,44} hash)|(.{1,44} hash2)|(.{1,44} custom)";
            }
        }
    }

    deviation /oc-netinst:network-instances/oc-netinst:network-instance/oc-netinst:mpls/oc-netinst:signaling-protocols/oc-netinst:rsvp-te/oc-netinst:interface-attributes/oc-netinst:interface/oc-netinst:authentication/oc-netinst:state/oc-netinst:authentication-key {
        deviate replace {
            type string {
                length "1..51";
                pattern "(.{1,16})|(.{1,44} hash)|(.{1,44} hash2)|(.{1,44} custom)";
            }
        }
    }

    deviation /oc-netinst:network-instances/oc-netinst:network-instance/oc-netinst:mpls/oc-netinst:signaling-protocols/oc-netinst:rsvp-te/oc-netinst:interface-attributes/oc-netinst:interface/oc-netinst:protection {
        deviate not-supported;
    }

    deviation /oc-netinst:network-instances/oc-netinst:network-instance/oc-netinst:mpls/oc-netinst:signaling-protocols/oc-netinst:rsvp-te/oc-netinst:interface-attributes/oc-netinst:interface {
        deviate add {
            unique "oc-netinst:interface-ref/oc-netinst:config/oc-netinst:interface oc-netinst:interface-ref/oc-netinst:config/oc-netinst:subinterface";
        }
    }

}
