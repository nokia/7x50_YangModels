submodule nokia-conf-svc-vprn-grp-if-wlangw {

    yang-version "1.1";

    belongs-to nokia-conf { prefix "conf"; }

    import nokia-sros-yang-extensions     { prefix "sros-ext"; }
    import nokia-types-application-assurance { prefix "types-aa"; }
    import nokia-types-qos                { prefix "types-qos"; }
    import nokia-types-services           { prefix "types-services"; }
    import nokia-types-sros               { prefix "types-sros"; }
    import nokia-types-subscriber-mgmt    { prefix "types-submgt"; }
    import nokia-types-wlangw             { prefix "types-wlangw"; }

    include nokia-conf-aa-group;
    include nokia-conf-aaa;
    include nokia-conf-application-assurance;
    include nokia-conf-group-encryption;
    include nokia-conf-groups;
    include nokia-conf-isa;
    include nokia-conf-qos;
    include nokia-conf-redundancy;
    include nokia-conf-service;
    include nokia-conf-submgt-isa-filter;
    include nokia-conf-submgt-isa-policer;
    include nokia-conf-submgt-vrgw;
    include nokia-conf-subscriber-mgmt;
    include nokia-conf-svc-nat;
    include nokia-conf-svc-vpls;

    sros-ext:sros-major-release "rel26";
    organization "Nokia";
    contact
        "Nokia SR OS Support
         Web: <http://www.nokia.com>";
    description
        "Nokia YANG Data model to configure vprn service group interface WLAN Gateway on SR OS based routers.

         Copyright 2016 Nokia. All rights reserved. Reproduction of this document
         is authorized on the condition that the foregoing copyright notice is included.

         This nokia-conf-svc-vprn-grp-if-wlangw YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-05-27";

    grouping conf-svc-vprn-grp-if-wlangw-wlan-gw {
        container wlan-gw {
            when "../type = 'wlan-gw'" {
                description "only available in group-interfaces of type 'wlan-gw'";
            }
            description "Enter the wlan-gw context";

            leaf admin-state {
                type types-sros:admin-state;
                default "disable";
                description "Administrative state of WLAN Gateway";
            }

            leaf oper-down-on-group-degrade {
                type boolean;
                default "false";
                description "Bring interface down when the ISA WLAN Gateway degraded";
            }

            leaf tcp-mss-adjust {
                type uint32 {
                    range "160..10240";
                }
                units "bytes";
                description "TCP Maximum Segment Size (MSS) adjustment for gateway";
            }

            leaf wlan-gw-group {
                type leafref {
                    path "../../../../../../isa/wlan-gw-group/id";
                }
                sros-ext:auto-restart-to-modify;
                description "ID of WLAN Gateway ISA group that gateway binds to";
            }

            leaf gateway-router {
                type string;
                sros-ext:auto-restart-to-modify;
                description "Routing instance the WLAN-GW endpoint resides in";
            }

            leaf promiscuous-mode {
                type boolean;
                sros-ext:auto-restart-to-modify;
                default "false";
                description "Enable promiscuous mode for this group interface";
            }

            leaf-list apply-groups {
                type leafref {
                    path "../../../../../../groups/group/name";
                }
                max-elements 8;
                ordered-by user;
                description "Apply a configuration group at this level";
            }

            leaf-list apply-groups-exclude {
                type leafref {
                    path "../../../../../../groups/group/name";
                }
                max-elements 8;
                ordered-by user;
                description "Exclude a configuration group at this level";
            }

            container lanext {
                presence "Enable the lanext context";
                sros-ext:auto-restart-to-modify;
                description "Enable the lanext context";

                leaf max-bd {
                    type uint32 {
                        range "1..131071";
                    }
                    sros-ext:auto-restart-to-modify;
                    default "131071";
                    description "Maximum number of bridge domains";
                }

            } // container lanext

            container learn-ap-mac {
                presence "Enable the learn-ap-mac context";
                description "Enable the learn-ap-mac context";

                leaf delay-auth {
                    type boolean;
                    default "false";
                    description "Delay AP-MAC until after ARP/ND authentication response";
                }

            } // container learn-ap-mac

            container mobility {
                description "Enter the mobility context";

                leaf hold-time {
                    type types-sros:time-duration {
                        range "0..255";
                    }
                    units "seconds";
                    default "5";
                    description "Minimum time between two mobility events for single UE";
                }

                leaf inter-tunnel-type {
                    type boolean;
                    sros-ext:auto-restart-to-modify;
                    default "false";
                    description "Enable mobility between terminating tunnel types";
                }

                leaf inter-vlan {
                    type boolean;
                    default "false";
                    description "Allow mobility within different VLANs of the same range";
                }

                container trigger {
                    description "Enter the trigger context";

                    leaf data {
                        type boolean;
                        default "false";
                        description "Use data traffic as mobility trigger";
                    }

                    leaf iapp {
                        type boolean;
                        default "false";
                        description "Use IAPP messages as a mobility trigger";
                    }

                    leaf control {
                        type boolean;
                        default "false";
                        description "Use control traffic as a mobility trigger";
                    }

                } // container trigger

            } // container mobility

            container tunnel-egress-qos {
                description "Enter the tunnel-egress-qos context";

                leaf admin-state {
                    type types-sros:admin-state;
                    sros-ext:auto-restart-to-modify;
                    default "disable";
                    description "Administrative state of egress QoS for WLAN-GW tunnels";
                }

                leaf agg-rate-limit {
                    type types-qos:pir-rate-override;
                    default "max";
                    description "HQoS aggregate rate limit";
                }

                leaf granularity {
                    type types-wlangw:shaping-granularity;
                    sros-ext:auto-restart-to-modify;
                    default "per-tunnel";
                    description "Granularity of the egress shaping for WLAN Gateway";
                }

                leaf hold-time {
                    type union {
                        type types-sros:time-duration {
                            range "1..86400";
                        }
                        type enumeration {
                            enum infinite                       { value -1; }
                        }
                    }
                    units "seconds";
                    description "Minimum time to hold egress shaping resources";
                }

                leaf multi-client-only {
                    type boolean;
                    default "false";
                    description "Allow shaping for tunnel traffic for multiple UEs";
                }

                leaf qos {
                    type leafref {
                        path "../../../../../../../qos/sap-egress/sap-egress-policy-name";
                    }
                    sros-ext:auto-restart-to-modify;
                    description "Egress QoS policy linked with each interface tunnel";
                }

                leaf scheduler-policy {
                    type leafref {
                        path "../../../../../../../qos/scheduler-policy/scheduler-policy-name";
                    }
                    sros-ext:auto-restart-to-modify;
                    description "Egress scheduler policy linked with each tunnel";
                }

            } // container tunnel-egress-qos

            container tunnel-encaps {
                description "Enter the tunnel-encaps context";

                leaf learn-l2tp-cookie {
                    type union {
                        type enumeration {
                            enum never {
                                value 2;
                                description "Never interpret the cookie";
                            }
                            enum always {
                                value 3;
                                description "Interpret cookie regardless of first two octets value";
                            }
                        }
                        type types-sros:hex-string {
                            length "6";
                        }
                    }
                    default "never";
                    description "System that learns the cookie from L2TP tunnels terminating on this interface";
                }

            } // container tunnel-encaps

            container group-encryption {
                description "Enter the group-encryption context";

                leaf encryption-keygroup-inbound {
                    type leafref {
                        path "../../../../../../../group-encryption/encryption-keygroup/id";
                    }
                    description "Encryption keygroup for inbound traffic";
                }

                leaf encryption-keygroup-outbound {
                    type leafref {
                        path "../../../../../../../group-encryption/encryption-keygroup/id";
                    }
                    description "Encryption keygroup for inbound traffic";
                }

            } // container group-encryption

            container mcs-peer {
                presence "Enable the mcs-peer context";
                description "Enable the mcs-peer context";

                leaf address {
                    type leafref {
                        path "../../../../../../../redundancy/multi-chassis/peer/ip-address";
                    }
                    sros-ext:immutable;
                    sros-ext:auto-restart-to-modify;
                    mandatory true;
                    description "IP address of the MCS peer";
                }

                leaf sync-tag {
                    type types-sros:named-item;
                    sros-ext:immutable;
                    sros-ext:auto-restart-to-modify;
                    mandatory true;
                    description "Synchronization tag shared by MCS peers";
                }

            } // container mcs-peer

            container l2-ap {
                description "Enter the l2-ap context";

                leaf auto-sub-id-fmt {
                    type enumeration {
                        enum include-ap-tags                { value 0; }
                        enum sap-only                       { value 1; }
                    }
                    default "include-ap-tags";
                    description "Format of the auto-generated subscriber ID";
                }

                leaf default-encap-type {
                    type enumeration {
                        enum null                           { value 1; }
                        enum dot1q                          { value 2; }
                        enum qinq                           { value 10; }
                    }
                    sros-ext:auto-restart-to-modify;
                    default "null";
                    description "Default encapsulation type for Layer 2 access points";
                }

                list access-point {
                    key "sap-id";
                    description "Enter the access-point list instance";

                    leaf sap-id {
                        type types-sros:sap;
                        description "SAP ID for the Layer 2 access point";
                    }

                    leaf admin-state {
                        type types-sros:admin-state;
                        default "disable";
                        description "Administrative state of the L2 access points";
                    }

                    leaf encap-type {
                        type enumeration {
                            enum null                           { value 1; }
                            enum dot1q                          { value 2; }
                            enum qinq                           { value 10; }
                        }
                        sros-ext:auto-restart-to-modify;
                        description "Service encapsulation type of this access point";
                    }

                    leaf epipe-sap-template {
                        type leafref {
                            path "../../../../../../../template/epipe-sap-template/name";
                        }
                        sros-ext:auto-restart-to-modify;
                        description "Parameters template for the L2 access point SAP";
                    }

                    leaf-list apply-groups {
                        type leafref {
                            path "../../../../../../../../groups/group/name";
                        }
                        max-elements 8;
                        ordered-by user;
                        description "Apply a configuration group at this level";
                    }

                    leaf-list apply-groups-exclude {
                        type leafref {
                            path "../../../../../../../../groups/group/name";
                        }
                        max-elements 8;
                        ordered-by user;
                        description "Exclude a configuration group at this level";
                    }

                } // list access-point

            } // container l2-ap

            list gateway-address {
                key "address";
                max-elements 10;
                description "Enter the gateway-address list instance";

                leaf address {
                    type types-sros:ip-unicast-without-local-address;
                    description "Gateway endpoint address of the WLAN Gateway tunnel";
                }

                leaf-list apply-groups {
                    type leafref {
                        path "../../../../../../../groups/group/name";
                    }
                    max-elements 8;
                    ordered-by user;
                    description "Apply a configuration group at this level";
                }

                leaf-list apply-groups-exclude {
                    type leafref {
                        path "../../../../../../../groups/group/name";
                    }
                    max-elements 8;
                    ordered-by user;
                    description "Exclude a configuration group at this level";
                }

                container purpose {
                    description "Enter the purpose context";

                    leaf xconnect {
                        type boolean;
                        default "false";
                        description "Use tunnel IP address for crosse-connect traffic";
                    }

                } // container purpose

            } // list gateway-address

            list vlan-range {
                key "range";
                description "Enter the vlan-range list instance";

                leaf range {
                    type string {
                        pattern "((([0-9]|[1-9][0-9]{1,2}|[1-3][0-9]{3}|40[0-8][0-9]|409[0-5]))(\\.\\.(([0-9]|[1-9][0-9]{1,2}|[1-3][0-9]{3}|40[0-8][0-9]|409[0-5])))?)|(unmatched)";
                    }
                    description "IEEE 802.1q VLAN tag range";
                }

                leaf dynamic-service {
                    type boolean;
                    default "false";
                    description "Dynamically assign WLAN-GW subscriber to a VPLS service";
                }

                leaf http-redirect-policy {
                    type leafref {
                        path "../../../../../../../subscriber-mgmt/http-redirect-policy/name";
                    }
                    description "Default HTTP redirect policy for portal authentication";
                }

                leaf idle-timeout-action {
                    type types-wlangw:idle-timeout-action;
                    default "remove";
                    description "Action to perform when the idle timeout expires";
                }

                leaf nat-policy {
                    type leafref {
                        path "../../../../../../nat/nat-policy/name";
                    }
                    description "NAT policy for DSM and ISA portal authentication";
                }

                leaf retail-service {
                    type types-services:service-name;
                    description "Default retail service for new UEs in this range";
                }

                leaf-list apply-groups {
                    type leafref {
                        path "../../../../../../../groups/group/name";
                    }
                    max-elements 8;
                    ordered-by user;
                    description "Apply a configuration group at this level";
                }

                leaf-list apply-groups-exclude {
                    type leafref {
                        path "../../../../../../../groups/group/name";
                    }
                    max-elements 8;
                    ordered-by user;
                    description "Exclude a configuration group at this level";
                }

                container authentication {
                    description "Enter the authentication context";

                    leaf hold-time {
                        type types-sros:time-duration {
                            range "0..3600";
                        }
                        units "seconds";
                        default "5";
                        description "Minimum time UE held down after failed authentication";
                    }

                    leaf on-control-plane {
                        type boolean;
                        default "false";
                        description "Allow authentication on first control plane packet";
                    }

                    leaf policy {
                        type leafref {
                            path "../../../../../../../../aaa/radius/isa-policy/name";
                        }
                        description "RADIUS policy for authentication";
                    }

                    leaf vlan-mismatch-timeout {
                        type types-sros:time-duration {
                            range "5..60";
                        }
                        units "seconds";
                        description "Timeout if packet received with a non-matching VLAN tag";
                    }

                    container local {
                        presence "Enable the local context";
                        description "Enable the local context";

                        leaf coa-policy {
                            type leafref {
                                path "../../../../../../../../../aaa/radius/isa-policy/name";
                            }
                            description "RADIUS ISA policy applied to CoA or disconnect messages";
                        }

                        leaf default-ue-state {
                            type enumeration {
                                enum portal {
                                    value 1;
                                    description "Portal redirect UE using the http-redirect-policy";
                                }
                                enum dsm {
                                    value 2;
                                    description "DSM UE using DSM parameters";
                                }
                            }
                            mandatory true;
                            description "UE state accepted for immediate authentication";
                        }

                    } // container local

                } // container authentication

                container data-triggered-ue-creation {
                    description "Enter the data-triggered-ue-creation context";

                    leaf arp {
                        type boolean;
                        default "false";
                        description "Authenticate ARP packets received from an unknown UE";
                    }

                    leaf ospf {
                        type boolean;
                        default "false";
                        description "Authenticate OSPF packets received from an unknown UE";
                    }

                    leaf admin-state {
                        type types-sros:admin-state;
                        default "disable";
                        description "Administrative state of data-triggered UE creation";
                    }

                    container create-proxy-cache-entry {
                        description "Enter the create-proxy-cache-entry context";

                        leaf mac-format {
                            type types-submgt:mac-specification;
                            default "aa:";
                            description "MAC address format";
                        }

                        container proxy-server {
                            presence "Enable the proxy-server context";
                            description "Enable the proxy-server context";

                            leaf router-instance {
                                type string;
                                mandatory true;
                                description "Router instance of the RADIUS proxy server";
                            }

                            leaf name {
                                type types-sros:named-item;
                                mandatory true;
                                description "RADIUS Proxy server name";
                            }

                        } // container proxy-server

                    } // container create-proxy-cache-entry

                } // container data-triggered-ue-creation

                container l2-service {
                    presence "Enable the l2-service context";
                    description "Enable the l2-service context";

                    leaf admin-state {
                        type types-sros:admin-state;
                        default "disable";
                        description "Administrative state of Layer 2 service for VLAN range";
                    }

                    leaf description {
                        type types-sros:description;
                        description "Text description";
                    }

                    leaf service {
                        type leafref {
                            path "../../../../../../../vpls/service-name";
                        }
                        mandatory true;
                        description "Layer 2 service associated with the range";
                    }

                } // container l2-service

                container dhcp4 {
                    description "Enter the dhcp4 context";

                    leaf admin-state {
                        type types-sros:admin-state;
                        default "disable";
                        description "Administrative state of DHCPv4";
                    }

                    leaf l2-aware-ip-address {
                        type union {
                            type types-sros:ipv4-unicast-address;
                            type enumeration {
                                enum from-pool {
                                    value 0;
                                    description "IP address allocated from a pool";
                                }
                            }
                        }
                        description "L2-Aware NAT inside IP address";
                    }

                    leaf-list dns {
                        type types-sros:ipv4-unicast-address;
                        max-elements 2;
                        ordered-by user;
                        description "DNS servers signaled in DHCP";
                    }

                    leaf-list nbns {
                        type types-sros:ipv4-unicast-address;
                        max-elements 2;
                        ordered-by user;
                        description "NetBIOS servers signaled in DHCP";
                    }

                    container lease-time {
                        description "Enter the lease-time context";

                        leaf active {
                            type types-sros:time-duration {
                                range "300..3600";
                            }
                            units "seconds";
                            default "600";
                            description "Lease time an authenticated user";
                        }

                        leaf initial {
                            type types-sros:time-duration {
                                range "300..3600";
                            }
                            units "seconds";
                            default "600";
                            description "Lease time for migrant user (unauthenticated)";
                        }

                    } // container lease-time

                } // container dhcp4

                container dhcp6 {
                    description "Enter the dhcp6 context";

                    leaf admin-state {
                        type types-sros:admin-state;
                        default "disable";
                        description "Administrative state of the protocol";
                    }

                    leaf-list apply-groups {
                        type leafref {
                            path "../../../../../../../../groups/group/name";
                        }
                        max-elements 8;
                        ordered-by user;
                        description "Apply a configuration group at this level";
                    }

                    leaf-list apply-groups-exclude {
                        type leafref {
                            path "../../../../../../../../groups/group/name";
                        }
                        max-elements 8;
                        ordered-by user;
                        description "Exclude a configuration group at this level";
                    }

                    container preferred-lifetime {
                        description "Enter the preferred-lifetime context";

                        leaf active {
                            type types-sros:time-duration {
                                range "300..3600";
                            }
                            units "seconds";
                            default "600";
                            description "Preferred signaled lifetime after full authentication";
                        }

                        leaf initial {
                            type types-sros:time-duration {
                                range "300..3600";
                            }
                            units "seconds";
                            default "300";
                            description "Signaled preferred lifetime after full authentication";
                        }

                    } // container preferred-lifetime

                    container valid-lifetime {
                        description "Enter the valid-lifetime context";

                        leaf active {
                            type types-sros:time-duration {
                                range "300..3600";
                            }
                            units "seconds";
                            default "600";
                            description "Signaled valid lifetime after full authentication";
                        }

                        leaf initial {
                            type types-sros:time-duration {
                                range "300..3600";
                            }
                            units "seconds";
                            default "300";
                            description "Valid signaled lifetime UE is not fully authenticated";
                        }

                    } // container valid-lifetime

                } // container dhcp6

                container slaac {
                    description "Enter the slaac context";

                    leaf admin-state {
                        type types-sros:admin-state;
                        default "disable";
                        description "Administrative state of the protocol";
                    }

                    leaf-list apply-groups {
                        type leafref {
                            path "../../../../../../../../groups/group/name";
                        }
                        max-elements 8;
                        ordered-by user;
                        description "Apply a configuration group at this level";
                    }

                    leaf-list apply-groups-exclude {
                        type leafref {
                            path "../../../../../../../../groups/group/name";
                        }
                        max-elements 8;
                        ordered-by user;
                        description "Exclude a configuration group at this level";
                    }

                    container preferred-lifetime {
                        description "Enter the preferred-lifetime context";

                        leaf active {
                            type types-sros:time-duration {
                                range "300..3600";
                            }
                            units "seconds";
                            default "600";
                            description "Preferred signaled lifetime after full authentication";
                        }

                        leaf initial {
                            type types-sros:time-duration {
                                range "300..3600";
                            }
                            units "seconds";
                            default "300";
                            description "Signaled preferred lifetime after full authentication";
                        }

                    } // container preferred-lifetime

                    container valid-lifetime {
                        description "Enter the valid-lifetime context";

                        leaf active {
                            type types-sros:time-duration {
                                range "300..3600";
                            }
                            units "seconds";
                            default "600";
                            description "Signaled valid lifetime after full authentication";
                        }

                        leaf initial {
                            type types-sros:time-duration {
                                range "300..3600";
                            }
                            units "seconds";
                            default "300";
                            description "Valid signaled lifetime UE is not fully authenticated";
                        }

                    } // container valid-lifetime

                } // container slaac

                container dsm {
                    description "Enter the dsm context";

                    leaf admin-state {
                        type types-sros:admin-state;
                        default "disable";
                        description "Administrative state of DSM";
                    }

                    leaf accounting-policy {
                        type leafref {
                            path "../../../../../../../../aaa/radius/isa-policy/name";
                        }
                        sros-ext:auto-restart-to-modify;
                        description "ISA Radius Policy for accounting";
                    }

                    leaf send-unrestricted-portal-url {
                        type boolean;
                        default "false";
                        description "Send an indicator if no captive portal is enabled";
                    }

                    leaf captive-portal-api-url {
                        type types-wlangw:one-time-http-redirect-url;
                        description "Captive portal URL";
                    }

                    leaf volume-quota-direction {
                        type enumeration {
                            enum both {
                                value 0;
                                description "Both directions";
                            }
                            enum ingress {
                                value 1;
                                description "Ingress direction (upstream)";
                            }
                            enum egress {
                                value 2;
                                description "Egress direction (downstream)";
                            }
                        }
                        default "both";
                        description "Volume quota direction for WLAN GW";
                    }

                    leaf-list apply-groups {
                        type leafref {
                            path "../../../../../../../../groups/group/name";
                        }
                        max-elements 8;
                        ordered-by user;
                        description "Apply a configuration group at this level";
                    }

                    leaf-list apply-groups-exclude {
                        type leafref {
                            path "../../../../../../../../groups/group/name";
                        }
                        max-elements 8;
                        ordered-by user;
                        description "Exclude a configuration group at this level";
                    }

                    container application-assurance {
                        description "Enter the application-assurance context";

                        leaf profile {
                            type leafref {
                                path "../../../../../../../../../application-assurance/group/partition/policy/app-profile/app-profile-name";
                            }
                            description "AA application profile used for portal authentication";
                        }

                        leaf accounting-statistics {
                            type boolean;
                            default "false";
                            description "Collect AA statistics";
                        }

                        leaf url-parameter {
                            type types-aa:aa-http-url-param;
                            description "AA URL parameter included for HTTP portal redirect";
                        }

                    } // container application-assurance

                    container accounting-update {
                        presence "Enable the accounting-update context";
                        description "Enable the accounting-update context";

                        leaf interval {
                            type uint32 {
                                range "5..259200";
                            }
                            units "minutes";
                            mandatory true;
                            description "Interim accounting update messages interval";
                        }

                    } // container accounting-update


                    container ingress {
                        description "Enter the ingress context";

                        leaf policer {
                            type leafref {
                                path "../../../../../../../../../subscriber-mgmt/isa-policer/name";
                            }
                            description "Policer for ingress traffic";
                        }

                        leaf ip-filter {
                            type leafref {
                                path "../../../../../../../../../subscriber-mgmt/isa-filter/name";
                            }
                            description "Filter for ingress traffic";
                        }

                        leaf soft-quota-exhausted-filter {
                            type leafref {
                                path "../../../../../../../../../subscriber-mgmt/isa-filter/name";
                            }
                            description "Filter applied when soft volume quota is reached";
                        }

                    } // container ingress

                    container egress {
                        description "Enter the egress context";

                        leaf policer {
                            type leafref {
                                path "../../../../../../../../../subscriber-mgmt/isa-policer/name";
                            }
                            description "Policer for egress traffic";
                        }

                    } // container egress

                    container one-time-redirect {
                        description "Enter the one-time-redirect context";

                        leaf url {
                            type types-wlangw:one-time-http-redirect-url;
                            description "URL for redirected HTTP protocol packets";
                        }

                        leaf port {
                            type uint32 {
                                range "1..65535";
                            }
                            default "80";
                            description "Destination port of packets for HTTP redirect";
                        }

                    } // container one-time-redirect

                } // container dsm

                list extension {
                    key "extension-range";
                    description "Add a list entry for extension";

                    leaf extension-range {
                        type string {
                            pattern "(([0-9]|[1-9][0-9]{1,2}|[1-3][0-9]{3}|40[0-8][0-9]|409[0-5]))(\\.\\.(([0-9]|[1-9][0-9]{1,2}|[1-3][0-9]{3}|40[0-8][0-9]|409[0-5])))?";
                        }
                        description "VLAN tag range used for matching";
                    }

                } // list extension

                container vrgw {
                    description "Enter the vrgw context";

                    leaf admin-state {
                        type types-sros:admin-state;
                        default "disable";
                        description "Administrative state of vRGW";
                    }

                    leaf-list apply-groups {
                        type leafref {
                            path "../../../../../../../../groups/group/name";
                        }
                        max-elements 8;
                        ordered-by user;
                        description "Apply a configuration group at this level";
                    }

                    leaf-list apply-groups-exclude {
                        type leafref {
                            path "../../../../../../../../groups/group/name";
                        }
                        max-elements 8;
                        ordered-by user;
                        description "Exclude a configuration group at this level";
                    }

                    container brg {
                        description "Enter the brg context";

                        leaf default-brg-profile {
                            type leafref {
                                path "../../../../../../../../../subscriber-mgmt/vrgw/brg-profile/brg-profile-name";
                            }
                            sros-ext:auto-restart-to-modify;
                            description "Default BRG profile to use if the AAA server does not specify one";
                        }

                        leaf authenticated-brg-only {
                            type boolean;
                            sros-ext:auto-restart-to-modify;
                            default "false";
                            description "Only allow hosts from BRGs pre-authenticated using the radius-proxy";
                        }

                    } // container brg

                    container lanext {
                        description "Enter the lanext context";

                        leaf admin-state {
                            type types-sros:admin-state;
                            default "disable";
                            description "Administrative state of HLE";
                        }

                        leaf assistive-address-resolution {
                            type boolean;
                            sros-ext:auto-restart-to-modify;
                            default "false";
                            description "ISA assists in address resolution";
                        }

                        leaf bd-mac-prefix {
                            type string {
                                length "8";
                                pattern "[0-9a-f][02468ace](:[0-9a-f]{2}){2}";
                            }
                            sros-ext:auto-restart-to-modify;
                            description "Prefix of the HLE BD MAC address";
                        }

                        leaf mac-translation {
                            type boolean;
                            sros-ext:auto-restart-to-modify;
                            default "false";
                            description "Allow MAC address translation for HLE services";
                        }

                        leaf-list apply-groups {
                            type leafref {
                                path "../../../../../../../../../groups/group/name";
                            }
                            max-elements 8;
                            ordered-by user;
                            sros-ext:auto-restart-to-modify;
                            description "Apply a configuration group at this level";
                        }

                        leaf-list apply-groups-exclude {
                            type leafref {
                                path "../../../../../../../../../groups/group/name";
                            }
                            max-elements 8;
                            ordered-by user;
                            sros-ext:auto-restart-to-modify;
                            description "Exclude a configuration group at this level";
                        }

                        container access {
                            sros-ext:auto-restart-to-modify;
                            description "Enter the access context";

                            leaf max-mac {
                                type uint32 {
                                    range "1..256";
                                }
                                sros-ext:auto-restart-to-modify;
                                default "20";
                                description "Maximum number of allowed MAC entries on access side";
                            }

                            leaf multi-access {
                                type boolean;
                                sros-ext:auto-restart-to-modify;
                                default "false";
                                description "Allow multiple access points";
                            }

                            leaf policer {
                                type leafref {
                                    path "../../../../../../../../../../subscriber-mgmt/isa-policer/name";
                                }
                                sros-ext:auto-restart-to-modify;
                                description "Policer for ingress home traffic";
                            }

                        } // container access

                        container network {
                            sros-ext:auto-restart-to-modify;
                            description "Enter the network context";

                            leaf admin-state {
                                type types-sros:admin-state;
                                sros-ext:auto-restart-to-modify;
                                default "enable";
                                description "Administrative state of the HLE network";
                            }

                            leaf max-mac {
                                type uint32 {
                                    range "1..64";
                                }
                                sros-ext:auto-restart-to-modify;
                                default "20";
                                description "Maximum number of allowed MAC entries on network side";
                            }

                            leaf policer {
                                type leafref {
                                    path "../../../../../../../../../../subscriber-mgmt/isa-policer/name";
                                }
                                sros-ext:auto-restart-to-modify;
                                description "Policer for ingress data center traffic";
                            }

                        } // container network


                    } // container lanext

                } // container vrgw

                container xconnect {
                    description "Enter the xconnect context";

                    leaf admin-state {
                        type types-sros:admin-state;
                        default "disable";
                        description "Administrative state of the cross-connect";
                    }

                    leaf-list apply-groups {
                        type leafref {
                            path "../../../../../../../../groups/group/name";
                        }
                        max-elements 8;
                        ordered-by user;
                        description "Apply a configuration group at this level";
                    }

                    leaf-list apply-groups-exclude {
                        type leafref {
                            path "../../../../../../../../groups/group/name";
                        }
                        max-elements 8;
                        ordered-by user;
                        description "Exclude a configuration group at this level";
                    }

                    container accounting {
                        description "Enter the accounting context";

                        leaf policy {
                            type leafref {
                                path "../../../../../../../../../aaa/radius/isa-policy/name";
                            }
                            sros-ext:auto-restart-to-modify;
                            description "ISA RADIUS accounting policy for cross-connected UEs";
                        }

                        leaf update-interval {
                            type types-sros:time-duration {
                                range "5..259200";
                            }
                            units "minutes";
                            description "Time between successive interim accounting updates";
                        }

                        leaf mobility-updates {
                            type boolean;
                            default "false";
                            description "Accounting updates triggered by mobility";
                        }

                    } // container accounting

                } // container xconnect

            } // list vlan-range

        } // container wlan-gw

    } // grouping conf-svc-vprn-grp-if-wlangw-wlan-gw

}
