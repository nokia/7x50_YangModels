submodule nokia-conf-submgt-gtp {

    yang-version "1.1";

    belongs-to nokia-conf { prefix "conf"; }

    import nokia-sros-yang-extensions     { prefix "sros-ext"; }
    import nokia-types-qos                { prefix "types-qos"; }
    import nokia-types-services           { prefix "types-services"; }
    import nokia-types-sros               { prefix "types-sros"; }

    include nokia-conf-groups;
    include nokia-conf-python;
    include nokia-conf-submgt-local-user-db;
    include nokia-conf-subscriber-mgmt;

    sros-ext:sros-major-release "rel26";
    organization "Nokia";
    contact
        "Nokia SR OS Support
         Web: <http://www.nokia.com>";
    description
        "Nokia YANG Data model to configure subscriber management gtp on SR OS based routers.

         Copyright 2016 Nokia. All rights reserved. Reproduction of this document
         is authorized on the condition that the foregoing copyright notice is included.

         This nokia-conf-submgt-gtp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-04-22";

    grouping conf-submgt-gtp {
        container gtp {
            description "Enter the gtp context";

            leaf gtp-u-ipv6-checksum {
                type enumeration {
                    enum false                          { value 0; }
                    enum true                           { value 1; }
                }
                default "false";
                description "UDP checksum for GTP-u packets transmitted over IPv6";
            }

            leaf max-held-uplink-sessions {
                type uint32 {
                    range "0..500000";
                }
                default "2000";
                description "Maximum GTP sessions held while UE is disconnected";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container serving-network {
                presence "Enable the serving-network context";
                description "Enable the serving-network context";

                leaf mcc {
                    type string {
                        length "3";
                        pattern "\\d{3}" {
                            error-message "mcc must be digits";
                        }
                    }
                    mandatory true;
                    description "Mobile Country Code (MCC) portion of serving network";
                }

                leaf mnc {
                    type string {
                        length "2..3";
                        pattern "\\d{2,3}" {
                            error-message "mnc must be digits";
                        }
                    }
                    mandatory true;
                    description "Mobile Network Code (MNC) portion of serving network";
                }

            } // container serving-network

            list apn-policy {
                key "name";
                max-elements 128;
                description "Enter the apn-policy list instance";

                leaf name {
                    type types-sros:named-item;
                    description "APN policy name for a new incoming GTP connection";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list apn {
                    key "apn-name";
                    max-elements 1024;
                    description "Enter the apn list instance";

                    leaf apn-name {
                        type string {
                            length "1..80";
                            pattern "([a-zA-Z0-9]+-+)*([a-zA-Z0-9]+\\.([a-zA-Z0-9]+-+)*)*[a-zA-Z0-9]+" {
                                error-message "wrong format of apn name";
                            }
                        }
                        description "GTP APN name";
                    }

                    leaf skip-gtp-ipv4-allocation {
                        type boolean;
                        default "false";
                        description "defer IPv4 address allocation to DHCP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    choice auth-policy {
                        case diameter {

                            leaf diameter-nasreq-policy {
                                type leafref {
                                    path "../../../../diameter-nasreq-policy/name";
                                }
                                description "NASREQ authentication policy name";
                            }

                        }
                        case radius {

                            leaf radius-auth-policy {
                                type leafref {
                                    path "../../../../radius-authentication-policy/name";
                                }
                                description "RADIUS authentication policy name";
                            }

                        }
                        case user-db {

                            leaf user-db {
                                type leafref {
                                    path "../../../../local-user-db/name";
                                }
                                description "Local user database name";
                            }

                        }
                    }
                    container ambr-qos-mapping {
                        description "Enter the ambr-qos-mapping context";

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container downlink {
                            presence "Enable the downlink context";
                            description "Enable the downlink context";

                            choice downlink {
                                mandatory true;
                                case aggregate-rate {

                                    leaf aggregate-rate {
                                        type empty;
                                        description "Map the downlink APN-AMBR rate to an aggregate rate";
                                    }

                                }
                                case arbiter {

                                    leaf arbiter {
                                        type types-sros:named-item;
                                        description "Name of arbiter to be overridden";
                                    }

                                }
                                case policer {

                                    leaf policer {
                                        type types-qos:sap-egress-policer-id;
                                        description "ID of policer to be overridden";
                                    }

                                }
                                case queue {

                                    leaf queue {
                                        type types-qos:egress-queue-id;
                                        description "Map the downlink APN-AMBR rate to a queue PIR override";
                                    }

                                }
                                case scheduler {

                                    leaf scheduler {
                                        type types-sros:named-item;
                                        description "Name of the scheduler to be overridden";
                                    }

                                }
                            }
                        } // container downlink

                        container uplink {
                            presence "Enable the uplink context";
                            description "Enable the uplink context";

                            choice uplink {
                                mandatory true;
                                case arbiter {

                                    leaf arbiter {
                                        type types-sros:named-item;
                                        description "Name of arbiter to be overridden";
                                    }

                                }
                                case policer {

                                    leaf policer {
                                        type types-qos:ingress-policer-id;
                                        description "Map the uplink APN-AMBR rate to a policer PIR override";
                                    }

                                }
                                case queue {

                                    leaf queue {
                                        type types-qos:ingress-queue-id;
                                        description "Map the uplink APN-AMBR rate to a queue PIR override";
                                    }

                                }
                                case scheduler {

                                    leaf scheduler {
                                        type types-sros:named-item;
                                        description "Name of scheduler to be overridden";
                                    }

                                }
                            }
                        } // container uplink

                    } // container ambr-qos-mapping

                    container defaults {
                        description "Enter the defaults context";

                        container group-interface {
                            presence "Enable the group-interface context";
                            description "Enable the group-interface context";

                            leaf svc-name {
                                type types-services:service-name;
                                mandatory true;
                                description "Service name where the group interface resides";
                            }

                            leaf name {
                                type types-sros:interface-name;
                                mandatory true;
                                description "Group interface name";
                            }

                        } // container group-interface

                    } // container defaults

                } // list apn

            } // list apn-policy

            list peer-profile {
                key "name";
                description "Enter the peer-profile list instance";

                leaf name {
                    type types-sros:named-item;
                    description "Peer profile name";
                }

                leaf description {
                    type types-sros:description;
                    description "Text description";
                }

                leaf interface-type {
                    type enumeration {
                        enum gn                             { value 1; }
                        enum s2a                            { value 2; }
                        enum s2b                            { value 3; }
                        enum s11                            { value 4; }
                    }
                    description "3GPP interface type for connections toward this peer";
                }

                leaf ip-ttl {
                    type uint8 {
                        range "1..255";
                    }
                    default "255";
                    description "IP header TTL value for GTP control messages";
                }

                leaf python-policy {
                    type leafref {
                        path "../../../../python/python-policy/name";
                    }
                    description "Python policy for MGW profile packets sent or received";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container keep-alive {
                    description "Enter the keep-alive context";

                    leaf admin-state {
                        type types-sros:admin-state;
                        default "enable";
                        description "Administrative state of GTP-C echo request messages";
                    }

                    leaf interval {
                        when "../admin-state = 'enable'" {
                            description "admin-state must be enabled";
                        }
                        type types-sros:time-duration {
                            range "60..180";
                        }
                        units "seconds";
                        default "60";
                        description "Frequency for sending keepalives";
                    }

                    leaf retry-count {
                        when "../admin-state = 'enable'" {
                            description "admin-state must be enabled";
                        }
                        type uint32 {
                            range "1..15";
                        }
                        default "4";
                        description "Time between echo retries toward the same peer";
                    }

                    leaf timeout {
                        when "../admin-state = 'enable'" {
                            description "admin-state must be enabled";
                        }
                        type uint32 {
                            range "1..20";
                        }
                        units "seconds";
                        default "5";
                        description "Timeout after which echo request is deemed unanswered";
                    }

                } // container keep-alive

                container message-retransmit {
                    description "Enter the message-retransmit context";

                    leaf timeout {
                        type uint32 {
                            range "1..30";
                        }
                        units "seconds";
                        default "5";
                        description "Timeout after which a message is considered unanswered";
                    }

                    leaf retry-count {
                        type uint32 {
                            range "1..8";
                        }
                        default "3";
                        description "Maximum unanswered retries before message deemed failed";
                    }

                } // container message-retransmit

                container s11 {
                    description "Enter the s11 context";

                    leaf ipv4-mtu {
                        type uint32 {
                            range "512..9000";
                        }
                        default "1400";
                        description "IPv4-MTU PCO sent in S11 GTP messages";
                    }

                    leaf end-marker-count {
                        type uint32 {
                            range "0..5";
                        }
                        default "1";
                        description "Number of GTP-U end marker packets that are sent";
                    }

                    leaf change-reporting-action {
                        type union {
                            type uint32 {
                                range "0..255";
                            }
                            type enumeration {
                                enum cgi-sai                        { value 1; }
                                enum rai                            { value 2; }
                                enum tai                            { value 3; }
                                enum ecgi                           { value 4; }
                                enum cgi-sai-rai                    { value 5; }
                                enum tai-ecgi                       { value 6; }
                            }
                        }
                        description "Value of change reporting action IE sends to the peer";
                    }

                    container qos {
                        description "Enter the qos context";

                        choice arp-qci-or-hss {
                            default "arp-qci";
                            case arp-qci {

                                leaf arp {
                                    type uint32 {
                                        range "1..15";
                                    }
                                    default "1";
                                    description "Allocation or retention priority";
                                }

                                leaf qci {
                                    type uint32 {
                                        range "1..255";
                                    }
                                    default "8";
                                    description "QoS Class Identifier (QCI) to send in GTP messages";
                                }

                            }
                        }
                        container ambr {
                            description "Enter the ambr context";

                            leaf down-link {
                                type int32 {
                                    range "0..10000000";
                                }
                                units "kilobps";
                                default "20000";
                                description "Downlink Aggregated Maximum Bit Rate (AMBR)";
                            }

                            leaf up-link {
                                type int32 {
                                    range "0..10000000";
                                }
                                units "kilobps";
                                default "10000";
                                description "Uplink Aggregated Maximum Bit Rate (AMBR)";
                            }

                        } // container ambr

                        container down-link {
                            description "Enter the down-link context";

                            leaf gbr {
                                type uint32 {
                                    range "0..100000";
                                }
                                units "kilobps";
                                default "0";
                                description "Guaranteed Bit Rate (GBR)";
                            }

                            leaf mbr {
                                type uint32 {
                                    range "0..100000";
                                }
                                units "kilobps";
                                default "0";
                                description "Maximum Bit Rate (MBR)";
                            }

                        } // container down-link

                        container up-link {
                            description "Enter the up-link context";

                            leaf gbr {
                                type uint32 {
                                    range "0..100000";
                                }
                                units "kilobps";
                                default "0";
                                description "Guaranteed Bit Rate (GBR)";
                            }

                            leaf mbr {
                                type uint32 {
                                    range "0..100000";
                                }
                                units "kilobps";
                                default "0";
                                description "Maximum Bit Rate (MBR)";
                            }

                        } // container up-link

                    } // container qos

                } // container s11

                container uplink {
                    description "Enter the uplink context";

                    leaf protocol-configuration-options {
                        type enumeration {
                            enum pco                            { value 1; }
                            enum apco                           { value 2; }
                        }
                        default "pco";
                        description "Information Element for Protocol Configuration Options";
                    }

                    leaf rat-type {
                        type union {
                            type uint32 {
                                range "0..255";
                            }
                            type enumeration {
                                enum utran                          { value 1; }
                                enum geran                          { value 2; }
                                enum wlan                           { value 3; }
                                enum gan                            { value 4; }
                                enum hspa                           { value 5; }
                                enum eutran                         { value 6; }
                                enum virtual                        { value 7; }
                            }
                        }
                        default "wlan";
                        description "Default Radio Access Type (RAT) signaled in GTP setup";
                    }

                    leaf report-wlan-location {
                        type boolean;
                        default "false";
                        description "Report WLAN or cellular location of UE during setup";
                    }

                    leaf session-hold-time {
                        type union {
                            type types-sros:time-duration {
                                range "0..3600";
                            }
                            type enumeration {
                                enum remaining-lease-time           { value -1; }
                            }
                        }
                        default "30";
                        description "Time to hold a GTP session after its UE is disconnected";
                    }

                    container charging-characteristics {
                        description "Enter the charging-characteristics context";

                        container home {
                            description "Enter the home context";

                            leaf bit0 {
                                type boolean;
                                default "false";
                                description "Set bit in charging characteristics information element";
                            }

                            leaf bit1 {
                                type boolean;
                                default "false";
                                description "Set bit in charging characteristics information element";
                            }

                            leaf bit2 {
                                type boolean;
                                default "false";
                                description "Set bit in charging characteristics information element";
                            }

                            leaf bit3 {
                                type boolean;
                                default "false";
                                description "Set bit in charging characteristics information element";
                            }

                            leaf bit4 {
                                type boolean;
                                default "false";
                                description "Set bit in charging characteristics information element";
                            }

                            leaf bit5 {
                                type boolean;
                                default "false";
                                description "Set bit in charging characteristics information element";
                            }

                            leaf bit6 {
                                type boolean;
                                default "false";
                                description "Set bit in charging characteristics information element";
                            }

                            leaf bit7 {
                                type boolean;
                                default "false";
                                description "Set bit in charging characteristics information element";
                            }

                            leaf bit8 {
                                type boolean;
                                default "false";
                                description "Set bit in charging characteristics information element";
                            }

                            leaf bit9 {
                                type boolean;
                                default "false";
                                description "Set bit in charging characteristics information element";
                            }

                            leaf bit10 {
                                type boolean;
                                default "false";
                                description "Set bit in charging characteristics information element";
                            }

                            leaf bit11 {
                                type boolean;
                                default "false";
                                description "Set bit in charging characteristics information element";
                            }

                            leaf bit12 {
                                type boolean;
                                default "false";
                                description "Set bit in charging characteristics information element";
                            }

                            leaf bit13 {
                                type boolean;
                                default "false";
                                description "Set bit in charging characteristics information element";
                            }

                            leaf bit14 {
                                type boolean;
                                default "false";
                                description "Set bit in charging characteristics information element";
                            }

                            leaf bit15 {
                                type boolean;
                                default "false";
                                description "Set bit in charging characteristics information element";
                            }

                        } // container home

                        container roaming {
                            description "Enter the roaming context";

                            leaf bit0 {
                                type boolean;
                                default "false";
                                description "Set bit in charging characteristics information element";
                            }

                            leaf bit1 {
                                type boolean;
                                default "false";
                                description "Set bit in charging characteristics information element";
                            }

                            leaf bit2 {
                                type boolean;
                                default "false";
                                description "Set bit in charging characteristics information element";
                            }

                            leaf bit3 {
                                type boolean;
                                default "false";
                                description "Set bit in charging characteristics information element";
                            }

                            leaf bit4 {
                                type boolean;
                                default "false";
                                description "Set bit in charging characteristics information element";
                            }

                            leaf bit5 {
                                type boolean;
                                default "false";
                                description "Set bit in charging characteristics information element";
                            }

                            leaf bit6 {
                                type boolean;
                                default "false";
                                description "Set bit in charging characteristics information element";
                            }

                            leaf bit7 {
                                type boolean;
                                default "false";
                                description "Set bit in charging characteristics information element";
                            }

                            leaf bit8 {
                                type boolean;
                                default "false";
                                description "Set bit in charging characteristics information element";
                            }

                            leaf bit9 {
                                type boolean;
                                default "false";
                                description "Set bit in charging characteristics information element";
                            }

                            leaf bit10 {
                                type boolean;
                                default "false";
                                description "Set bit in charging characteristics information element";
                            }

                            leaf bit11 {
                                type boolean;
                                default "false";
                                description "Set bit in charging characteristics information element";
                            }

                            leaf bit12 {
                                type boolean;
                                default "false";
                                description "Set bit in charging characteristics information element";
                            }

                            leaf bit13 {
                                type boolean;
                                default "false";
                                description "Set bit in charging characteristics information element";
                            }

                            leaf bit14 {
                                type boolean;
                                default "false";
                                description "Set bit in charging characteristics information element";
                            }

                            leaf bit15 {
                                type boolean;
                                default "false";
                                description "Set bit in charging characteristics information element";
                            }

                        } // container roaming

                    } // container charging-characteristics

                    container ggsn {
                        description "Enter the ggsn context";

                        container qos {
                            description "Enter the qos context";

                            leaf arp {
                                type uint32 {
                                    range "1..3";
                                }
                                default "1";
                                description "Allocation or retention priority";
                            }

                            container ambr {
                                presence "Enable the ambr context";
                                description "Enable the ambr context";

                                leaf down-link {
                                    type int32 {
                                        range "0..10000000";
                                    }
                                    units "kilobps";
                                    mandatory true;
                                    description "Downlink Aggregated Maximum Bit Rate (AMBR)";
                                }

                                leaf up-link {
                                    type int32 {
                                        range "0..10000000";
                                    }
                                    units "kilobps";
                                    mandatory true;
                                    description "Uplink Aggregated Maximum Bit Rate (AMBR)";
                                }

                            } // container ambr

                            container down-link {
                                description "Enter the down-link context";

                                leaf gbr {
                                    type uint32 {
                                        range "0..100000";
                                    }
                                    units "kilobps";
                                    default "2000";
                                    description "Guaranteed Bit Rate (GBR)";
                                }

                                leaf mbr {
                                    type uint32 {
                                        range "0..100000";
                                    }
                                    units "kilobps";
                                    default "2000";
                                    description "Maximum Bit Rate (MBR)";
                                }

                            } // container down-link

                            container up-link {
                                description "Enter the up-link context";

                                leaf gbr {
                                    type uint32 {
                                        range "0..100000";
                                    }
                                    units "kilobps";
                                    default "5000";
                                    description "Guaranteed Bit Rate (GBR)";
                                }

                                leaf mbr {
                                    type uint32 {
                                        range "0..100000";
                                    }
                                    units "kilobps";
                                    default "5000";
                                    description "Maximum Bit Rate (MBR)";
                                }

                            } // container up-link

                        } // container qos

                    } // container ggsn

                    container pgw {
                        description "Enter the pgw context";

                        container qos {
                            description "Enter the qos context";

                            leaf arp {
                                type uint32 {
                                    range "1..15";
                                }
                                default "1";
                                description "Allocation or retention priority";
                            }

                            leaf qci {
                                type uint32 {
                                    range "1..9";
                                }
                                default "8";
                                description "QoS Class Identifier (QCI) to send in GTP messages";
                            }

                            container ambr {
                                description "Enter the ambr context";

                                leaf down-link {
                                    type int32 {
                                        range "0..10000000";
                                    }
                                    units "kilobps";
                                    default "20000";
                                    description "Downlink Aggregated Maximum Bit Rate (AMBR)";
                                }

                                leaf up-link {
                                    type int32 {
                                        range "0..10000000";
                                    }
                                    units "kilobps";
                                    default "10000";
                                    description "Uplink Aggregated Maximum Bit Rate (AMBR)";
                                }

                            } // container ambr

                            container down-link {
                                description "Enter the down-link context";

                                leaf gbr {
                                    type uint32 {
                                        range "0..100000";
                                    }
                                    units "kilobps";
                                    default "0";
                                    description "Guaranteed Bit Rate (GBR)";
                                }

                                leaf mbr {
                                    type uint32 {
                                        range "0..100000";
                                    }
                                    units "kilobps";
                                    default "0";
                                    description "Maximum Bit Rate (MBR)";
                                }

                            } // container down-link

                            container up-link {
                                description "Enter the up-link context";

                                leaf gbr {
                                    type uint32 {
                                        range "0..100000";
                                    }
                                    units "kilobps";
                                    default "0";
                                    description "Guaranteed Bit Rate (GBR)";
                                }

                                leaf mbr {
                                    type uint32 {
                                        range "0..100000";
                                    }
                                    units "kilobps";
                                    default "0";
                                    description "Maximum Bit Rate (MBR)";
                                }

                            } // container up-link

                        } // container qos

                    } // container pgw

                } // container uplink

            } // list peer-profile

        } // container gtp

    } // grouping conf-submgt-gtp

}
