submodule nokia-state-port-otu {

    yang-version "1.1";

    belongs-to nokia-state { prefix "state"; }

    import ietf-yang-types                { prefix "yang"; }
    import nokia-sros-yang-extensions     { prefix "sros-ext"; }
    import nokia-types-port               { prefix "types-port"; }

    sros-ext:sros-major-release "rel26";
    organization "Nokia";
    contact
        "Nokia SR OS Support
         Web: <http://www.nokia.com>";
    description
        "Nokia YANG Data model with operational state for optical transport unit ports on SR OS based routers.

         Copyright 2016 Nokia. All rights reserved. Reproduction of this document
         is authorized on the condition that the foregoing copyright notice is included.

         This nokia-state-port-otu YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    grouping state-port-otu {
        container otu {
            description "Enter the otu context";

            leaf current-alarms {
                type types-port:otu-report-alarms;
                description "Indicates the current alarms on the OTU port.";
            }

            leaf reported-alarms {
                type types-port:otu-report-alarms;
                description
                    "Indicates the monitored alarms currently being raised on the OTU port.
                     This leaf reports any 'current-alarms' that respect what is configured
                     by 'report-alarm'.";
            }

            leaf operational-data-rate {
                type uint32;
                units "megabps";
                description "Indicates the rate at which the OTU data is transmitted on the line.";
            }

            container path-monitoring {
                description "Enter the path-monitoring context";

                container trail-trace-identifier {
                    description "Enter the trail-trace-identifier context";

                    leaf receive {
                        type string;
                        description "Indicates the TTI received OTU overhead.";
                    }

                } // container trail-trace-identifier

            } // container path-monitoring

            container payload-structure-identifier {
                description "Enter the payload-structure-identifier context";

                container payload {
                    description "Enter the payload context";

                    leaf receive {
                        type types-port:otu-psi-payload-type;
                        description "Indicates the payload type in the received OTU PSI overhead.";
                    }

                } // container payload

            } // container payload-structure-identifier

            container section-monitoring {
                description "Enter the section-monitoring context";

                container trail-trace-identifier {
                    description "Enter the trail-trace-identifier context";

                    leaf receive {
                        type string;
                        description "Indicates the TTI received OTU overhead.";
                    }

                } // container trail-trace-identifier

            } // container section-monitoring

            container statistics {
                description "Enter the statistics context";

                container raw {
                    description "Enter the raw context";

                    leaf elapsed-seconds {
                        type yang:counter32;
                        description
                            "Indicates the number of elapsed seconds since the last OTU raw
                             statistics clearing.";
                    }

                    leaf negative-pointer-justifications {
                        type yang:counter32;
                        description
                            "Indicates the number of Negative Pointer Justifications (NPJ) that
                             occurred during the asynchronous demapping of the received payload
                             inside the OTU frame.";
                    }

                    leaf positive-pointer-justifications {
                        type yang:counter32;
                        description
                            "Indicates the number of Positive Pointer Justifications (PPJ) that
                             occurred during the asynchronous demapping of the received payload
                             inside the OTU frame.";
                    }

                    container forward-error-correction {
                        description "Enter the forward-error-correction context";

                        leaf corrected-bits {
                            type yang:counter64;
                            description "Indicates the number of corrected bits.";
                        }

                        leaf corrected-ones {
                            type yang:counter64;
                            description "Indicates the number of corrected ones.";
                        }

                        leaf corrected-zeros {
                            type yang:counter64;
                            description "Indicates the number of corrected zeros.";
                        }

                        leaf uncorrectable-sub-rows {
                            type yang:counter64;
                            description "Indicates the number of uncorrectable sub-rows.";
                        }

                        leaf corrected-ber {
                            type string {
                                length "1..32";
                            }
                            description "Indicates the corrected Bit Error Rate (BER).";
                        }

                        leaf uncorrected-ber {
                            type string {
                                length "1..32";
                            }
                            description "Indicates the uncorrected Bit Error Rate (BER).";
                        }

                        leaf errored-seconds {
                            type yang:counter32;
                            description "Indicates the number of Errored Seconds (SES).";
                        }

                        leaf severely-errored-seconds {
                            type yang:counter32;
                            description "Indicates the number of Severely Errored Seconds (SES).";
                        }

                        leaf unavailable-seconds {
                            type yang:counter32;
                            description "Indicates the number of Unavailable Seconds (UAS).";
                        }

                    } // container forward-error-correction

                    container path-monitoring {
                        description "Enter the path-monitoring context";

                        leaf bei-errors {
                            type yang:counter64;
                            description "Indicates the number of Backward Error Indication (BEI) errors.";
                        }

                        leaf bip8-ber {
                            type string {
                                length "1..32";
                            }
                            description "Indicates the BIP8 Bit Error Rate (BER).";
                        }

                        leaf bip8-errors {
                            type yang:counter64;
                            description "Indicates the number of BIP8 errors.";
                        }

                        leaf errored-seconds {
                            type yang:counter32;
                            description "Indicates the number of Errored Seconds (SES).";
                        }

                        leaf severely-errored-seconds {
                            type yang:counter32;
                            description "Indicates the number of Severely Errored Seconds (SES).";
                        }

                        leaf unavailable-seconds {
                            type yang:counter32;
                            description "Indicates the number of Unavailable Seconds (UAS).";
                        }

                    } // container path-monitoring

                    container section-monitoring {
                        description "Enter the section-monitoring context";

                        leaf bei-errors {
                            type yang:counter64;
                            description "Indicates the number of Backward Error Indication (BEI) errors.";
                        }

                        leaf bip8-ber {
                            type string {
                                length "1..32";
                            }
                            description "Indicates the BIP8 Bit Error Rate (BER).";
                        }

                        leaf bip8-errors {
                            type yang:counter64;
                            description "Indicates the number of BIP8 errors.";
                        }

                        leaf errored-seconds {
                            type yang:counter32;
                            description "Indicates the number of Errored Seconds (SES).";
                        }

                        leaf severely-errored-seconds {
                            type yang:counter32;
                            description "Indicates the number of Severely Errored Seconds (SES).";
                        }

                        leaf unavailable-seconds {
                            type yang:counter32;
                            description "Indicates the number of Unavailable Seconds (UAS).";
                        }

                    } // container section-monitoring

                } // container raw

            } // container statistics

        } // container otu

    } // grouping state-port-otu

}
