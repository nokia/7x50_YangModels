submodule nokia-state-svc-vpls {

    yang-version "1.1";

    belongs-to nokia-state { prefix "state"; }

    import ietf-yang-types                { prefix "yang"; }
    import nokia-sros-yang-extensions     { prefix "sros-ext"; }
    import nokia-types-card               { prefix "types-card"; }
    import nokia-types-eth-cfm            { prefix "types-eth-cfm"; }
    import nokia-types-igmp               { prefix "types-igmp"; }
    import nokia-types-igp                { prefix "types-igp"; }
    import nokia-types-isis               { prefix "types-isis"; }
    import nokia-types-mpls               { prefix "types-mpls"; }
    import nokia-types-pim                { prefix "types-pim"; }
    import nokia-types-qos                { prefix "types-qos"; }
    import nokia-types-services           { prefix "types-services"; }
    import nokia-types-sros               { prefix "types-sros"; }
    import nokia-types-subscriber-mgmt    { prefix "types-submgt"; }

    include nokia-state-eth-cfm;
    include nokia-state-router;
    include nokia-state-router-segment-routing;
    include nokia-state-service;

    sros-ext:sros-major-release "rel26";
    organization "Nokia";
    contact
        "Nokia SR OS Support
         Web: <http://www.nokia.com>";
    description
        "Nokia YANG Data model with operational state for vpls services on SR OS based routers.

         Copyright 2016 Nokia. All rights reserved. Reproduction of this document
         is authorized on the condition that the foregoing copyright notice is included.

         This nokia-state-svc-vpls YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-05-27";

    grouping state-svc-vpls {
        list vpls {
            key "service-name";
            description "Enter the vpls list instance";

            leaf service-name {
                type types-services:service-name;
                description "Name of the service";
            }

            leaf oper-service-id {
                type types-services:service-id;
                description "Service identifier";
            }

            leaf oper-state {
                type types-sros:oper-state;
                description "Operational state.";
            }

            leaf sap-count {
                type int32;
                description "Number of SAPs";
            }

            leaf sdp-bind-count {
                type int32;
                description "Number of SDP binds";
            }

            leaf template-used {
                type string;
                description "Template used to create this service";
            }

            leaf creation-origin {
                type types-sros:creation-origin;
                description "Creation origin of the service";
            }

            leaf l2pt-term-enabled {
                type boolean;
                description
                    "If 'l2pt-termination' and/or 'bpdu-translation'
                     is in use in this service by at least one SAP or
                     spoke SDP Bind. If the value is 'true', it means that
                     at least one of 'l2pt-termination' or 'bpdu-translation'
                     is enabled.";
            }

            container fdb {
                description "Enter the fdb context";

                leaf mac-relearn-only {
                    type boolean;
                    description
                        "When set to 'true' either the FDB table of this VPLS
                         service is full, or that the maximum system wide number of
                         MACs supported by the node has been reached, and thus
                         MAC learning is temporary disabled, and only MAC relearns
                         can take place.";
                }

                leaf table-high-utilization {
                    type boolean;
                    description "Set to 'true' when the FDB table utilization reaches the high watermark and 'false' when it reaches the low watermark.";
                }

                leaf relearn-attempt-for-pinned-mac-address {
                    type yang:mac-address;
                    description "The MAC address being assigned to an interface while pinned.";
                }

                leaf relearn-attempt-for-pinned-mac-address-last-changed {
                    type yang:date-and-time;
                    description "Timestamp when the MAC address being assigned to an interface while pinned was detected.";
                }

                container statistics {
                    description "Enter the statistics context";

                    leaf total {
                        type int32;
                        description "Number of entries allocated in the FDB ";
                    }

                    leaf in-use {
                        type int32;
                        description "Number of entries currently in use in the FDB";
                    }

                    leaf static {
                        type int32;
                        description "Number of static entries in the FDB";
                    }

                    leaf learned {
                        type int32;
                        description "Number of learned entries in the FDB";
                    }

                    leaf oam {
                        type int32;
                        description "Number of OAM entries in the FDB";
                    }

                    leaf conditional-static {
                        type int32;
                        description "Number of conditional static entries in the FDB";
                    }

                    leaf dhcp {
                        type int32;
                        description "Number of dhcp-learned entries in the FDB";
                    }

                    leaf host {
                        type int32;
                        description "Number of host-learned entries in the FDB";
                    }

                    leaf interface {
                        type int32;
                        description "Number of interface entries in the FDB";
                    }

                    leaf bgp-evpn {
                        type int32;
                        description "Number of bgp-evpn entries in the FDB";
                    }

                    leaf evpn-static {
                        type int32;
                        description "Number of evpn static entries in the FDB";
                    }

                    leaf spb {
                        type int32;
                        description "Number of SPB entries in the FDB";
                    }

                    leaf eth-cfm {
                        type int32;
                        description "Number of eth-cfm entries in FDB";
                    }

                } // container statistics

                container bgp-evpn {
                    description "Enter the bgp-evpn context";

                    leaf duplicate-mac-address-detected {
                        type boolean;
                        description "Indicates if a duplicated MAC address is detected";
                    }

                    leaf black-hole-dup-mac-address-detected {
                        type yang:mac-address;
                        description "The black hole duplicated MAC address";
                    }

                    leaf black-hole-dup-mac-address-detected-last-changed {
                        type yang:date-and-time;
                        description "Timestamp when the black hole duplicated MAC address was detected";
                    }

                    leaf protected-mac-address-received {
                        type yang:mac-address;
                        description "The protected MAC address received";
                    }

                    leaf protected-mac-address-received-last-changed {
                        type yang:date-and-time;
                        description "Timestamp when the protected MAC address was receieved";
                    }

                } // container bgp-evpn

                container backbone-vpls {
                    description "Enter the backbone-vpls context";

                    leaf pbb-protected-mac-address-received {
                        type yang:mac-address;
                        description "The PBB protected MAC address received";
                    }

                    leaf pbb-protected-mac-address-received-last-changed {
                        type yang:date-and-time;
                        description "Timestamp when the PBB protected MAC address was receieved";
                    }

                } // container backbone-vpls

                list endpoint {
                    key "name";
                    description "Enter the endpoint list instance";

                    leaf name {
                        type types-sros:named-item;
                        description "Name of the service endpoint";
                    }

                    leaf mac-addresses-learned-crossed-high-watermark {
                        type boolean;
                        description "Set to 'true' when the numberof MAC addresses in the FDB table for this endpoint reaches the high watermark and 'false' when it reaches the low watermark.";
                    }

                } // list endpoint

                container card-status {
                    description "Enter the card-status context";

                    list card {
                        key "slot-id";
                        description "Enter the card list instance";

                        leaf slot-id {
                            type uint32;
                            description "Slot id";
                        }

                        leaf allocated {
                            type uint32;
                            description "Number of slots allocated";
                        }

                        leaf pending-allocated {
                            type uint32;
                            description "Number of slots pending to be allocated";
                        }

                        leaf pending-free {
                            type uint32;
                            description "Number of slots pending to be free";
                        }

                    } // list card

                } // container card-status

                list mac {
                    key "address";
                    description "Enter the mac list instance";

                    leaf address {
                        type yang:mac-address;
                        description "MAC address";
                    }

                    leaf locale {
                        type types-services:vpls-fdb-locale;
                        description "locality of the this FDB entry.";
                    }

                    leaf sap {
                        type types-sros:sap;
                        description "SAP for this FDB entry.";
                    }

                    leaf sdp-bind {
                        type types-services:state-sdp-bind-id-or-zero;
                        description "SDP binding of the SDP for this FDB entry.";
                    }

                    leaf ivpls-mac-count {
                        type uint32;
                        description
                            "Number of ISID VPLS service MAC addressess which are using
                             this FDB MAC entry.";
                    }

                    leaf pbb-epipes-count {
                        type uint32;
                        description "Number of EPipes that resolve to this MAC Address.";
                    }

                    leaf backbone-destination-address {
                        type yang:mac-address;
                        description
                            "Backbone VPLS service MAC address used as destination MAC address
                             in the Provider Backbone Bridging frames for this FDB Entry.";
                    }

                    leaf type {
                        type types-services:fdb-mac-type;
                        description "Type for FDB MAC address.";
                    }

                    leaf last-update {
                        type types-sros:date-time;
                        description "Time this entry was last updated.";
                    }

                    leaf age {
                        type uint32;
                        description "Age for this MAC address.";
                    }

                    leaf protected-mac {
                        type boolean;
                        description "If this FDB MAC entry is protected.";
                    }

                    container endpoint {
                        description "Enter the endpoint context";

                        leaf name {
                            type types-sros:named-item;
                            description "Endpoint name for this FDB entry.";
                        }

                        leaf sdp-bind {
                            type types-services:state-sdp-bind-id-or-zero;
                            description "Endpoint SDP ID for this FDB entry.";
                        }

                    } // container endpoint

                    container vxlan {
                        description "Enter the vxlan context";

                        leaf esi {
                            type string;
                            description "Ethernet Segment Identifier for this FDB entry.";
                        }

                        leaf instance {
                            type int32;
                            description "Vxlan Instace for this FDB entry.";
                        }

                        leaf tep {
                            type types-sros:ip-address;
                            description "Vxlan Tunnel Endpoint address for this FDB entry.";
                        }

                        leaf vni {
                            type types-services:vxlan-vni;
                            description "Vxlan Network Identifier for this FDB entry.";
                        }

                    } // container vxlan

                    container evpn-mpls {
                        description "Enter the evpn-mpls context";

                        leaf etree-leaf {
                            type boolean;
                            description "Indicates if this MAC entry was learned from EVPN etree leaf.";
                        }

                        leaf esi {
                            type string;
                            description "Ethernet Segment Identifier for this FDB entry.";
                        }

                        leaf tep {
                            type types-sros:ip-address;
                            description "EVPN MPLS Tunnel Endpoint address for this FDB entry.";
                        }

                        leaf label {
                            type uint32;
                            description "MPLS label of endpoint of ethernet VPN (EVPN).";
                        }

                        leaf tunnel-identifier {
                            type uint32;
                            description "Tunnel identifier associated to the non multi-homing EVPN MPLS destination.";
                        }

                        leaf transport-type {
                            type types-mpls:mpls-transport-type;
                            description "Transport type used for this FDB entry.";
                        }

                    } // container evpn-mpls

                    container srv6 {
                        description "Enter the srv6 context";

                        leaf instance {
                            type int32;
                            description "EVPN SRv6 instance";
                        }

                        leaf tep {
                            type types-sros:ip-address;
                            description "Tunnel endpoint address";
                        }

                        leaf sid-address {
                            type types-sros:ip-address;
                            description "SID address";
                        }

                        leaf esi {
                            type string;
                            description "Ethernet Segment Identifier for this FDB entry.";
                        }

                    } // container srv6

                    container mac-status {
                        description "Enter the mac-status context";

                        leaf type {
                            type enumeration {
                                enum global                         { value 0; }
                                enum select                         { value 1; }
                            }
                            description "If the FDB MAC entry is global or selective.";
                        }

                        leaf status {
                            type enumeration {
                                enum pending                        { value 0; }
                                enum pending-allocated              { value 1; }
                                enum pending-free                   { value 2; }
                                enum allocated                      { value 3; }
                            }
                            description "Status of the FDB MAC entry.";
                        }

                        leaf card {
                            type union {
                                type uint32;
                                type enumeration {
                                    enum all                            { value 0; }
                                }
                            }
                            description "Card on which the FDB MAC entry is allocated.";
                        }

                    } // container mac-status

                } // list mac

            } // container fdb

            container mfib {
                description "Enter the mfib context";

                container table {
                    description "Enter the table context";

                    leaf high-utilization {
                        type boolean;
                        description "Set to 'true' when the utilization of the MFIB table reaches the high watermark and 'false' when it reaches the low watermark.";
                    }

                    list mac-based-stream {
                        key "mac-address";
                        description "Enter the mac-based-stream list instance";

                        leaf mac-address {
                            type yang:mac-address;
                        }

                        leaf matched-packets {
                            type yang:zero-based-counter64;
                            description "The number of multicast packets that matched this entry.";
                        }

                        leaf matched-octets {
                            type yang:zero-based-counter64;
                            description "The number of forwarded octets that matched this entry.";
                        }

                        leaf forwarding-rate {
                            type yang:zero-based-counter64;
                            units "kilobps";
                            description "The forwarded rate that matched this entry.";
                        }

                        list sap {
                            key "sap-id";
                            description "Enter the sap list instance";

                            leaf sap-id {
                                type types-sros:sap;
                                description "SAP identifier";
                            }

                            leaf forwarding-state {
                                type types-igmp:forwarding-state;
                                description "The traffic forwarding state on this port.";
                            }

                            leaf port-service-name {
                                type types-services:service-name;
                                description "The service to which this port belongs";
                            }

                        } // list sap

                        list sdp {
                            key "sdp-bind-id";
                            description "Enter the sdp list instance";

                            leaf sdp-bind-id {
                                type types-services:sdp-bind-id;
                                description
                                    "SDP Binding identifier as <sdp-id>:<vc-id>.
                                     sdp-id - [1..32767]
                                     vc-id - [1..4294967295].";
                            }

                            leaf forwarding-state {
                                type types-igmp:forwarding-state;
                                description "The traffic forwarding state on this port.";
                            }

                            leaf port-service-name {
                                type types-services:service-name;
                                description "The service to which this port belongs";
                            }

                        } // list sdp

                        list vxlan {
                            key "vtep vni";
                            description "Enter the vxlan list instance";

                            leaf vtep {
                                type types-sros:ip-unicast-address;
                            }

                            leaf vni {
                                type types-services:vxlan-vni;
                            }

                            leaf forwarding-state {
                                type types-igmp:forwarding-state;
                                description "The traffic forwarding state on this port.";
                            }

                            leaf port-service-name {
                                type types-services:service-name;
                                description "The service to which this port belongs";
                            }

                        } // list vxlan

                        list evpn-mpls {
                            key "tep label";
                            description "Enter the evpn-mpls list instance";

                            leaf tep {
                                type types-sros:ip-unicast-address;
                            }

                            leaf label {
                                type uint32;
                            }

                            leaf forwarding-state {
                                type types-igmp:forwarding-state;
                                description "The traffic forwarding state on this port.";
                            }

                            leaf port-service-name {
                                type types-services:service-name;
                                description "The service to which this port belongs";
                            }

                        } // list evpn-mpls

                    } // list mac-based-stream

                    list ipv4-based-stream {
                        key "group-address source-address";
                        description "Enter the ipv4-based-stream list instance";

                        leaf group-address {
                            type types-sros:ipv4-address;
                            description "Group address of multicast channel.";
                        }

                        leaf source-address {
                            type types-sros:ipv4-address;
                            description "Source address of multicast channel.";
                        }

                        leaf matched-packets {
                            type yang:zero-based-counter64;
                            description "The number of multicast packets that matched this entry.";
                        }

                        leaf matched-octets {
                            type yang:zero-based-counter64;
                            description "The number of forwarded octets that matched this entry.";
                        }

                        leaf forwarding-rate {
                            type yang:zero-based-counter64;
                            units "kilobps";
                            description "The forwarded rate that matched this entry.";
                        }

                        list sap {
                            key "sap-id";
                            description "Enter the sap list instance";

                            leaf sap-id {
                                type types-sros:sap;
                                description "SAP identifier";
                            }

                            leaf forwarding-state {
                                type types-igmp:forwarding-state;
                                description "The traffic forwarding state on this port.";
                            }

                            leaf port-service-name {
                                type types-services:service-name;
                                description "The service to which this port belongs";
                            }

                        } // list sap

                        list sdp {
                            key "sdp-bind-id";
                            description "Enter the sdp list instance";

                            leaf sdp-bind-id {
                                type types-services:sdp-bind-id;
                                description
                                    "SDP Binding identifier as <sdp-id>:<vc-id>.
                                     sdp-id - [1..32767]
                                     vc-id - [1..4294967295].";
                            }

                            leaf forwarding-state {
                                type types-igmp:forwarding-state;
                                description "The traffic forwarding state on this port.";
                            }

                            leaf port-service-name {
                                type types-services:service-name;
                                description "The service to which this port belongs";
                            }

                        } // list sdp

                        list vxlan {
                            key "vtep vni";
                            description "Enter the vxlan list instance";

                            leaf vtep {
                                type types-sros:ip-unicast-address;
                            }

                            leaf vni {
                                type types-services:vxlan-vni;
                            }

                            leaf forwarding-state {
                                type types-igmp:forwarding-state;
                                description "The traffic forwarding state on this port.";
                            }

                            leaf port-service-name {
                                type types-services:service-name;
                                description "The service to which this port belongs";
                            }

                        } // list vxlan

                        list evpn-mpls {
                            key "tep label";
                            description "Enter the evpn-mpls list instance";

                            leaf tep {
                                type types-sros:ip-unicast-address;
                            }

                            leaf label {
                                type uint32;
                            }

                            leaf forwarding-state {
                                type types-igmp:forwarding-state;
                                description "The traffic forwarding state on this port.";
                            }

                            leaf port-service-name {
                                type types-services:service-name;
                                description "The service to which this port belongs";
                            }

                        } // list evpn-mpls

                        list multicast-management-operational-data {
                            key "chassis-number slot-number fp-number";
                            description "Enter the multicast-management-operational-data list instance";

                            leaf chassis-number {
                                type uint32;
                                description "The unique index identifying this physical chassis.";
                            }

                            leaf slot-number {
                                type uint32;
                                description
                                    "The unique value which identifies the IOM slot within a
                                     chassis in the system.";
                            }

                            leaf fp-number {
                                type uint32;
                                description "Forwarding plane within a specific IOM card";
                            }

                            leaf bandwith {
                                type yang:gauge32;
                                units "kilobps";
                                description "Current bandwidth";
                            }

                            leaf current-path {
                                type enumeration {
                                    enum none                           { value 0; }
                                    enum primary                        { value 1; }
                                    enum secondary                      { value 2; }
                                    enum ancillary                      { value 3; }
                                    enum blackhole                      { value 4; }
                                }
                                description "Explicit sf path.";
                            }

                            leaf explicit-path {
                                type boolean;
                                description "???";
                            }

                            leaf admin-bw {
                                type yang:gauge32;
                                description "Admin bandwidth.";
                            }

                            leaf preference {
                                type yang:gauge32;
                                description "Preference level.";
                            }

                            leaf blackholed {
                                type boolean;
                                description "In black-hole state";
                            }

                            leaf blackhole-rate {
                                type yang:gauge32;
                                description "The current rate at which this channel will be placed in black-hole state";
                            }

                            leaf highest-bw {
                                type yang:gauge32;
                                description "The highest multicast bandwidth that has been accounted.";
                            }

                            leaf second-highest-bw {
                                type yang:gauge32;
                                description "The second highest multicast bandwidth that has been accounted.";
                            }

                            leaf expiry-time {
                                type uint32;
                                units "seconds";
                                description "Remaining time before the bandwidth update timer on the FP expires";
                            }

                            leaf plane {
                                type uint32;
                                description "Forwarding plane";
                            }

                        } // list multicast-management-operational-data

                    } // list ipv4-based-stream

                    list ipv6-based-stream {
                        key "group-address source-address";
                        description "Enter the ipv6-based-stream list instance";

                        leaf group-address {
                            type types-sros:ipv6-address;
                            description "Group address of multicast channel.";
                        }

                        leaf source-address {
                            type types-sros:ipv6-address;
                            description "Source address of multicast channel.";
                        }

                        leaf matched-packets {
                            type yang:zero-based-counter64;
                            description "The number of multicast packets that matched this entry.";
                        }

                        leaf matched-octets {
                            type yang:zero-based-counter64;
                            description "The number of forwarded octets that matched this entry.";
                        }

                        leaf forwarding-rate {
                            type yang:zero-based-counter64;
                            units "kilobps";
                            description "The forwarded rate that matched this entry.";
                        }

                        list sap {
                            key "sap-id";
                            description "Enter the sap list instance";

                            leaf sap-id {
                                type types-sros:sap;
                                description "SAP identifier";
                            }

                            leaf forwarding-state {
                                type types-igmp:forwarding-state;
                                description "The traffic forwarding state on this port.";
                            }

                            leaf port-service-name {
                                type types-services:service-name;
                                description "The service to which this port belongs";
                            }

                        } // list sap

                        list sdp {
                            key "sdp-bind-id";
                            description "Enter the sdp list instance";

                            leaf sdp-bind-id {
                                type types-services:sdp-bind-id;
                                description
                                    "SDP Binding identifier as <sdp-id>:<vc-id>.
                                     sdp-id - [1..32767]
                                     vc-id - [1..4294967295].";
                            }

                            leaf forwarding-state {
                                type types-igmp:forwarding-state;
                                description "The traffic forwarding state on this port.";
                            }

                            leaf port-service-name {
                                type types-services:service-name;
                                description "The service to which this port belongs";
                            }

                        } // list sdp

                        list vxlan {
                            key "vtep vni";
                            description "Enter the vxlan list instance";

                            leaf vtep {
                                type types-sros:ip-unicast-address;
                            }

                            leaf vni {
                                type types-services:vxlan-vni;
                            }

                            leaf forwarding-state {
                                type types-igmp:forwarding-state;
                                description "The traffic forwarding state on this port.";
                            }

                            leaf port-service-name {
                                type types-services:service-name;
                                description "The service to which this port belongs";
                            }

                        } // list vxlan

                        list evpn-mpls {
                            key "tep label";
                            description "Enter the evpn-mpls list instance";

                            leaf tep {
                                type types-sros:ip-unicast-address;
                            }

                            leaf label {
                                type uint32;
                            }

                            leaf forwarding-state {
                                type types-igmp:forwarding-state;
                                description "The traffic forwarding state on this port.";
                            }

                            leaf port-service-name {
                                type types-services:service-name;
                                description "The service to which this port belongs";
                            }

                        } // list evpn-mpls

                        list multicast-management-operational-data {
                            key "chassis-number slot-number fp-number";
                            description "Enter the multicast-management-operational-data list instance";

                            leaf chassis-number {
                                type uint32;
                                description "The unique index identifying this physical chassis.";
                            }

                            leaf slot-number {
                                type uint32;
                                description
                                    "The unique value which identifies the IOM slot within a
                                     chassis in the system.";
                            }

                            leaf fp-number {
                                type uint32;
                                description "Forwarding plane within a specific IOM card";
                            }

                            leaf bandwith {
                                type yang:gauge32;
                                units "kilobps";
                                description "Current bandwidth";
                            }

                            leaf current-path {
                                type enumeration {
                                    enum none                           { value 0; }
                                    enum primary                        { value 1; }
                                    enum secondary                      { value 2; }
                                    enum ancillary                      { value 3; }
                                    enum blackhole                      { value 4; }
                                }
                                description "Explicit sf path.";
                            }

                            leaf explicit-path {
                                type boolean;
                                description "???";
                            }

                            leaf admin-bw {
                                type yang:gauge32;
                                description "Admin bandwidth.";
                            }

                            leaf preference {
                                type yang:gauge32;
                                description "Preference level.";
                            }

                            leaf blackholed {
                                type boolean;
                                description "In black-hole state";
                            }

                            leaf blackhole-rate {
                                type yang:gauge32;
                                description "The current rate at which this channel will be placed in black-hole state";
                            }

                            leaf highest-bw {
                                type yang:gauge32;
                                description "The highest multicast bandwidth that has been accounted.";
                            }

                            leaf second-highest-bw {
                                type yang:gauge32;
                                description "The second highest multicast bandwidth that has been accounted.";
                            }

                            leaf expiry-time {
                                type uint32;
                                units "seconds";
                                description "Remaining time before the bandwidth update timer on the FP expires";
                            }

                            leaf plane {
                                type uint32;
                                description "Forwarding plane";
                            }

                        } // list multicast-management-operational-data

                    } // list ipv6-based-stream

                } // container table

            } // container mfib

            container vxlan {
                description "Enter the vxlan context";

                container statistics {
                    description "Enter the statistics context";

                    leaf last-cleared {
                        type types-sros:date-time;
                        description "Indicates the time of the last clearing of vpls vxlan statistics.";
                    }

                    leaf vni-failure-statistics {
                        type types-sros:date-time;
                        description "Indicates the VTEP egress VNI failure statistics time";
                    }

                    leaf vtep {
                        type uint32;
                        description "Indicates the number of VTEPs";
                    }

                    leaf service-multicast-limit {
                        type uint32;
                        description "Indicates the vxlan TLS multicast limit";
                    }

                    leaf system-limit {
                        type uint32;
                        description "Indicates the system limit";
                    }

                    leaf egress-multicast-list-limit {
                        type uint32;
                        description "indicates the egress multicast system limit";
                    }

                } // container statistics

                list instance {
                    key "vxlan-instance";
                    description "Enter the instance list instance";

                    leaf vxlan-instance {
                        type uint32 {
                            range "1..2";
                        }
                        description "VXLAN instance";
                    }

                    leaf mcast-dest-usage-high {
                        type boolean;
                        description "Indicates if the number of VTEP-Egress VNIs exceeds the per-service VTEP-Egress VNI multicast limit";
                    }

                    container destinations {
                        description "Enter the destinations context";

                        list non-ethernet-segment-destination {
                            key "ip-address vni";
                            description "Enter the non-ethernet-segment-destination list instance";

                            leaf ip-address {
                                type types-sros:ip-address;
                                description "IP address of the tunnel endpoint";
                            }

                            leaf vni {
                                type types-services:vxlan-vni;
                                description "VNI of the vxlan";
                            }

                            leaf mac-count {
                                type uint32;
                                description "Number of MAC addresses";
                            }

                            leaf oper-state {
                                type types-sros:oper-state;
                                description "Operational status of tunnel endpoint";
                            }

                            leaf es-pbr {
                                type boolean;
                                description "Whether VTEP-VNI is programmed due to PBR.";
                            }

                            leaf multicast-forwarding-type {
                                type types-services:multicast-forwarding-type;
                                description "Mulitcast forwarding type";
                            }

                            leaf type {
                                type enumeration {
                                    enum none                           { value 0; }
                                    enum static                         { value 1; }
                                    enum evpn                           { value 2; }
                                }
                                description "Type of vxlan instance created on this VPLS service.";
                            }

                            leaf supplementary-broadcast-domain {
                                type boolean;
                                description "Whether the VTEP and Egress VNI is included in the supplementery broadcast-list multicast.";
                            }

                            leaf oper-flags {
                                type types-services:oper-flags;
                                description "Conditions affecting the operational status of the vxlan tunnel endpoint";
                            }

                            leaf last-update {
                                type types-sros:date-time;
                                description "Time this entry was last updated.";
                            }

                            container igmp-snooping {
                                description "Enter the igmp-snooping context";

                                container statistics {
                                    description "Enter the statistics context";

                                    container received {
                                        description "Enter the received context";

                                        leaf general-queries {
                                            type yang:counter32;
                                            description "General Queries.";
                                        }

                                        leaf group-queries {
                                            type yang:counter32;
                                            description "Group Specific Queries.";
                                        }

                                        leaf group-source-queries {
                                            type yang:counter32;
                                            description "Group and Source Specific Queries.";
                                        }

                                        leaf v1-reports {
                                            type yang:counter32;
                                            description "V1 Reports.";
                                        }

                                        leaf v2-reports {
                                            type yang:counter32;
                                            description "V2 Reports.";
                                        }

                                        leaf v3-reports {
                                            type yang:counter32;
                                            description "V3 Reports.";
                                        }

                                        leaf leaves {
                                            type yang:counter32;
                                            description "Leaves.";
                                        }

                                        leaf drops {
                                            type yang:counter32;
                                            description "Total number of dropped packets.";
                                        }

                                        leaf bgp-smet-routes {
                                            type yang:counter32;
                                            description "Total number of BGP SMET routes.";
                                        }

                                        leaf bgp-join-sync-routes {
                                            type yang:counter32;
                                            description "Total number of BGP JOIN SYNC routes.";
                                        }

                                        leaf bgp-leave-sync-routes {
                                            type yang:counter32;
                                            description "Total number of BGP LEAVE SYNC routes.";
                                        }

                                    } // container received

                                    container transmitted {
                                        description "Enter the transmitted context";

                                        leaf general-queries {
                                            type yang:counter32;
                                            description "General Queries.";
                                        }

                                        leaf group-queries {
                                            type yang:counter32;
                                            description "Group Specific Queries.";
                                        }

                                        leaf group-source-queries {
                                            type yang:counter32;
                                            description "Group and Source Specific Queries.";
                                        }

                                        leaf v1-reports {
                                            type yang:counter32;
                                            description "V1 Reports.";
                                        }

                                        leaf v2-reports {
                                            type yang:counter32;
                                            description "V2 Reports.";
                                        }

                                        leaf v3-reports {
                                            type yang:counter32;
                                            description "V3 Reports.";
                                        }

                                        leaf leaves {
                                            type yang:counter32;
                                            description "Leaves.";
                                        }

                                        leaf drops {
                                            type yang:counter32;
                                            description "Total number of dropped packets.";
                                        }

                                        leaf errors {
                                            type yang:counter32;
                                            description "Transmission Errors.";
                                        }

                                        leaf bgp-join-sync-routes {
                                            type yang:counter32;
                                            description "Total number of BGP JOIN SYNC routes.";
                                        }

                                        leaf bgp-leave-sync-routes {
                                            type yang:counter32;
                                            description "Total number of BGP LEAVE SYNC routes.";
                                        }

                                    } // container transmitted

                                    container forwarded {
                                        description "Enter the forwarded context";

                                        leaf general-queries {
                                            type yang:counter32;
                                            description "General Queries.";
                                        }

                                        leaf group-queries {
                                            type yang:counter32;
                                            description "Group Specific Queries.";
                                        }

                                        leaf group-source-queries {
                                            type yang:counter32;
                                            description "Group and Source Specific Queries.";
                                        }

                                        leaf v1-reports {
                                            type yang:counter32;
                                            description "V1 Reports.";
                                        }

                                        leaf v2-reports {
                                            type yang:counter32;
                                            description "V2 Reports.";
                                        }

                                        leaf v3-reports {
                                            type yang:counter32;
                                            description "V3 Reports.";
                                        }

                                        leaf leaves {
                                            type yang:counter32;
                                            description "Leaves.";
                                        }

                                        leaf drops {
                                            type yang:counter32;
                                            description "Total number of dropped packets.";
                                        }

                                        leaf unknown-types {
                                            type yang:counter32;
                                            description "Unknown types.";
                                        }

                                        leaf errors {
                                            type yang:counter32;
                                            description "Forwarding Errors.";
                                        }

                                    } // container forwarded

                                    container error {
                                        description "Enter the error context";

                                        leaf bad-length {
                                            type yang:counter32;
                                            description "Bad length.";
                                        }

                                        leaf bad-ip-checksum {
                                            type yang:counter32;
                                            description "Bad Ip checksum.";
                                        }

                                        leaf unknown-type {
                                            type yang:counter32;
                                            description "Unknown type.";
                                        }

                                        leaf wrong-version {
                                            type yang:counter32;
                                            description "Wrong version.";
                                        }

                                        leaf import-policy-drops {
                                            type yang:counter32;
                                            description
                                                "Number of times we matched the host IP address or group or
                                                 source addresses specified in the import policy.";
                                        }

                                        leaf missing-router-alert {
                                            type yang:counter32;
                                            description "Router alert flag is not set.";
                                        }

                                        leaf bad-encoding {
                                            type yang:counter32;
                                            description "Badly encoded.";
                                        }

                                        leaf local-scope {
                                            type yang:counter32;
                                            description "Link-local scope multicast group address.";
                                        }

                                        leaf mcac-policy-drops {
                                            type yang:counter32;
                                            description
                                                "Number of times a join is dropped because of applying a
                                                 multicast CAC policy.";
                                        }

                                        leaf reached-maximum-number-groups {
                                            type yang:counter32;
                                            description
                                                "Number of times a join is dropped because we reached the maximum
                                                 number of groups.";
                                        }

                                        leaf reached-maximum-number-group-sources {
                                            type yang:counter32;
                                            description
                                                "Number of times a join is dropped because we reached the maximum
                                                 number group-source combinations.";
                                        }

                                        leaf reached-maximum-number-sources {
                                            type yang:counter32;
                                            description
                                                "Number of times a join is dropped because we reached the maximum
                                                 number of sources per group.";
                                        }

                                        leaf out-of-memory-drops {
                                            type yang:counter32;
                                            description "Number of times a join is dropped because we ran out of memory.";
                                        }

                                        leaf mcs-failures {
                                            type yang:counter32;
                                            description "Number of times a group could not be synced through multi chassis synchronisation (MCS).";
                                        }

                                        leaf bad-igmp-checksum {
                                            type yang:counter32;
                                            description
                                                "Number of times a packet is dropped because of a bad IGMP
                                                 header checksum.";
                                        }

                                        leaf zero-source-ip-addr {
                                            type yang:counter32;
                                            description "Number of times a packet is dropped because it has a zero source ip address.";
                                        }

                                        leaf send-query-cfg-drops {
                                            type yang:counter32;
                                            description "Number of times a query is dropped because send-queries is configured.";
                                        }

                                        leaf mvr-from-vpls-cfg-drops {
                                            type yang:counter32;
                                            description "Number of times a packet is dropped because mvr from-vpls could not be applied.";
                                        }

                                        leaf mvr-to-sap-cfg-drops {
                                            type yang:counter32;
                                            description "Number of times a packet is dropped because it has mvr to-sap configuration.";
                                        }

                                        leaf dropped-bgp-smet-routes {
                                            type yang:counter32;
                                            description "Total number of dropped BGP SMET routes.";
                                        }

                                        leaf dropped-bgp-join-sync-routes {
                                            type yang:counter32;
                                            description "Total number of dropped BGP JOIN SYNC routes.";
                                        }

                                        leaf dropped-bgp-leave-sync-routes {
                                            type yang:counter32;
                                            description "Total number of dropped BGP LEAVE SYNC routes.";
                                        }

                                    } // container error

                                } // container statistics

                                list group {
                                    key "group-address";
                                    description "Enter the group list instance";

                                    leaf group-address {
                                        type types-sros:ipv4-multicast-address;
                                        description "Group address of multicast channel.";
                                    }

                                    leaf group-type {
                                        type types-igmp:learn-type;
                                    }

                                    leaf filter-mode {
                                        type types-igmp:filter-mode;
                                    }

                                    leaf expiry-time {
                                        type uint32;
                                        units "seconds";
                                        description "The time left before multicast group timeout.";
                                    }

                                    leaf up-time {
                                        type uint32;
                                        units "seconds";
                                        description "The time elapsed since this entry was created.";
                                    }

                                    leaf v1-host-timer {
                                        type uint32;
                                        units "seconds";
                                        description
                                            "The time remaining until the local router will assume that
                                             there are no longer any version 1 members.";
                                    }

                                    leaf v2-host-timer {
                                        type uint32;
                                        units "seconds";
                                        description
                                            "The time remaining until the local router will assume that
                                             there are no longer any version 2 members.";
                                    }

                                    leaf igmp-compatibility-mode {
                                        type types-igmp:igmp-version;
                                        description "Compatibility with older version routers.";
                                    }

                                    list source {
                                        key "source-address";
                                        description "Enter the source list instance";

                                        leaf source-address {
                                            type types-sros:ipv4-address;
                                            description "Source address of multicast channel.";
                                        }

                                        leaf source-type {
                                            type types-igmp:learn-type;
                                        }

                                        leaf forwarding-state {
                                            type types-igmp:forwarding-state;
                                            description "Traffic forwardeding state on this port.";
                                        }

                                        leaf expiry-time {
                                            type uint32;
                                            units "seconds";
                                            description "The time left before multicast group timeout.";
                                        }

                                        leaf up-time {
                                            type uint32;
                                            units "seconds";
                                            description "The time elapsed since this entry was created.";
                                        }

                                    } // list source

                                } // list group

                            } // container igmp-snooping

                            container mld-snooping {
                                description "Enter the mld-snooping context";

                                container statistics {
                                    description "Enter the statistics context";

                                    container received {
                                        description "Enter the received context";

                                        leaf general-queries {
                                            type yang:counter32;
                                            description "General Queries.";
                                        }

                                        leaf group-queries {
                                            type yang:counter32;
                                            description "Group Specific Queries.";
                                        }

                                        leaf group-source-queries {
                                            type yang:counter32;
                                            description "Group and Source Specific Queries.";
                                        }

                                        leaf v1-reports {
                                            type yang:counter32;
                                            description "V1 Reports.";
                                        }

                                        leaf v2-reports {
                                            type yang:counter32;
                                            description "V2 Reports.";
                                        }

                                        leaf leaves {
                                            type yang:counter32;
                                            description "Leaves.";
                                        }

                                        leaf drops {
                                            type yang:counter32;
                                            description "Total number of dropped packets.";
                                        }

                                        leaf bgp-smet-routes {
                                            type yang:counter32;
                                            description "Total number of BGP SMET routes.";
                                        }

                                        leaf bgp-join-sync-routes {
                                            type yang:counter32;
                                            description "Total number of BGP JOIN SYNC routes.";
                                        }

                                        leaf bgp-leave-sync-routes {
                                            type yang:counter32;
                                            description "Total number of BGP LEAVE SYNC routes.";
                                        }

                                    } // container received

                                    container transmitted {
                                        description "Enter the transmitted context";

                                        leaf general-queries {
                                            type yang:counter32;
                                            description "General Queries.";
                                        }

                                        leaf group-queries {
                                            type yang:counter32;
                                            description "Group Specific Queries.";
                                        }

                                        leaf group-source-queries {
                                            type yang:counter32;
                                            description "Group and Source Specific Queries.";
                                        }

                                        leaf v1-reports {
                                            type yang:counter32;
                                            description "V1 Reports.";
                                        }

                                        leaf v2-reports {
                                            type yang:counter32;
                                            description "V2 Reports.";
                                        }

                                        leaf leaves {
                                            type yang:counter32;
                                            description "Leaves.";
                                        }

                                        leaf drops {
                                            type yang:counter32;
                                            description "Total number of dropped packets.";
                                        }

                                        leaf errors {
                                            type yang:counter32;
                                            description "Transmission Errors.";
                                        }

                                        leaf bgp-join-sync-routes {
                                            type yang:counter32;
                                            description "Total number of BGP JOIN SYNC routes.";
                                        }

                                        leaf bgp-leave-sync-routes {
                                            type yang:counter32;
                                            description "Total number of BGP LEAVE SYNC routes.";
                                        }

                                    } // container transmitted

                                    container forwarded {
                                        description "Enter the forwarded context";

                                        leaf general-queries {
                                            type yang:counter32;
                                            description "General Queries.";
                                        }

                                        leaf group-queries {
                                            type yang:counter32;
                                            description "Group Specific Queries.";
                                        }

                                        leaf group-source-queries {
                                            type yang:counter32;
                                            description "Group and Source Specific Queries.";
                                        }

                                        leaf v1-reports {
                                            type yang:counter32;
                                            description "V1 Reports.";
                                        }

                                        leaf v2-reports {
                                            type yang:counter32;
                                            description "V2 Reports.";
                                        }

                                        leaf leaves {
                                            type yang:counter32;
                                            description "Leaves.";
                                        }

                                        leaf drops {
                                            type yang:counter32;
                                            description "Total number of dropped packets.";
                                        }

                                        leaf unknown-types {
                                            type yang:counter32;
                                            description "Unknown types.";
                                        }

                                        leaf errors {
                                            type yang:counter32;
                                            description "Forwarding Errors.";
                                        }

                                    } // container forwarded

                                    container error {
                                        description "Enter the error context";

                                        leaf bad-length {
                                            type yang:counter32;
                                            description "Bad length.";
                                        }

                                        leaf unknown-type {
                                            type yang:counter32;
                                            description "Unknown type.";
                                        }

                                        leaf wrong-version {
                                            type yang:counter32;
                                            description "Wrong version.";
                                        }

                                        leaf import-policy-drops {
                                            type yang:counter32;
                                            description
                                                "Number of times we matched the host IP address or group or
                                                 source addresses specified in the import policy.";
                                        }

                                        leaf missing-router-alert {
                                            type yang:counter32;
                                            description "Router alert flag is not set.";
                                        }

                                        leaf bad-encoding {
                                            type yang:counter32;
                                            description "Badly encoded.";
                                        }

                                        leaf local-scope {
                                            type yang:counter32;
                                            description "Link-local scope multicast group address.";
                                        }

                                        leaf reserved-scope {
                                            type yang:counter32;
                                            description "Reserved scope multicast group address.";
                                        }

                                        leaf reached-maximum-number-groups {
                                            type yang:counter32;
                                            description
                                                "Number of times a join is dropped because we reached the maximum
                                                 number of groups.";
                                        }

                                        leaf reached-maximum-number-group-sources {
                                            type yang:counter32;
                                            description
                                                "Number of times a join is dropped because we reached the maximum
                                                 number group-source combinations.";
                                        }

                                        leaf reached-maximum-number-sources {
                                            type yang:counter32;
                                            description
                                                "Number of times a join is dropped because we reached the maximum
                                                 number of sources per group.";
                                        }

                                        leaf out-of-memory-drops {
                                            type yang:counter32;
                                            description "Number of times a join is dropped because we ran out of memory.";
                                        }

                                        leaf bad-mld-checksum {
                                            type yang:counter32;
                                            description
                                                "Number of times a packet is dropped because of a bad MLD
                                                 header checksum.";
                                        }

                                        leaf zero-source-ip-addr {
                                            type yang:counter32;
                                            description "Number of times a packet is dropped because it has a zero source ip address.";
                                        }

                                        leaf send-query-cfg-drops {
                                            type yang:counter32;
                                            description "Number of times a query is dropped because send-queries is configured.";
                                        }

                                        leaf dropped-bgp-smet-routes {
                                            type yang:counter32;
                                            description "Total number of dropped BGP SMET routes.";
                                        }

                                        leaf dropped-bgp-join-sync-routes {
                                            type yang:counter32;
                                            description "Total number of dropped BGP JOIN SYNC routes.";
                                        }

                                        leaf dropped-bgp-leave-sync-routes {
                                            type yang:counter32;
                                            description "Total number of dropped BGP LEAVE SYNC routes.";
                                        }

                                    } // container error

                                } // container statistics

                                list group {
                                    key "group-address";
                                    description "Enter the group list instance";

                                    leaf group-address {
                                        type types-sros:ipv6-multicast-address;
                                        description "Group address of multicast channel.";
                                    }

                                    leaf group-type {
                                        type types-igmp:learn-type;
                                    }

                                    leaf filter-mode {
                                        type types-igmp:filter-mode;
                                    }

                                    leaf expiry-time {
                                        type uint32;
                                        units "seconds";
                                        description "The time left before multicast group timeout.";
                                    }

                                    leaf up-time {
                                        type uint32;
                                        units "seconds";
                                        description "The time elapsed since this entry was created.";
                                    }

                                    leaf v1-host-timer {
                                        type uint32;
                                        units "seconds";
                                        description
                                            "The time remaining until the local router will assume that
                                             there are no longer any version 1 members.";
                                    }

                                    leaf mld-compatibility-mode {
                                        type types-igmp:mld-version;
                                        description "Compatibility with older version routers.";
                                    }

                                    list source {
                                        key "source-address";
                                        description "Enter the source list instance";

                                        leaf source-address {
                                            type types-sros:ipv6-address;
                                            description "Source address of multicast channel.";
                                        }

                                        leaf source-type {
                                            type types-igmp:learn-type;
                                        }

                                        leaf forwarding-state {
                                            type types-igmp:forwarding-state;
                                            description "Traffic forwardeding state on this port.";
                                        }

                                        leaf expiry-time {
                                            type uint32;
                                            units "seconds";
                                            description "The time left before multicast group timeout.";
                                        }

                                        leaf up-time {
                                            type uint32;
                                            units "seconds";
                                            description "The time elapsed since this entry was created.";
                                        }

                                    } // list source

                                } // list group

                            } // container mld-snooping

                            container pim-snooping {
                                description "Enter the pim-snooping context";

                                container ipv4 {
                                    description "Enter the ipv4 context";

                                    leaf oper-state {
                                        type types-sros:oper-state;
                                        description
                                            "The value of the this object indicates the operational
                                             state of PIM for this interface.";
                                    }

                                    leaf up-time {
                                        type uint32;
                                        units "seconds";
                                        description "The time since this interface became operational.";
                                    }

                                    leaf group-count {
                                        type uint32;
                                        description
                                            "The number of multicast groups which currently have this
                                             interface as an outgoing interface.";
                                    }

                                    leaf maximum-groups-until-now {
                                        type uint32;
                                        description "The highest value that 'group-count' had till now.";
                                    }

                                    leaf pseudo-wire-forwarder {
                                        type boolean;
                                        description
                                            "Whether this interface is the forwarding interface
                                             of a pair of redundant pseudo-wire ports.";
                                    }

                                    container statistics {
                                        description "Enter the statistics context";

                                        leaf rx-packets {
                                            type yang:counter32;
                                            description "The number of multicast data packets received on this interface.";
                                        }

                                        leaf rx-hellos {
                                            type yang:counter32;
                                            description "The number of PIM hello messages received on this interface.";
                                        }

                                        leaf rx-join-prunes {
                                            type yang:counter32;
                                            description
                                                "The number of PIM
                                                 Join Prune messages received on this interface.";
                                        }

                                        leaf tx-packets {
                                            type yang:counter32;
                                            description "The number of multicast data packets transmitted on this interface.";
                                        }

                                        leaf tx-join-prunes {
                                            type yang:counter32;
                                            description
                                                "The number of PIM
                                                 Join Prune messages transmitted on this interface.";
                                        }

                                        leaf rx-hellos-dropped {
                                            type yang:counter32;
                                            description
                                                "The number of PIM Hello messages which were received on this interface but were
                                                 dropped.";
                                        }

                                        leaf rx-neighbor-unknown {
                                            type yang:counter32;
                                            description
                                                "The number of PIM messages (other than Hello messages) which were received on this
                                                 interface and were rejected because the adjacency with the neighbor
                                                 router was not already established.";
                                        }

                                        leaf rx-bad-checksum-discard {
                                            type yang:counter32;
                                            description
                                                "The number of PIM messages received on this interface which were discarded because
                                                 of bad checksum.";
                                        }

                                        leaf rx-bad-version-discard {
                                            type yang:counter32;
                                            description "The number of PIM messages with bad versions received on this interface.";
                                        }

                                        leaf rx-bad-encodings {
                                            type yang:counter32;
                                            description "The number of PIM messages with bad encodings received on this interface.";
                                        }

                                        leaf join-policy-drops {
                                            type yang:counter32;
                                            description
                                                "The number of times the join policy match resulted in dropping PIM Join-Prune
                                                 Message or one of the source group contained in the message.";
                                        }

                                        leaf rx-join-prune-errors {
                                            type yang:counter32;
                                            description
                                                "The number of errors while processing Join-Prune messages received on this
                                                 interface.";
                                        }

                                    } // container statistics

                                    list neighbor {
                                        key "neighbor-address";
                                        description "Enter the neighbor list instance";

                                        leaf neighbor-address {
                                            type types-sros:ipv4-address;
                                            description "This value indicates the IPv4 address of the PIM neighbor.";
                                        }

                                        leaf dr-priority {
                                            type uint32;
                                            description
                                                "This value indicates neighbor's DR priority which is received
                                                 in the hello message. If the Hello Message did not contain
                                                 the DR priority field, the value of priority will be '1'.";
                                        }

                                        leaf dr-priority-present {
                                            type boolean;
                                            description
                                                "This value of indicates whether the DR priority field was present
                                                 in the Hello message received from the PIM neighbor.";
                                        }

                                        leaf tracking-support {
                                            type boolean;
                                            description
                                                "This value indicates whether the T bit in the LAN Prune Delay
                                                 option was present in the Hello message. This indicates the
                                                 neighbor's capability to disable Join message suppression.";
                                        }

                                        leaf lan-delay {
                                            type uint32;
                                            units "milliseconds";
                                            description
                                                "This value indicates the value of lan delay field present in
                                                 the Hello message received from the neighbor. ";
                                        }

                                        leaf lan-delay-present {
                                            type boolean;
                                            description
                                                "This value indicates whether the Hello message received from
                                                 the neighbor contained the Lan Delay field.";
                                        }

                                        leaf generated-id {
                                            type uint32;
                                            description
                                                "This value indicates a randomly generated 32-bit value that is
                                                 regenerated each time PIM forwarding is started or restarted on
                                                 the interface, including when the router itself restarts.";
                                        }

                                        leaf override-interval {
                                            type uint32;
                                            units "milliseconds";
                                            description
                                                "This value indicates the value of the override interval present
                                                 in the Hello message.";
                                        }

                                        leaf up-time {
                                            type uint32;
                                            units "seconds";
                                            description
                                                "This value indicates the time since this PIM neighbor (last)
                                                 became a neighbor of the local router.";
                                        }

                                        leaf expiry-time {
                                            type uint32;
                                            units "seconds";
                                            description
                                                "This value indicates the minimum time remaining before this
                                                 PIM neighbor will be aged out.";
                                        }

                                        leaf hold-time {
                                            type uint32;
                                            units "seconds";
                                            description
                                                "This value indicates the value of the hold time present in the
                                                 Hello message.";
                                        }

                                        leaf join-attribute-support {
                                            type boolean;
                                            description
                                                "This value indicates whether the Hello Message received from
                                                 the neighbor contained the Join Attribute field.";
                                        }

                                        list secondary-neighbor {
                                            key "secondary-neighbor-address";
                                            description "Enter the secondary-neighbor list instance";

                                            leaf secondary-neighbor-address {
                                                type types-sros:ipv4-address;
                                                description
                                                    "This value indicates the IPv4 address of the secondary PIM
                                                     neighbor.";
                                            }

                                        } // list secondary-neighbor

                                    } // list neighbor

                                    list sg {
                                        key "group-address source-address";
                                        description "Enter the sg list instance";

                                        leaf group-address {
                                            type types-sros:ipv4-address;
                                            description "The multicast group address of the entry.";
                                        }

                                        leaf source-address {
                                            type types-sros:ipv4-address;
                                            description "The source address of the multicast sender.";
                                        }

                                        leaf up-time {
                                            type uint32;
                                            units "seconds";
                                            description "The time since this source group entry got created.";
                                        }

                                        leaf join-prune-state {
                                            type types-pim:join-prune-state;
                                            description
                                                "The Join Prune state for this entry on the interface.

                                                 PIM Join or Prune messages are sent by the downstream routers
                                                 towards the RPF' neighbor.";
                                        }

                                        leaf join-prune-timer {
                                            type uint32;
                                            units "seconds";
                                            description
                                                "The time remaining before the router transitions the value of
                                                 join-prune-state to 'no-info'.

                                                 The timer is started or restarted when a valid Join message is
                                                 received. If the value of this object is zero and
                                                 join-prune-state is 'join' state, it means that the
                                                 downstream router sent a holdtime of '0xffff'. In this case,
                                                 join-prune-state will not transition until an appropriate
                                                 cancelling of Join or Prune message is received.";
                                        }

                                        leaf prune-pending-timer {
                                            type uint32;
                                            units "seconds";
                                            description
                                                "The time remaining before the router transitions the value of
                                                 join-prune-state to 'no-info'.

                                                 The timer is set when the PIM Prune message is received.";
                                        }

                                        leaf join-prune-rpt-state {
                                            type types-pim:join-prune-state;
                                            description
                                                "The Join Prune Rpt state for this entry on the interface.

                                                 PIM Join or Prune messages are sent by the downstream routers towards the
                                                 RPF' neighbor. (S,G,rpt) state is a result of receiving (S,G, rpt) JP message
                                                 from the downstream router on the RP tree.";
                                        }

                                        leaf join-prune-rpt-timer {
                                            type uint32;
                                            units "seconds";
                                            description
                                                "The time remaining before the router transitions the value of
                                                 join-prune-rpt-state to 'no-info'.

                                                 The timer is started or restarted when a valid Join message is
                                                 received. If the value of this object is zero and
                                                 join-prune-rpt-state is in 'join' state, it means that the
                                                 downstream router sent a holdtime of '0xffff'. In this case,
                                                 join-prune-rpt-state will not transition until an appropriate
                                                 cancelling of Join or Prune message is received from the
                                                 downstream router.";
                                        }

                                        leaf join-prune-rpt-pending-timer {
                                            type uint32;
                                            units "seconds";
                                            description
                                                "The time remaining before the router transitions the value of
                                                 join-prune-rpt-state to 'no-info'.

                                                 The timer is set when the (S,G,rpt) PIM Prune message is received.";
                                        }

                                    } // list sg

                                } // container ipv4

                                container ipv6 {
                                    description "Enter the ipv6 context";

                                    leaf oper-state {
                                        type types-sros:oper-state;
                                        description
                                            "The value of the this object indicates the operational
                                             state of PIM for this interface.";
                                    }

                                    leaf up-time {
                                        type uint32;
                                        units "seconds";
                                        description "The time since this interface became operational.";
                                    }

                                    leaf group-count {
                                        type uint32;
                                        description
                                            "The number of multicast groups which currently have this
                                             interface as an outgoing interface.";
                                    }

                                    leaf maximum-groups-until-now {
                                        type uint32;
                                        description "The highest value that 'group-count' had till now.";
                                    }

                                    leaf pseudo-wire-forwarder {
                                        type boolean;
                                        description
                                            "Whether this interface is the forwarding interface
                                             of a pair of redundant pseudo-wire ports.";
                                    }

                                    container statistics {
                                        description "Enter the statistics context";

                                        leaf rx-packets {
                                            type yang:counter32;
                                            description "The number of multicast data packets received on this interface.";
                                        }

                                        leaf rx-hellos {
                                            type yang:counter32;
                                            description "The number of PIM hello messages received on this interface.";
                                        }

                                        leaf rx-join-prunes {
                                            type yang:counter32;
                                            description
                                                "The number of PIM
                                                 Join Prune messages received on this interface.";
                                        }

                                        leaf tx-packets {
                                            type yang:counter32;
                                            description "The number of multicast data packets transmitted on this interface.";
                                        }

                                        leaf tx-join-prunes {
                                            type yang:counter32;
                                            description
                                                "The number of PIM
                                                 Join Prune messages transmitted on this interface.";
                                        }

                                        leaf rx-hellos-dropped {
                                            type yang:counter32;
                                            description
                                                "The number of PIM Hello messages which were received on this interface but were
                                                 dropped.";
                                        }

                                        leaf rx-neighbor-unknown {
                                            type yang:counter32;
                                            description
                                                "The number of PIM messages (other than Hello messages) which were received on this
                                                 interface and were rejected because the adjacency with the neighbor
                                                 router was not already established.";
                                        }

                                        leaf rx-bad-checksum-discard {
                                            type yang:counter32;
                                            description
                                                "The number of PIM messages received on this interface which were discarded because
                                                 of bad checksum.";
                                        }

                                        leaf rx-bad-version-discard {
                                            type yang:counter32;
                                            description "The number of PIM messages with bad versions received on this interface.";
                                        }

                                        leaf rx-bad-encodings {
                                            type yang:counter32;
                                            description "The number of PIM messages with bad encodings received on this interface.";
                                        }

                                        leaf join-policy-drops {
                                            type yang:counter32;
                                            description
                                                "The number of times the join policy match resulted in dropping PIM Join-Prune
                                                 Message or one of the source group contained in the message.";
                                        }

                                        leaf rx-join-prune-errors {
                                            type yang:counter32;
                                            description
                                                "The number of errors while processing Join-Prune messages received on this
                                                 interface.";
                                        }

                                    } // container statistics

                                    list neighbor {
                                        key "neighbor-address";
                                        description "Enter the neighbor list instance";

                                        leaf neighbor-address {
                                            type types-sros:ipv6-address;
                                            description "This value indicates the IPv6 address of the PIM neighbor.";
                                        }

                                        leaf dr-priority {
                                            type uint32;
                                            description
                                                "This value indicates neighbor's DR priority which is received
                                                 in the hello message. If the Hello Message did not contain
                                                 the DR priority field, the value of priority will be '1'.";
                                        }

                                        leaf dr-priority-present {
                                            type boolean;
                                            description
                                                "This value of indicates whether the DR priority field was present
                                                 in the Hello message received from the PIM neighbor.";
                                        }

                                        leaf tracking-support {
                                            type boolean;
                                            description
                                                "This value indicates whether the T bit in the LAN Prune Delay
                                                 option was present in the Hello message. This indicates the
                                                 neighbor's capability to disable Join message suppression.";
                                        }

                                        leaf lan-delay {
                                            type uint32;
                                            units "milliseconds";
                                            description
                                                "This value indicates the value of lan delay field present in
                                                 the Hello message received from the neighbor. ";
                                        }

                                        leaf lan-delay-present {
                                            type boolean;
                                            description
                                                "This value indicates whether the Hello message received from
                                                 the neighbor contained the Lan Delay field.";
                                        }

                                        leaf generated-id {
                                            type uint32;
                                            description
                                                "This value indicates a randomly generated 32-bit value that is
                                                 regenerated each time PIM forwarding is started or restarted on
                                                 the interface, including when the router itself restarts.";
                                        }

                                        leaf override-interval {
                                            type uint32;
                                            units "milliseconds";
                                            description
                                                "This value indicates the value of the override interval present
                                                 in the Hello message.";
                                        }

                                        leaf up-time {
                                            type uint32;
                                            units "seconds";
                                            description
                                                "This value indicates the time since this PIM neighbor (last)
                                                 became a neighbor of the local router.";
                                        }

                                        leaf expiry-time {
                                            type uint32;
                                            units "seconds";
                                            description
                                                "This value indicates the minimum time remaining before this
                                                 PIM neighbor will be aged out.";
                                        }

                                        leaf hold-time {
                                            type uint32;
                                            units "seconds";
                                            description
                                                "This value indicates the value of the hold time present in the
                                                 Hello message.";
                                        }

                                        leaf join-attribute-support {
                                            type boolean;
                                            description
                                                "This value indicates whether the Hello Message received from
                                                 the neighbor contained the Join Attribute field.";
                                        }

                                        list secondary-neighbor {
                                            key "secondary-neighbor-address";
                                            description "Enter the secondary-neighbor list instance";

                                            leaf secondary-neighbor-address {
                                                type types-sros:ipv6-address;
                                                description
                                                    "This value indicates the IPv6 address of the secondary PIM
                                                     neighbor.";
                                            }

                                        } // list secondary-neighbor

                                    } // list neighbor

                                    list sg {
                                        key "group-address source-address";
                                        description "Enter the sg list instance";

                                        leaf group-address {
                                            type types-sros:ipv6-address;
                                            description "The multicast group address of the entry.";
                                        }

                                        leaf source-address {
                                            type types-sros:ipv6-address;
                                            description "The source address of the multicast sender.";
                                        }

                                        leaf up-time {
                                            type uint32;
                                            units "seconds";
                                            description "The time since this source group entry got created.";
                                        }

                                        leaf join-prune-state {
                                            type types-pim:join-prune-state;
                                            description
                                                "The Join Prune state for this entry on the interface.

                                                 PIM Join or Prune messages are sent by the downstream routers
                                                 towards the RPF' neighbor.";
                                        }

                                        leaf join-prune-timer {
                                            type uint32;
                                            units "seconds";
                                            description
                                                "The time remaining before the router transitions the value of
                                                 join-prune-state to 'no-info'.

                                                 The timer is started or restarted when a valid Join message is
                                                 received. If the value of this object is zero and
                                                 join-prune-state is 'join' state, it means that the
                                                 downstream router sent a holdtime of '0xffff'. In this case,
                                                 join-prune-state will not transition until an appropriate
                                                 cancelling of Join or Prune message is received.";
                                        }

                                        leaf prune-pending-timer {
                                            type uint32;
                                            units "seconds";
                                            description
                                                "The time remaining before the router transitions the value of
                                                 join-prune-state to 'no-info'.

                                                 The timer is set when the PIM Prune message is received.";
                                        }

                                        leaf join-prune-rpt-state {
                                            type types-pim:join-prune-state;
                                            description
                                                "The Join Prune Rpt state for this entry on the interface.

                                                 PIM Join or Prune messages are sent by the downstream routers towards the
                                                 RPF' neighbor. (S,G,rpt) state is a result of receiving (S,G, rpt) JP message
                                                 from the downstream router on the RP tree.";
                                        }

                                        leaf join-prune-rpt-timer {
                                            type uint32;
                                            units "seconds";
                                            description
                                                "The time remaining before the router transitions the value of
                                                 join-prune-rpt-state to 'no-info'.

                                                 The timer is started or restarted when a valid Join message is
                                                 received. If the value of this object is zero and
                                                 join-prune-rpt-state is in 'join' state, it means that the
                                                 downstream router sent a holdtime of '0xffff'. In this case,
                                                 join-prune-rpt-state will not transition until an appropriate
                                                 cancelling of Join or Prune message is received from the
                                                 downstream router.";
                                        }

                                        leaf join-prune-rpt-pending-timer {
                                            type uint32;
                                            units "seconds";
                                            description
                                                "The time remaining before the router transitions the value of
                                                 join-prune-rpt-state to 'no-info'.

                                                 The timer is set when the (S,G,rpt) PIM Prune message is received.";
                                        }

                                    } // list sg

                                } // container ipv6

                            } // container pim-snooping

                        } // list non-ethernet-segment-destination

                        list ethernet-segment-destination {
                            key "esi";
                            description "Enter the ethernet-segment-destination list instance";

                            leaf esi {
                                type string;
                                description "Ethernet segment identifier";
                            }

                            leaf mac-count {
                                type uint32;
                                description "Number of MAC addresses";
                            }

                            list tep {
                                key "ip-address vni";
                                description "Enter the tep list instance";

                                leaf ip-address {
                                    type types-sros:ip-address;
                                    description "IP address of the tunnel endpoint";
                                }

                                leaf vni {
                                    type types-services:vxlan-vni;
                                    description "VNI of the vxlan";
                                }

                                leaf oper-state {
                                    type types-sros:up-down-status;
                                    description "Operational status of vxlan esi tunnel endpoint";
                                }

                                leaf oper-flags {
                                    type types-services:oper-flags;
                                    description "Conditions affecting the operational status of the vxlan esi tunnel endpoint";
                                }

                            } // list tep

                        } // list ethernet-segment-destination

                    } // container destinations

                    container oper-flags {
                        description "Enter the oper-flags context";

                        leaf multi-homing-standby {
                            type boolean;
                            description "Standby because of a BGP multi-home protocol.";
                        }

                    } // container oper-flags

                    container ethernet-segment {
                        description "Enter the ethernet-segment context";

                        leaf name {
                            type types-sros:named-item-or-empty;
                            description "Ethernet segment name";
                        }

                        leaf oper-state {
                            type types-services:evpn-mh-es-status;
                            description "Operational status of the ethernet-segment";
                        }

                    } // container ethernet-segment

                } // list instance

            } // container vxlan

            container proxy-arp {
                description "Enter the proxy-arp context";

                list host {
                    key "ip-address";
                    description "Enter the host list instance";

                    leaf ip-address {
                        type types-sros:ip-address;
                        description "IP address";
                    }

                    leaf mac-address {
                        type types-sros:mac-address;
                        description "MAC address";
                    }

                    leaf type {
                        type types-services:proxy-entry-type;
                        description "Entry type";
                    }

                    leaf status {
                        type types-services:proxy-status;
                        description "Status";
                    }

                    leaf immutable {
                        type boolean;
                        description "Immutable";
                    }

                    leaf last-update {
                        type types-sros:date-time;
                        description "Time this entry was last updated.";
                    }

                } // list host

                container statistics {
                    description "Enter the statistics context";

                    leaf evpn {
                        type uint32;
                        description "Count of evpn entries";
                    }

                    leaf static {
                        type uint32;
                        description "Count of static entries";
                    }

                    leaf dynamic {
                        type uint32;
                        description "Count of dynamic entries";
                    }

                    leaf duplicate {
                        type uint32;
                        description "Count of duplicate entries";
                    }

                } // container statistics

            } // container proxy-arp

            container proxy-nd {
                description "Enter the proxy-nd context";

                list host {
                    key "ip-address";
                    description "Enter the host list instance";

                    leaf ip-address {
                        type types-sros:ip-address;
                        description "IP address";
                    }

                    leaf mac-address {
                        type types-sros:mac-address;
                        description "MAC address";
                    }

                    leaf type {
                        type types-services:proxy-entry-type;
                        description "Entry type";
                    }

                    leaf status {
                        type types-services:proxy-status;
                        description "Status";
                    }

                    leaf router-host {
                        type types-services:proxy-router-host;
                        description "Router/Host";
                    }

                    leaf immutable {
                        type boolean;
                        description "Immutable";
                    }

                    leaf override {
                        type boolean;
                        description "EVPN override";
                    }

                    leaf last-update {
                        type types-sros:date-time;
                        description "Time this entry was last updated.";
                    }

                } // list host

                container statistics {
                    description "Enter the statistics context";

                    leaf evpn {
                        type uint32;
                        description "Count of evpn entries";
                    }

                    leaf static {
                        type uint32;
                        description "Count of static entries";
                    }

                    leaf dynamic {
                        type uint32;
                        description "Count of dynamic entries";
                    }

                    leaf duplicate {
                        type uint32;
                        description "Count of duplicate entries";
                    }

                } // container statistics

            } // container proxy-nd

            container mrp {
                description "Enter the mrp context";

                container mmrp {
                    description "Enter the mmrp context";

                    leaf oper-state {
                        type types-sros:oper-state;
                        description "Operational state.";
                    }

                    leaf attribute-count {
                        type uint32;
                        description
                            "Number of MMRP attributes currently associated to the
                             VPLS by either being registered or declared.";
                    }

                    leaf registered-attribute-count {
                        type uint32;
                        description "Number of registered MVRP attributes";
                    }

                    leaf declared-attribute-count {
                        type uint32;
                        description "Number of declared MVRP attributes";
                    }

                    leaf failed-registeration-count {
                        type uint32;
                        description "Number of failed MVRP registerations";
                    }

                } // container mmrp


            } // container mrp

            container pbb {
                description "Enter the pbb context";

                leaf oper-source-bmac {
                    type yang:mac-address;
                    description "Backbone Source MAC Address for PBB packets.";
                }

                list backbone-vpls {
                    key "backbone-vpls-service-name";
                    description "Enter the backbone-vpls list instance";

                    leaf backbone-vpls-service-name {
                        type leafref {
                            path "../../../../vpls/service-name";
                        }
                        description "Backbone VPLS service";
                    }

                    leaf oper-isid {
                        type types-services:isid;
                        description
                            "VPLS service ISID used as part of the PBB frames. It is used at
                             the destination PE as a demultiplexor field.";
                    }

                } // list backbone-vpls

            } // container pbb

            container temp-flood {
                description "Enter the temp-flood context";

                leaf active {
                    type boolean;
                    description "Whether temporary flooding is currently active";
                }

                leaf change-count {
                    type int32;
                    description
                        "Number of times temporary flooding status
                         changed from inactive to active.

                         The value of this object resets to zero when temporary
                         flooding is disabled.";
                }

            } // container temp-flood

            container spb {
                description "Enter the spb context";

                list level {
                    key "id";
                    description "Enter the level list instance";

                    leaf id {
                        type int32 {
                            range "1";
                        }
                        description "Level identifier";
                    }

                    leaf multicast-forwarding-type {
                        type enumeration {
                            enum spf                            { value 0; }
                            enum spanning-tree                  { value 1; }
                        }
                        description "Forwarding type";
                    }

                    leaf bridge-id {
                        type string;
                        description "Bridge identifier";
                    }

                    leaf multicast-designated-bridge-id {
                        type string;
                        description "Designated bridge identifier for multicast traffic";
                    }

                    list database {
                        key "lsp-id";
                        description "Enter the database list instance";

                        leaf lsp-id {
                            type types-isis:lsp-id;
                            description
                                "The value specifies the LSP Id and is given in the format as 6 octets of adjacency system-id followed by
                                 1 octet Lan-ID and 1 octet LSP Number.";
                        }

                        leaf seq {
                            type yang:counter32;
                            description
                                "The value indicates the sequence number of
                                 an LSP and is a four byte quantity that represents the version of an LSP.

                                 The higher the sequence number, the more up to date the information.

                                 The sequence number is always incremented by the system that originated
                                 the LSP and ensures that there is only one version of that LSP in the
                                 entire network.";
                        }

                        leaf checksum {
                            type int32 {
                                range "0..65535";
                            }
                            description
                                "The value indicates the checksum of
                                 contents of LSP from the SourceID field in the LSP till the end.

                                 The checksum is computed using the Fletcher checksum algorithm. ";
                        }

                        leaf zero-rtl {
                            type boolean;
                            description
                                "The value indicates the LSP state if
                                 it has once reached zero remaining lifetime.

                                 If this object is 'true' then the object lifetime-remain will
                                 maintain the time remaining after which this LSP will be discarded.";
                        }

                        leaf lifetime-remain {
                            type int32 {
                                range "0..65535";
                            }
                            units "seconds";
                            description
                                "The value indicates the
                                 Remaining lifetime of this LSP and is a decrementing counter that
                                 decrements in seconds starting from the value as received in the
                                 LSP if not self-originated OR from lsp-life-time for self
                                 originated LSPs.

                                 When the remaining lifetime becomes zero, the contents of the LSP
                                 should not be considered for SPF calculation.";
                        }

                        leaf version {
                            type int32;
                            description
                                "The value indicates the version of
                                 the ISIS protocol that has generated the LSP";
                        }

                        leaf pkt-type {
                            type int32;
                            description
                                "The value indicates the packet type
                                 for instance Hello PDUs, LSPs, CSNPs OR PSNPs at both IS-IS protocol
                                 levels i.e. L1 and L2 as maintained in of the object packet-type.";
                        }

                        leaf pkt-version {
                            type int32;
                            description
                                "The value indicates the version of
                                 the ISIS protocol that has generated the Packet.";
                        }

                        leaf attributes {
                            type int32;
                            description
                                "The value indicates the attributes
                                 associated with the LSP and these include the attached bit,
                                 overload bit, IS type of the system originating the LSP and the
                                 partition repair capability.

                                 The attached bit and the overload bit are of significance only when
                                 present in the LSP numbered zero and should be ignored on receipt in
                                 any other LSP.";
                        }

                        leaf max-area {
                            type int32;
                            description
                                "The value indicates the maximum number
                                 of areas supported by the originator of the LSP.

                                 A value of 0 indicates a default of 3 areas. ";
                        }

                        leaf alloc-len {
                            type int32;
                            description
                                "The value indicates the length
                                 allocated for the LSP to be stored.";
                        }

                        leaf system-id {
                            type types-igp:system-id;
                            description "The value indicates the system-id as part of lsp-id used by the originator.";
                        }

                        leaf system-id-len {
                            type int32;
                            description
                                "The value indicates the length of
                                 the system-id as used by the originator.";
                        }

                        leaf used-len {
                            type int32;
                            description
                                "The value indicates the used length
                                 for the LSP.

                                 For an LSP that is not self originated, the used length is always equal
                                 to alloc-len for self originated LSPs, the used length is
                                 less than or equal to alloc-len.";
                        }

                        leaf value {
                            type string {
                                length "56..19558";
                            }
                            description "Contents of the LSP.";
                        }

                    } // list database

                    list spf {
                        key "forwarding-tree algorithm path-id";
                        description "Enter the spf list instance";

                        leaf forwarding-tree {
                            type enumeration {
                                enum unicast                        { value 1; }
                                enum multicast                      { value 2; }
                            }
                            description "Forwarding tree type";
                        }

                        leaf algorithm {
                            type types-services:spb-algorithm;
                            description "Algorithm type";
                        }

                        leaf path-id {
                            type string {
                                length "16";
                            }
                            description
                                "The value specifies the path identifier
                                 and has first 6 octets as the system-id followed by one octet
                                 of the Lan-ID.";
                        }

                        leaf interface-name {
                            type types-sros:interface-name;
                            description "Outgoing interface name for the route.";
                        }

                        leaf system-id {
                            type string;
                            description
                                "System-id of the nexthop IS through which this route is
                                 reachable.";
                        }

                        leaf metric {
                            type uint32;
                            description "Associated metric value.";
                        }

                        leaf snpa {
                            type types-isis:snpa-address;
                            description "The value indicates the subnet point of attachment for this path.";
                        }

                    } // list spf

                } // list level

                container fdb {
                    description "Enter the fdb context";

                    list mac {
                        key "address";
                        description "Enter the mac list instance";

                        leaf address {
                            type yang:mac-address;
                            description "MAC address";
                        }

                        container unicast {
                            description "Enter the unicast context";

                            leaf locale {
                                type types-services:fdb-locale;
                                description "locality of the this FDB entry.";
                            }

                            leaf sap {
                                type types-sros:sap;
                                description "SAP for this FDB entry.";
                            }

                            leaf sdp-bind {
                                type types-services:state-sdp-bind-id-or-zero;
                                description "SDP binding of the SDP for this FDB entry.";
                            }

                            leaf status {
                                type types-services:fdb-state;
                                description "State of this FDB entry in the user VPLS.";
                            }

                        } // container unicast

                        container multicast {
                            description "Enter the multicast context";

                            leaf locale {
                                type types-services:fdb-locale;
                                description "locality of the this FDB entry.";
                            }

                            leaf sap {
                                type types-sros:sap;
                                description "SAP for this FDB entry.";
                            }

                            leaf sdp-bind {
                                type types-services:state-sdp-bind-id-or-zero;
                                description "SDP binding of the SDP for this FDB entry.";
                            }

                            leaf status {
                                type types-services:fdb-state;
                                description "State of this FDB entry in the user VPLS.";
                            }

                        } // container multicast

                    } // list mac

                    list fid-mac {
                        key "fid address";
                        description "Enter the fid-mac list instance";

                        leaf fid {
                            type types-services:spb-fid;
                            description "SPB control vpls FID";
                        }

                        leaf address {
                            type yang:mac-address;
                            description "MAC address";
                        }

                        container unicast {
                            description "Enter the unicast context";

                            leaf locale {
                                type types-services:fdb-locale;
                                description "locality of the this FDB entry.";
                            }

                            leaf sap {
                                type types-sros:sap;
                                description "SAP for this FDB entry.";
                            }

                            leaf sdp-bind {
                                type types-services:state-sdp-bind-id-or-zero;
                                description "SDP binding of the SDP for this FDB entry.";
                            }

                            leaf last-update {
                                type types-sros:date-time;
                                description "Time this entry was last updated.";
                            }

                        } // container unicast

                        container multicast {
                            description "Enter the multicast context";

                            leaf locale {
                                type types-services:fdb-locale;
                                description "locality of the this FDB entry.";
                            }

                            leaf sap {
                                type types-sros:sap;
                                description "SAP for this FDB entry.";
                            }

                            leaf sdp-bind {
                                type types-services:state-sdp-bind-id-or-zero;
                                description "SDP binding of the SDP for this FDB entry.";
                            }

                            leaf last-update {
                                type types-sros:date-time;
                                description "Time this entry was last updated.";
                            }

                        } // container multicast

                    } // list fid-mac

                } // container fdb

                container mfib {
                    description "Enter the mfib context";

                    list mac {
                        key "address";
                        description "Enter the mac list instance";

                        leaf address {
                            type yang:mac-address;
                            description "MAC address";
                        }

                        leaf isid {
                            type uint32;
                            description "ISID of the group MAC address.";
                        }

                        leaf status {
                            type bits {
                                bit ok                             { position 0; }
                                bit add-modify-pending             { position 1; }
                                bit delete-pending                 { position 2; }
                                bit system-mfib-limit              { position 3; }
                                bit no-fate-shared                 { position 4; }
                                bit spb-mfib-limit                 { position 5; }
                                bit use-default-multicast-tree     { position 6; }
                            }
                            description "State of this FDB entry in the user VPLS.";
                        }

                    } // list mac

                    list fid-mac {
                        key "fid address";
                        description "Enter the fid-mac list instance";

                        leaf fid {
                            type types-services:spb-fid;
                            description "SPB control vpls FID";
                        }

                        leaf address {
                            type yang:mac-address;
                            description "MAC address";
                        }

                        leaf isid {
                            type uint32;
                            description "ISID of the group MAC address.";
                        }

                        leaf last-update {
                            type types-sros:date-time;
                            description "Time this entry was last updated.";
                        }

                        list sap {
                            key "id";
                            description "Enter the sap list instance";

                            leaf id {
                                type types-sros:sap;
                                description "SAP information";
                            }

                            leaf isid {
                                type uint32;
                                description "ISID of the group MAC address.";
                            }

                            leaf last-update {
                                type types-sros:date-time;
                                description "Time this entry was last updated.";
                            }

                        } // list sap

                        list sdp-bind {
                            key "id";
                            description "Enter the sdp-bind list instance";

                            leaf id {
                                type types-services:sdp-bind-id;
                                description "SDP binding of the SDP for this FDB entry.";
                            }

                            leaf isid {
                                type uint32;
                                description "ISID of the group MAC address.";
                            }

                            leaf last-update {
                                type types-sros:date-time;
                                description "Time this entry was last updated.";
                            }

                        } // list sdp-bind

                    } // list fid-mac

                } // container mfib

                container route {
                    description "Enter the route context";

                    list unicast {
                        key "fid address";
                        description "Enter the unicast list instance";

                        leaf fid {
                            type types-services:spb-fid;
                            description "SPB control vpls FID";
                        }

                        leaf address {
                            type yang:mac-address;
                            description "MAC address";
                        }

                        leaf interface-name {
                            type types-sros:interface-name;
                            description "Outgoing interface name for the route.";
                        }

                        leaf version {
                            type uint32;
                            description "Run of spf calculation in which this route was selected.";
                        }

                        leaf metric {
                            type uint32;
                            description "Associated metric value.";
                        }

                        leaf system-id {
                            type string;
                            description
                                "System-id of the nexthop IS through which this route is
                                 reachable.";
                        }

                        leaf metric-type {
                            type enumeration {
                                enum exact                          { value 0; }
                                enum lower-bound                    { value 1; }
                            }
                            description "Associated type of metric";
                        }

                    } // list unicast

                    list multicast {
                        key "fid address";
                        description "Enter the multicast list instance";

                        leaf fid {
                            type types-services:spb-fid;
                            description "SPB control vpls FID";
                        }

                        leaf address {
                            type yang:mac-address;
                            description "MAC address";
                        }

                        leaf interface-name {
                            type types-sros:interface-name;
                            description "Outgoing interface name for the route.";
                        }

                        leaf version {
                            type uint32;
                            description "Run of spf calculation in which this route was selected.";
                        }

                        leaf metric {
                            type uint32;
                            description "Associated metric value.";
                        }

                        leaf system-id {
                            type string;
                            description
                                "System-id of the nexthop IS through which this route is
                                 reachable.";
                        }

                        leaf metric-type {
                            type enumeration {
                                enum exact                          { value 0; }
                                enum lower-bound                    { value 1; }
                            }
                            description "Associated type of metric";
                        }

                    } // list multicast

                } // container route

                container interface {
                    description "Enter the interface context";

                    list sap {
                        key "sap-id";
                        description "Enter the sap list instance";

                        leaf sap-id {
                            type types-sros:sap;
                            description "SAP information";
                        }

                    } // list sap

                    list sdp-bind {
                        key "sdp-bind-id";
                        description "Enter the sdp-bind list instance";

                        leaf sdp-bind-id {
                            type types-services:sdp-bind-id;
                            description "SDP binding information";
                        }

                    } // list sdp-bind

                } // container interface

                list spf-log {
                    key "time-stamp";
                    description "Enter the spf-log list instance";

                    leaf time-stamp {
                        type yang:timeticks;
                        units "centiseconds";
                        description "The value specifies the time (in centiseconds) since system-up when the SPF was ran.";
                    }

                    leaf duration {
                        type yang:timeticks;
                        units "centiseconds";
                        description "The value indicates the time (in centiseconds) required to complete the SPF run.";
                    }

                    leaf l1-nodes {
                        type uint32;
                        description "The value indicates the number of L1 nodes involved in the SPF run.";
                    }

                    leaf l2-nodes {
                        type uint32;
                        description "The value indicates the number of L2 nodes involved in the SPF run.";
                    }

                    leaf trigger-lsp-id {
                        type types-isis:lsp-id;
                        description "The value indicates the LSP-Id of the last LSP processed before the SPF run.";
                    }

                    leaf event-count {
                        type uint32;
                        description "The value indicates the number of SPF events that triggered the SPF calculation.";
                    }

                    leaf type {
                        type enumeration {
                            enum regular                        { value 0; }
                            enum lfa                            { value 1; }
                            enum partial-spf                    { value 2; }
                            enum partial-lfa                    { value 3; }
                            enum remote-lfa                     { value 4; }
                            enum ti-lfa                         { value 5; }
                        }
                        description "The value indicates the type of SPF calculation.";
                    }

                    leaf trigger-reason {
                        type bits {
                            bit new-adjacency                  { position 0; }
                            bit new-lsp                        { position 1; }
                            bit new-area                       { position 2; }
                            bit reach                          { position 3; }
                            bit ecmp-changed                   { position 4; }
                            bit new-metric                     { position 5; }
                            bit te-changed                     { position 6; }
                            bit restart                        { position 7; }
                            bit lsp-expired                    { position 8; }
                            bit lsp-db-changed                 { position 9; }
                            bit lsp-changed                    { position 10; }
                            bit new-preference                 { position 11; }
                            bit new-nlp-id                     { position 12; }
                            bit manual-run                     { position 13; }
                            bit admin-tag-changed              { position 14; }
                            bit tunnel-changed                 { position 15; }
                            bit throttle-end                   { position 16; }
                            bit lfa-changed                    { position 17; }
                        }
                        description
                            "The value indicates the reasons that triggered this SPF run.

                             new-sdjacency (0)      - a new adjacency was formed.
                             new-ldp (1)            - a new LSP was received.
                             new-srea (2)           - a new area was joined.
                             reach (3)              - a new prefix can be reached.
                             ecmp-changed (4)       - the number of ecmp routes to a destination changed.
                             new-metric (5)         - a route has a new metric.
                             te-changed (6)         - traffic engineering changed.
                             restart (7)            - the IS-IS router was restarted.
                             lsp-expired (8)        - an LSP expired.
                             lsp-db-changed (9)     - the IS-IS LSP database was cleared.
                             lsp-changed (10)       - an LSP changed.
                             new-preference (11)    - a route preference changed.
                             new-nlp-id (12)        - a Network Layer Protocol was added to the
                                                      IS-IS router protocol set.
                             manual-run (13)        - Manual request issued.
                             admin-tag-changed (14) - admin tag has changed.
                             tunnel-changed (15)    - list of tunnels has changed.
                             throttle-end (16)      - throttling of SPF ended.
                             lfa-changed (17)       - lfa changed.";
                    }

                } // list spf-log

                list host {
                    key "system-id";
                    description "Enter the host list instance";

                    leaf system-id {
                        type string;
                        description
                            "System-id of the nexthop IS through which this route is
                             reachable.";
                    }

                    leaf host-name {
                        type string;
                        description "Host name";
                    }

                } // list host

            } // container spb

            list segment-routing-v6 {
                key "instance";
                description "Enter the segment-routing-v6 list instance";

                leaf instance {
                    type types-services:vpls-srv6-instance;
                    description "Segment routing v6 instance";
                }

                leaf mcast-dest-usage-high {
                    type boolean;
                    description "Indicates if the number of SRv6 tunnel endpoint-egress multicast binds exceeds the per-service limit";
                }

                list locator {
                    key "locator-name";
                    description "Enter the locator list instance";

                    leaf locator-name {
                        type leafref {
                            path "../../../../../router/segment-routing/segment-routing-v6/locator/locator-name";
                        }
                        description "SRv6 locator name.";
                    }

                    container function {
                        description "Enter the function context";

                        container end-dt2u {
                            description "Enter the end-dt2u context";

                            leaf oper-value {
                                type uint32;
                                description "SRv6 function value.";
                            }

                            leaf status {
                                type types-sros:srv6-error-status;
                                description "specifies the current state of this function.";
                            }

                            leaf segment-identifier {
                                type types-sros:ipv6-address;
                                description "address used in the SRv6 packet.";
                            }

                        } // container end-dt2u

                        container end-dt2m {
                            description "Enter the end-dt2m context";

                            leaf oper-value {
                                type uint32;
                                description "SRv6 function value.";
                            }

                            leaf status {
                                type types-sros:srv6-error-status;
                                description "specifies the current state of this function.";
                            }

                            leaf segment-identifier {
                                type types-sros:ipv6-address;
                                description "address used in the SRv6 packet.";
                            }

                        } // container end-dt2m

                    } // container function

                } // list locator

                list micro-segment-locator {
                    key "locator-name";
                    description "Enter the micro-segment-locator list instance";

                    leaf locator-name {
                        type leafref {
                            path "../../../../../router/segment-routing/segment-routing-v6/micro-segment-locator/locator-name";
                        }
                        description "SRv6 locator name.";
                    }

                    container function {
                        description "Enter the function context";

                        container udt2m {
                            description "Enter the udt2m context";

                            leaf oper-value {
                                type uint32;
                                description "SRv6 function value.";
                            }

                            leaf status {
                                type types-sros:srv6-error-status;
                                description "specifies the current state of this function.";
                            }

                            leaf segment-identifier {
                                type types-sros:ipv6-address;
                                description "address used in the SRv6 packet.";
                            }

                        } // container udt2m

                        container udt2u {
                            description "Enter the udt2u context";

                            leaf oper-value {
                                type uint32;
                                description "SRv6 function value.";
                            }

                            leaf status {
                                type types-sros:srv6-error-status;
                                description "specifies the current state of this function.";
                            }

                            leaf segment-identifier {
                                type types-sros:ipv6-address;
                                description "address used in the SRv6 packet.";
                            }

                        } // container udt2u

                    } // container function

                } // list micro-segment-locator

                container destinations {
                    description "Enter the destinations context";

                    list ethernet-segment-destination {
                        key "esi";
                        description "Enter the ethernet-segment-destination list instance";

                        leaf esi {
                            type string;
                            description "Ethernet segment identifier";
                        }

                        leaf last-update {
                            type types-sros:date-time;
                            description "Time this entry was last updated.";
                        }

                        list tep {
                            key "tep-address sid-address";
                            description "Enter the tep list instance";

                            leaf tep-address {
                                type types-sros:ip-address;
                                description "Tunnel endpoint ip-address";
                            }

                            leaf sid-address {
                                type types-sros:ipv6-address;
                                description "SID ip-address";
                            }

                            leaf last-update {
                                type types-sros:date-time;
                                description "Time this entry was last updated.";
                            }

                            leaf oper-state {
                                type types-sros:up-down-status;
                                description "Operational status of srv6 tunnel endpoint";
                            }

                            leaf oper-flags {
                                type types-services:oper-flags;
                                description "Conditions affecting the operational status of the srv6 tunnel endpoint";
                            }

                        } // list tep

                    } // list ethernet-segment-destination

                    list non-ethernet-segment-destination {
                        key "tep-address sid-address";
                        description "Enter the non-ethernet-segment-destination list instance";

                        leaf tep-address {
                            type types-sros:ip-address;
                            description "Tunnel endpoint ip-address";
                        }

                        leaf sid-address {
                            type types-sros:ipv6-address;
                            description "SID ip-address";
                        }

                        leaf srv6-type {
                            type enumeration {
                                enum none                           { value 0; }
                                enum static                         { value 1; }
                                enum evpn                           { value 2; }
                            }
                            description "Type of SRv6 instance created";
                        }

                        leaf oper-state {
                            type types-sros:up-down-status;
                            description "Operational status of srv6 tunnel endpoint";
                        }

                        leaf oper-flags {
                            type types-services:oper-flags;
                            description "Conditions affecting the operational status of the srv6 tunnel endpoint";
                        }

                        leaf last-update {
                            type types-sros:date-time;
                            description "Time this entry was last updated.";
                        }

                    } // list non-ethernet-segment-destination

                } // container destinations

            } // list segment-routing-v6

            container stp {
                description "Enter the stp context";

                leaf bridge-address {
                    type yang:mac-address;
                    description "MAC Address of the bridge";
                }

                leaf time-since-topology-change {
                    type uint32;
                    description "Time since topology change was detected by STP";
                }

                leaf topology-changes {
                    type int32;
                    description "Total number of topology changes detected by STP";
                }

                leaf designated-root {
                    type types-sros:bridge-id;
                    description "The bridge identifier of the root of the spanning tree";
                }

                leaf root-cost {
                    type int32;
                    description "The cost of the path to the root bridge";
                }

                leaf root-port {
                    type int32;
                    description "The port number of the port with the lowest cost path";
                }

                leaf max-age {
                    type int32;
                    description "The maximum age of the stp information learned";
                }

                leaf oper-hello-time {
                    type int32;
                    description "The amount of time between the transmission of Configuration BPDUs";
                }

                leaf oper-forward-delay {
                    type int32;
                    description "The amount of time it takes to change its state when moving towards the forwarding state";
                }

                leaf oper-state {
                    type types-sros:up-down-status;
                    description "The operational status of the stp instance";
                }

                leaf virtual-root-bridge-status {
                    type types-sros:up-down-status;
                    description "The operational status of the Virtual Root Bridge of the stp instance";
                }

                leaf topology-change-active {
                    type boolean;
                    description "Indicates when topology change is currently in progress";
                }

                leaf primary-bridge {
                    type types-sros:bridge-id;
                    description "The bridge ID of the primary bridge being the gateway from the core mesh towards root bridge";
                }

                leaf bridge-instance-id {
                    type int32 {
                        range "0..4095";
                    }
                    description "The stp bridge ID chosen by the system";
                }

                leaf vcp-oper-protocol {
                    type enumeration {
                        enum not-applicable                 { value 0; }
                        enum stp                            { value 1; }
                        enum rstp                           { value 2; }
                        enum mstp                           { value 3; }
                    }
                    description "Indicates whether stp, rstp, or mstp is running on this VCP";
                }

                leaf cist-regional-root {
                    type types-sros:bridge-id;
                    description "The bridge ID of the regional root of the CIST spanning tree";
                }

                leaf cist-int-root-cost {
                    type int32;
                    description "The cost of the path to the CIST regional root bridge";
                }

                leaf cist-remaining-hop-count {
                    type int32;
                    description "The remaining number of hops";
                }

                leaf cist-regional-root-port {
                    type int32;
                    description "The port number of the port with the lowest cost path";
                }

                leaf vcp-state {
                    type enumeration {
                        enum disabled                       { value 1; }
                        enum blocking                       { value 2; }
                        enum listening                      { value 3; }
                        enum learning                       { value 4; }
                        enum forwarding                     { value 5; }
                        enum broken                         { value 6; }
                        enum discarding                     { value 7; }
                    }
                    description "The current state of the VCP";
                }

                container backbone-vpls {
                    description "Enter the backbone-vpls context";

                    leaf port-state {
                        type enumeration {
                            enum disabled                       { value 1; }
                            enum blocking                       { value 2; }
                            enum listening                      { value 3; }
                            enum learning                       { value 4; }
                            enum forwarding                     { value 5; }
                            enum broken                         { value 6; }
                            enum discarding                     { value 7; }
                        }
                        description "The PIP uplink's current state";
                    }

                    leaf port-role {
                        type enumeration {
                            enum master                         { value 0; }
                            enum root                           { value 1; }
                            enum designated                     { value 2; }
                            enum alternate                      { value 3; }
                            enum backup                         { value 4; }
                            enum disabled                       { value 5; }
                        }
                        description "The current role of the PIP uplink";
                    }

                    leaf designated-bridge {
                        type types-sros:bridge-id;
                        description "The identifier of the designated bridge of the PIP uplink";
                    }

                    leaf designated-port {
                        type int32;
                        description "The identifier of the port on the designated bridge";
                    }

                    leaf exception {
                        type enumeration {
                            enum none                           { value 1; }
                            enum one-way-communication          { value 2; }
                            enum downstream-loop-detected       { value 3; }
                        }
                        description "Indicates if an stp exception is present on the pip";
                    }

                    leaf forward-transitions {
                        type uint32;
                        description "The number of times the port has transitioned from learned state to forwarding state";
                    }

                    leaf config-bpdus-received {
                        type uint32;
                        description "The number of configuration BPDUs received on this PIP uplink";
                    }

                    leaf tcn-bpdus-received {
                        type uint32;
                        description "The number of topology change notification BPDUs received on this PIP uplink";
                    }

                    leaf rst-bpdus-received {
                        type uint32;
                        description "The number of RST BPDUs recieved on this PIP uplink";
                    }

                    leaf mst-bpdus-received {
                        type uint32;
                        description "The number of MST BPDUs received on this PIP uplink";
                    }

                    leaf bad-bpdus-received {
                        type uint32;
                        description "The number of bad BPDUs received on this PIP uplink";
                    }

                    leaf config-bpdus-transmitted {
                        type uint32;
                        description "The number of configuration BPDUs transmitted on this PIP uplink";
                    }

                    leaf tcn-bpdus-transmitted {
                        type uint32;
                        description "The number of topology change notification BPDUs transmitted on this PIP uplink";
                    }

                    leaf rst-bpdus-transmitted {
                        type uint32;
                        description "The number of RST BPDUs transmitted on this PIP uplink";
                    }

                    leaf mst-bpdus-transmitted {
                        type uint32;
                        description "The number of MST BPDUs transmitted on this PIP uplink";
                    }

                    leaf oper-state {
                        type types-sros:up-down-status;
                        description "The operational status of the stp instance";
                    }

                    leaf mvpls-prune-state {
                        type enumeration {
                            enum not-applicable                 { value 1; }
                            enum not-pruned                     { value 2; }
                            enum pruned                         { value 3; }
                        }
                        description "The mVPLS prune state of this PIP uplink";
                    }

                    leaf oper-protocol {
                        type enumeration {
                            enum not-applicable                 { value 0; }
                            enum stp                            { value 1; }
                            enum rstp                           { value 2; }
                            enum mstp                           { value 3; }
                        }
                        description "The protocol running on this PIP uplink";
                    }

                    leaf port-num {
                        type int32 {
                            range "0..4094";
                        }
                        description "The port number associated with this PIP uplink";
                    }

                    leaf inside-region {
                        type boolean;
                        description "Indicates if the network connected to the PIP is in the same MST region";
                    }

                } // container backbone-vpls

                list mst-instance {
                    key "mst-inst-number";
                    description "Enter the mst-instance list instance";

                    leaf mst-inst-number {
                        type uint32 {
                            range "1..4094";
                        }
                        description "Multiple Spanning Tree Instance number";
                    }

                    leaf regional-root {
                        type binary {
                            length "8";
                        }
                        description
                            "The bridge identifier of the regional root
                             of the MSTI spanning tree";
                    }

                    leaf root-cost {
                        type int32;
                        description
                            "The cost of the path to the regional root bridge
                             as seen from this bridge.";
                    }

                    leaf hop-count {
                        type int32;
                        description "The remaining number of hops.";
                    }

                    leaf root-port {
                        type int32;
                        description
                            "The port number of the port which offers the lowest cost
                             path from this bridge to the regional root bridge.";
                    }

                } // list mst-instance

            } // container stp

            list bgp {
                key "bgp-instance";
                description "Enter the bgp list instance";

                leaf bgp-instance {
                    type int32 {
                        range "1..2";
                    }
                    description "BGP instance";
                }

                leaf oper-route-distinguisher-type {
                    type types-services:route-distinguisher-type;
                    description "Type of operational route-distinguisher.";
                }

                leaf oper-route-distinguisher {
                    type string;
                    description "Operational route-distinguisher used when advertising NLRIs.";
                }

                container route-target {
                    description "Enter the route-target context";

                    leaf export-origin {
                        type types-services:route-target-origin;
                        description "Origin of route-target export policy";
                    }

                    leaf oper-export {
                        type string;
                        description "Operational route-target used when advertising NLRIs.";
                    }

                    leaf import-origin {
                        type types-services:route-target-origin;
                        description "Origin of route-target import policy";
                    }

                    leaf oper-import {
                        type string;
                        description "Operational route-target used when importing NLRIs.";
                    }

                } // container route-target

            } // list bgp

            container igmp-snooping {
                description "Enter the igmp-snooping context";

                leaf transmitted-bgp-smet-routes {
                    type yang:counter32;
                    description "Transmitted BGP SMET routes";
                }

                container querier {
                    description "Enter the querier context";

                    leaf address {
                        type types-sros:ipv4-address;
                        description
                            "The source IP address used by queries sent out by
                             this multicast router.";
                    }

                    leaf version {
                        type types-igmp:igmp-version;
                        description
                            "The version of the protocol that is sent by this
                             multicast router.";
                    }

                    leaf up-time {
                        type uint32;
                        units "seconds";
                        description
                            "The time since this multicast router has been known
                             in this service.";
                    }

                    leaf expiry-time {
                        type uint32;
                        units "seconds";
                        description "The time remaining before this multicast router is aged out.";
                    }

                    container igmp-v3-states {
                        description "Enter the igmp-v3-states context";

                        leaf general-query-interval {
                            type uint32;
                            units "seconds";
                            description "The General Query Interval used by this multicast router.";
                        }

                        leaf general-response-interval {
                            type uint32;
                            units "seconds";
                            description
                                "The General Query Response interval used by this
                                 multicast router.";
                        }

                        leaf robust-count {
                            type uint32;
                            description "The Robust Count value used by this multicast router.";
                        }

                    } // container igmp-v3-states

                    container port {
                        description "Enter the port context";

                        leaf port-type {
                            type enumeration {
                                enum sap                            { value 0; }
                                enum sdp                            { value 1; }
                                enum rvpls                          { value 2; }
                                enum vxlan                          { value 3; }
                                enum evpn-mpls                      { value 4; }
                            }
                        }

                        leaf sap-id {
                            type types-sros:sap;
                            description "SAP identifier.";
                        }

                        leaf sdp-bind-id {
                            type types-services:sdp-bind-id;
                            description "SDP Binding identifier.";
                        }

                        leaf rvpls-service-name {
                            type types-services:service-name;
                            description "RVPLS service identifier.";
                        }

                        leaf rvpls-interface-name {
                            type types-sros:interface-name;
                            description "RVPLS interface identifier.";
                        }

                        leaf vxlan-vtep {
                            type types-sros:ip-unicast-address;
                            description "VXLAN VTEP identifier.";
                        }

                        leaf vxlan-vni {
                            type types-services:vxlan-vni;
                            description "VXLAN VNI identifier.";
                        }

                    } // container port

                } // container querier

                list multicast-router {
                    key "address";
                    description "Enter the multicast-router list instance";

                    leaf address {
                        type types-sros:ipv4-address;
                        description
                            "The source IP address used by queries sent out by
                             this multicast router.";
                    }

                    leaf version {
                        type types-igmp:igmp-version;
                        description
                            "The version of the protocol that is sent by this
                             multicast router.";
                    }

                    leaf up-time {
                        type uint32;
                        units "seconds";
                        description
                            "The time since this multicast router has been known
                             in this service.";
                    }

                    leaf expiry-time {
                        type uint32;
                        units "seconds";
                        description "The time remaining before this multicast router is aged out.";
                    }

                    container igmp-v3-states {
                        description "Enter the igmp-v3-states context";

                        leaf general-query-interval {
                            type uint32;
                            units "seconds";
                            description "The General Query Interval used by this multicast router.";
                        }

                        leaf general-response-interval {
                            type uint32;
                            units "seconds";
                            description
                                "The General Query Response interval used by this
                                 multicast router.";
                        }

                        leaf robust-count {
                            type uint32;
                            description "The Robust Count value used by this multicast router.";
                        }

                    } // container igmp-v3-states

                    container port {
                        description "Enter the port context";

                        leaf port-type {
                            type enumeration {
                                enum sap                            { value 0; }
                                enum sdp                            { value 1; }
                                enum rvpls                          { value 2; }
                                enum vxlan                          { value 3; }
                                enum evpn-mpls                      { value 4; }
                            }
                        }

                        leaf sap-id {
                            type types-sros:sap;
                            description "SAP identifier.";
                        }

                        leaf sdp-bind-id {
                            type types-services:sdp-bind-id;
                            description "SDP Binding identifier.";
                        }

                        leaf rvpls-service-name {
                            type types-services:service-name;
                            description "RVPLS service identifier.";
                        }

                        leaf rvpls-interface-name {
                            type types-sros:interface-name;
                            description "RVPLS interface identifier.";
                        }

                        leaf vxlan-vtep {
                            type types-sros:ip-unicast-address;
                            description "VXLAN VTEP identifier.";
                        }

                        leaf vxlan-vni {
                            type types-services:vxlan-vni;
                            description "VXLAN VNI identifier.";
                        }

                    } // container port

                } // list multicast-router

                list group {
                    key "group-address";
                    description "Enter the group list instance";

                    leaf group-address {
                        type types-sros:ipv4-multicast-address;
                        description "Group address of multicast channel.";
                    }

                    leaf filter-mode {
                        type types-igmp:filter-mode;
                    }

                    leaf up-time {
                        type uint32;
                        units "seconds";
                        description "The time elapsed since this entry was created.";
                    }

                    list source {
                        key "source-address";
                        description "Enter the source list instance";

                        leaf source-address {
                            type types-sros:ipv4-address;
                            description "Source address of multicast channel.";
                        }

                        leaf up-time {
                            type uint32;
                            units "seconds";
                            description "The time elapsed since this entry was created.";
                        }

                    } // list source

                } // list group

                list evpn-group {
                    key "group-address";
                    description "Enter the evpn-group list instance";

                    leaf group-address {
                        type types-sros:ipv4-multicast-address;
                        description "Group address of multicast channel.";
                    }

                    leaf filter-mode {
                        type types-igmp:filter-mode;
                    }

                    leaf up-time {
                        type uint32;
                        units "seconds";
                        description "The time elapsed since this entry was created.";
                    }

                    leaf v1-support {
                        type boolean;
                        description "Version 1 is supported.";
                    }

                    leaf v2-support {
                        type boolean;
                        description "Version 2 is supported.";
                    }

                    leaf v3-support {
                        type boolean;
                        description "Version 3 is supported.";
                    }

                    list source {
                        key "source-address";
                        description "Enter the source list instance";

                        leaf source-address {
                            type types-sros:ipv4-address;
                            description "Source address of multicast channel.";
                        }

                        leaf up-time {
                            type uint32;
                            units "seconds";
                            description "The time elapsed since this entry was created.";
                        }

                    } // list source

                } // list evpn-group

            } // container igmp-snooping

            container mld-snooping {
                description "Enter the mld-snooping context";

                leaf transmitted-bgp-smet-routes {
                    type yang:counter32;
                    description "Transmitted BGP SMET routes";
                }

                container querier {
                    description "Enter the querier context";

                    leaf address {
                        type types-sros:ipv6-address;
                        description
                            "The source IP address used by queries sent out by
                             this multicast router.";
                    }

                    leaf version {
                        type types-igmp:igmp-version;
                        description
                            "The version of the protocol that is sent by this
                             multicast router.";
                    }

                    leaf up-time {
                        type uint32;
                        units "seconds";
                        description
                            "The time since this multicast router has been known
                             in this service.";
                    }

                    leaf expiry-time {
                        type uint32;
                        units "seconds";
                        description "The time remaining before this multicast router is aged out.";
                    }

                    container mld-v2-states {
                        description "Enter the mld-v2-states context";

                        leaf general-query-interval {
                            type uint32;
                            units "seconds";
                            description "The General Query Interval used by this multicast router.";
                        }

                        leaf general-response-interval {
                            type uint32;
                            units "seconds";
                            description
                                "The General Query Response interval used by this
                                 multicast router.";
                        }

                        leaf robust-count {
                            type uint32;
                            description "The Robust Count value used by this multicast router.";
                        }

                    } // container mld-v2-states

                    container port {
                        description "Enter the port context";

                        leaf port-type {
                            type enumeration {
                                enum sap                            { value 0; }
                                enum sdp                            { value 1; }
                                enum rvpls                          { value 2; }
                                enum vxlan                          { value 3; }
                                enum evpn-mpls                      { value 4; }
                            }
                        }

                        leaf sap-id {
                            type types-sros:sap;
                            description "SAP identifier.";
                        }

                        leaf sdp-bind-id {
                            type types-services:sdp-bind-id;
                            description "SDP Binding identifier.";
                        }

                        leaf rvpls-service-name {
                            type types-services:service-name;
                            description "RVPLS service identifier.";
                        }

                        leaf rvpls-interface-name {
                            type types-sros:interface-name;
                            description "RVPLS interface identifier.";
                        }

                        leaf vxlan-vtep {
                            type types-sros:ip-unicast-address;
                            description "VXLAN VTEP identifier.";
                        }

                        leaf vxlan-vni {
                            type types-services:vxlan-vni;
                            description "VXLAN VNI identifier.";
                        }

                    } // container port

                } // container querier

                list multicast-router {
                    key "address";
                    description "Enter the multicast-router list instance";

                    leaf address {
                        type types-sros:ipv6-address;
                        description
                            "The source IP address used by queries sent out by
                             this multicast router.";
                    }

                    leaf version {
                        type types-igmp:igmp-version;
                        description
                            "The version of the protocol that is sent by this
                             multicast router.";
                    }

                    leaf up-time {
                        type uint32;
                        units "seconds";
                        description
                            "The time since this multicast router has been known
                             in this service.";
                    }

                    leaf expiry-time {
                        type uint32;
                        units "seconds";
                        description "The time remaining before this multicast router is aged out.";
                    }

                    container mld-v2-states {
                        description "Enter the mld-v2-states context";

                        leaf general-query-interval {
                            type uint32;
                            units "seconds";
                            description "The General Query Interval used by this multicast router.";
                        }

                        leaf general-response-interval {
                            type uint32;
                            units "seconds";
                            description
                                "The General Query Response interval used by this
                                 multicast router.";
                        }

                        leaf robust-count {
                            type uint32;
                            description "The Robust Count value used by this multicast router.";
                        }

                    } // container mld-v2-states

                    container port {
                        description "Enter the port context";

                        leaf port-type {
                            type enumeration {
                                enum sap                            { value 0; }
                                enum sdp                            { value 1; }
                                enum rvpls                          { value 2; }
                                enum vxlan                          { value 3; }
                                enum evpn-mpls                      { value 4; }
                            }
                        }

                        leaf sap-id {
                            type types-sros:sap;
                            description "SAP identifier.";
                        }

                        leaf sdp-bind-id {
                            type types-services:sdp-bind-id;
                            description "SDP Binding identifier.";
                        }

                        leaf rvpls-service-name {
                            type types-services:service-name;
                            description "RVPLS service identifier.";
                        }

                        leaf rvpls-interface-name {
                            type types-sros:interface-name;
                            description "RVPLS interface identifier.";
                        }

                        leaf vxlan-vtep {
                            type types-sros:ip-unicast-address;
                            description "VXLAN VTEP identifier.";
                        }

                        leaf vxlan-vni {
                            type types-services:vxlan-vni;
                            description "VXLAN VNI identifier.";
                        }

                    } // container port

                } // list multicast-router

                list group {
                    key "group-address";
                    description "Enter the group list instance";

                    leaf group-address {
                        type types-sros:ipv6-multicast-address;
                        description "Group address of multicast channel.";
                    }

                    leaf filter-mode {
                        type types-igmp:filter-mode;
                    }

                    leaf up-time {
                        type uint32;
                        units "seconds";
                        description "The time elapsed since this entry was created.";
                    }

                    list source {
                        key "source-address";
                        description "Enter the source list instance";

                        leaf source-address {
                            type types-sros:ipv6-address;
                            description "Source address of multicast channel.";
                        }

                        leaf up-time {
                            type uint32;
                            units "seconds";
                            description "The time elapsed since this entry was created.";
                        }

                    } // list source

                } // list group

                list evpn-group {
                    key "group-address";
                    description "Enter the evpn-group list instance";

                    leaf group-address {
                        type types-sros:ipv6-multicast-address;
                        description "Group address of multicast channel.";
                    }

                    leaf filter-mode {
                        type types-igmp:filter-mode;
                    }

                    leaf up-time {
                        type uint32;
                        units "seconds";
                        description "The time elapsed since this entry was created.";
                    }

                    leaf v1-support {
                        type boolean;
                        description "Version 1 is supported.";
                    }

                    leaf v2-support {
                        type boolean;
                        description "Version 2 is supported.";
                    }

                    list source {
                        key "source-address";
                        description "Enter the source list instance";

                        leaf source-address {
                            type types-sros:ipv6-address;
                            description "Source address of multicast channel.";
                        }

                        leaf up-time {
                            type uint32;
                            units "seconds";
                            description "The time elapsed since this entry was created.";
                        }

                    } // list source

                } // list evpn-group

            } // container mld-snooping

            container pim-snooping {
                description "Enter the pim-snooping context";

                container ipv4 {
                    description "Enter the ipv4 context";

                    leaf oper-state {
                        type types-sros:oper-state;
                        description
                            "The value of the this object indicates the operational
                             state of PIM.";
                    }

                    leaf operational-mode {
                        type types-pim:pim-vpls-operational-mode;
                        description
                            "The value of the this object indicates the operational
                             mode of PIM.";
                    }

                    leaf designated-router {
                        type types-sros:ip-address;
                        description "The address of the designated router.";
                    }

                    leaf tracking-support {
                        type boolean;
                        description "The service's capability to disable Join message suppression.";
                    }

                    leaf up-time {
                        type uint32;
                        units "seconds";
                        description "The time elapsed since PIM snooping was enabled.";
                    }

                    list sg {
                        key "group-address source-address";
                        description "Enter the sg list instance";

                        leaf group-address {
                            type types-sros:ipv4-multicast-address;
                            description
                                "The IP multicast group address for which this entry contains information.
                                 If the source-type is 'starStarRP', the value of this object will
                                 be zero and source-address will contain the address of the RP.";
                        }

                        leaf source-address {
                            type types-sros:ipv4-address;
                            description
                                "The source address for which this entry contains information.
                                 If source-type is 'starG', the value of this object will be zero.
                                 If source-type is 'starstarRP', the value of this object will be address of the RP.";
                        }

                        leaf rpf-neighbor-address {
                            type types-sros:ip-address;
                            description "The address of the RPF neighbor.";
                        }

                        leaf rpt-rpf-neighbor-address {
                            type types-sros:ip-address;
                            description "The address of the RPF neighbor on the RPT.";
                        }

                        leaf upstream-join-prune-state {
                            type enumeration {
                                enum not-joined                     { value 0; }
                                enum joined                         { value 1; }
                            }
                            description "The Upstream Join Prune state.";
                        }

                        leaf upstream-join-prune-timer {
                            type uint32;
                            units "seconds";
                            description
                                "The time remaining before the service sends another
                                 Join message to it's upstream neighbor.";
                        }

                        leaf upstream-join-prune-rpt-state {
                            type enumeration {
                                enum not-joined-star-g              { value 0; }
                                enum not-pruned                     { value 1; }
                                enum pruned                         { value 2; }
                            }
                            description "The Upstream Join Prune Rpt state.";
                        }

                        leaf upstream-join-prune-rpt-timer {
                            type uint32;
                            units "seconds";
                            description
                                "the delay to triggered Join(S,G,rpt) messages to prevent
                                 implosions of triggered messages.";
                        }

                        leaf join-or-prune-port-count {
                            type yang:gauge32;
                            description
                                "The number of ports on which the service received a Join or Prune message for
                                 this source group combination.";
                        }

                        leaf immediate-out-port-count {
                            type yang:gauge32;
                            description
                                "The number of ports in the immediate outgoing interface list. An outgoing
                                 list can be 'immediate' if it is built directly from the state of
                                 the relevant type as indicated by source-type.";
                        }

                        leaf inherited-out-port-count {
                            type yang:gauge32;
                            description
                                "The number of ports in the inherited outgoing interface list. An 'inherited'
                                 list inherits state from other types.";
                        }

                        leaf inherited-rpt-out-port-count {
                            type yang:gauge32;
                            description "The number of ports in the inherited outgoing interface list for (S,G,Rpt).";
                        }

                        leaf port-count {
                            type yang:gauge32;
                            description
                                "The number of ports on which the service received messages for this source group
                                 combination.";
                        }

                        leaf up-time {
                            type uint32;
                            units "seconds";
                            description "The time since this source group entry got created.";
                        }

                        container rpf-port {
                            description "Enter the rpf-port context";

                            leaf port-type {
                                type enumeration {
                                    enum sap                            { value 0; }
                                    enum sdp                            { value 1; }
                                    enum rvpls                          { value 2; }
                                    enum vxlan                          { value 3; }
                                    enum evpn-mpls                      { value 4; }
                                }
                            }

                            leaf sap-id {
                                type types-sros:sap;
                                description "SAP identifier.";
                            }

                            leaf sdp-bind-id {
                                type types-services:sdp-bind-id;
                                description "SDP Binding identifier.";
                            }

                            leaf rvpls-service-name {
                                type types-services:service-name;
                                description "RVPLS service identifier.";
                            }

                            leaf rvpls-interface-name {
                                type types-sros:interface-name;
                                description "RVPLS interface identifier.";
                            }

                            leaf vxlan-vtep {
                                type types-sros:ip-unicast-address;
                                description "VXLAN VTEP identifier.";
                            }

                            leaf vxlan-vni {
                                type types-services:vxlan-vni;
                                description "VXLAN VNI identifier.";
                            }

                        } // container rpf-port

                        list sap {
                            key "sap-id";
                            description "Enter the sap list instance";

                            leaf sap-id {
                                type types-sros:sap;
                                description "SAP identifier";
                            }

                            leaf port-flags {
                                type types-pim:vpls-sg-flags;
                                description "Set of lists to which this port belongs";
                            }

                        } // list sap

                        list spoke-sdp {
                            key "sdp-bind-id";
                            description "Enter the spoke-sdp list instance";

                            leaf sdp-bind-id {
                                type types-services:sdp-bind-id;
                                description
                                    "SDP Binding identifier as <sdp-id>:<vc-id>.
                                     sdp-id - [1..32767]
                                     vc-id - [1..4294967295].";
                            }

                            leaf port-flags {
                                type types-pim:vpls-sg-flags;
                                description "Set of lists to which this port belongs";
                            }

                        } // list spoke-sdp

                        container evpn-mpls {
                            description "Enter the evpn-mpls context";

                            leaf port-flags {
                                type types-pim:vpls-sg-flags;
                                description "Set of lists to which this port belongs";
                            }

                        } // container evpn-mpls

                        list vxlan {
                            key "vtep vni";
                            description "Enter the vxlan list instance";

                            leaf vtep {
                                type types-sros:ip-unicast-address;
                            }

                            leaf vni {
                                type types-services:vxlan-vni;
                            }

                            leaf port-flags {
                                type types-pim:vpls-sg-flags;
                                description "Set of lists to which this port belongs";
                            }

                        } // list vxlan

                        list rvpls {
                            key "routed-service-name routed-interface-name";
                            description "Enter the rvpls list instance";

                            leaf routed-service-name {
                                type types-services:service-name;
                                description "Service name.";
                            }

                            leaf routed-interface-name {
                                type types-sros:interface-name;
                                description "Router interface name.";
                            }

                            leaf port-flags {
                                type types-pim:vpls-sg-flags;
                                description "Set of lists to which this port belongs";
                            }

                        } // list rvpls

                    } // list sg

                    container statistics {
                        description "Enter the statistics context";

                        leaf sg-count {
                            type yang:gauge32;
                            description "The number of sg entries for which the source address is not null.";
                        }

                        leaf star-g-count {
                            type yang:gauge32;
                            description "The number of sg entries for which the source address is null.";
                        }

                    } // container statistics

                } // container ipv4

                container ipv6 {
                    description "Enter the ipv6 context";

                    leaf oper-state {
                        type types-sros:oper-state;
                        description
                            "The value of the this object indicates the operational
                             state of PIM.";
                    }

                    leaf operational-mode {
                        type types-pim:pim-vpls-operational-mode;
                        description
                            "The value of the this object indicates the operational
                             mode of PIM.";
                    }

                    leaf designated-router {
                        type types-sros:ip-address;
                        description "The address of the designated router.";
                    }

                    leaf tracking-support {
                        type boolean;
                        description "The service's capability to disable Join message suppression.";
                    }

                    leaf up-time {
                        type uint32;
                        units "seconds";
                        description "The time elapsed since PIM snooping was enabled.";
                    }

                    list sg {
                        key "group-address source-address";
                        description "Enter the sg list instance";

                        leaf group-address {
                            type types-sros:ipv6-multicast-address;
                            description
                                "The IP multicast group address for which this entry contains information.
                                 If the source-type is 'starStarRP', the value of this object will
                                 be zero and source-address will contain the address of the RP.";
                        }

                        leaf source-address {
                            type types-sros:ipv6-address;
                            description
                                "The source address for which this entry contains information.
                                 If source-type is 'starG', the value of this object will be zero.
                                 If source-type is 'starstarRP', the value of this object will be address of the RP.";
                        }

                        leaf rpf-neighbor-address {
                            type types-sros:ip-address;
                            description "The address of the RPF neighbor.";
                        }

                        leaf rpt-rpf-neighbor-address {
                            type types-sros:ip-address;
                            description "The address of the RPF neighbor on the RPT.";
                        }

                        leaf upstream-join-prune-state {
                            type enumeration {
                                enum not-joined                     { value 0; }
                                enum joined                         { value 1; }
                            }
                            description "The Upstream Join Prune state.";
                        }

                        leaf upstream-join-prune-timer {
                            type uint32;
                            units "seconds";
                            description
                                "The time remaining before the service sends another
                                 Join message to it's upstream neighbor.";
                        }

                        leaf upstream-join-prune-rpt-state {
                            type enumeration {
                                enum not-joined-star-g              { value 0; }
                                enum not-pruned                     { value 1; }
                                enum pruned                         { value 2; }
                            }
                            description "The Upstream Join Prune Rpt state.";
                        }

                        leaf upstream-join-prune-rpt-timer {
                            type uint32;
                            units "seconds";
                            description
                                "the delay to triggered Join(S,G,rpt) messages to prevent
                                 implosions of triggered messages.";
                        }

                        leaf join-or-prune-port-count {
                            type yang:gauge32;
                            description
                                "The number of ports on which the service received a Join or Prune message for
                                 this source group combination.";
                        }

                        leaf immediate-out-port-count {
                            type yang:gauge32;
                            description
                                "The number of ports in the immediate outgoing interface list. An outgoing
                                 list can be 'immediate' if it is built directly from the state of
                                 the relevant type as indicated by source-type.";
                        }

                        leaf inherited-out-port-count {
                            type yang:gauge32;
                            description
                                "The number of ports in the inherited outgoing interface list. An 'inherited'
                                 list inherits state from other types.";
                        }

                        leaf inherited-rpt-out-port-count {
                            type yang:gauge32;
                            description "The number of ports in the inherited outgoing interface list for (S,G,Rpt).";
                        }

                        leaf port-count {
                            type yang:gauge32;
                            description
                                "The number of ports on which the service received messages for this source group
                                 combination.";
                        }

                        leaf up-time {
                            type uint32;
                            units "seconds";
                            description "The time since this source group entry got created.";
                        }

                        container rpf-port {
                            description "Enter the rpf-port context";

                            leaf port-type {
                                type enumeration {
                                    enum sap                            { value 0; }
                                    enum sdp                            { value 1; }
                                    enum rvpls                          { value 2; }
                                    enum vxlan                          { value 3; }
                                    enum evpn-mpls                      { value 4; }
                                }
                            }

                            leaf sap-id {
                                type types-sros:sap;
                                description "SAP identifier.";
                            }

                            leaf sdp-bind-id {
                                type types-services:sdp-bind-id;
                                description "SDP Binding identifier.";
                            }

                            leaf rvpls-service-name {
                                type types-services:service-name;
                                description "RVPLS service identifier.";
                            }

                            leaf rvpls-interface-name {
                                type types-sros:interface-name;
                                description "RVPLS interface identifier.";
                            }

                            leaf vxlan-vtep {
                                type types-sros:ip-unicast-address;
                                description "VXLAN VTEP identifier.";
                            }

                            leaf vxlan-vni {
                                type types-services:vxlan-vni;
                                description "VXLAN VNI identifier.";
                            }

                        } // container rpf-port

                        list sap {
                            key "sap-id";
                            description "Enter the sap list instance";

                            leaf sap-id {
                                type types-sros:sap;
                                description "SAP identifier";
                            }

                            leaf port-flags {
                                type types-pim:vpls-sg-flags;
                                description "Set of lists to which this port belongs";
                            }

                        } // list sap

                        list spoke-sdp {
                            key "sdp-bind-id";
                            description "Enter the spoke-sdp list instance";

                            leaf sdp-bind-id {
                                type types-services:sdp-bind-id;
                                description
                                    "SDP Binding identifier as <sdp-id>:<vc-id>.
                                     sdp-id - [1..32767]
                                     vc-id - [1..4294967295].";
                            }

                            leaf port-flags {
                                type types-pim:vpls-sg-flags;
                                description "Set of lists to which this port belongs";
                            }

                        } // list spoke-sdp

                        container evpn-mpls {
                            description "Enter the evpn-mpls context";

                            leaf port-flags {
                                type types-pim:vpls-sg-flags;
                                description "Set of lists to which this port belongs";
                            }

                        } // container evpn-mpls

                        list vxlan {
                            key "vtep vni";
                            description "Enter the vxlan list instance";

                            leaf vtep {
                                type types-sros:ip-unicast-address;
                            }

                            leaf vni {
                                type types-services:vxlan-vni;
                            }

                            leaf port-flags {
                                type types-pim:vpls-sg-flags;
                                description "Set of lists to which this port belongs";
                            }

                        } // list vxlan

                        list rvpls {
                            key "routed-service-name routed-interface-name";
                            description "Enter the rvpls list instance";

                            leaf routed-service-name {
                                type types-services:service-name;
                                description "Service name.";
                            }

                            leaf routed-interface-name {
                                type types-sros:interface-name;
                                description "Router interface name.";
                            }

                            leaf port-flags {
                                type types-pim:vpls-sg-flags;
                                description "Set of lists to which this port belongs";
                            }

                        } // list rvpls

                    } // list sg

                    container statistics {
                        description "Enter the statistics context";

                        leaf sg-count {
                            type yang:gauge32;
                            description "The number of sg entries for which the source address is not null.";
                        }

                        leaf star-g-count {
                            type yang:gauge32;
                            description "The number of sg entries for which the source address is null.";
                        }

                    } // container statistics

                } // container ipv6

                container evpn-mpls {
                    description "Enter the evpn-mpls context";

                    container ipv4 {
                        description "Enter the ipv4 context";

                        leaf oper-state {
                            type types-sros:oper-state;
                            description
                                "The value of the this object indicates the operational
                                 state of PIM for this interface.";
                        }

                        leaf up-time {
                            type uint32;
                            units "seconds";
                            description "The time since this interface became operational.";
                        }

                        leaf group-count {
                            type uint32;
                            description
                                "The number of multicast groups which currently have this
                                 interface as an outgoing interface.";
                        }

                        leaf maximum-groups-until-now {
                            type uint32;
                            description "The highest value that 'group-count' had till now.";
                        }

                        leaf pseudo-wire-forwarder {
                            type boolean;
                            description
                                "Whether this interface is the forwarding interface
                                 of a pair of redundant pseudo-wire ports.";
                        }

                        container statistics {
                            description "Enter the statistics context";

                            leaf rx-packets {
                                type yang:counter32;
                                description "The number of multicast data packets received on this interface.";
                            }

                            leaf rx-hellos {
                                type yang:counter32;
                                description "The number of PIM hello messages received on this interface.";
                            }

                            leaf rx-join-prunes {
                                type yang:counter32;
                                description
                                    "The number of PIM
                                     Join Prune messages received on this interface.";
                            }

                            leaf tx-packets {
                                type yang:counter32;
                                description "The number of multicast data packets transmitted on this interface.";
                            }

                            leaf tx-join-prunes {
                                type yang:counter32;
                                description
                                    "The number of PIM
                                     Join Prune messages transmitted on this interface.";
                            }

                            leaf rx-hellos-dropped {
                                type yang:counter32;
                                description
                                    "The number of PIM Hello messages which were received on this interface but were
                                     dropped.";
                            }

                            leaf rx-neighbor-unknown {
                                type yang:counter32;
                                description
                                    "The number of PIM messages (other than Hello messages) which were received on this
                                     interface and were rejected because the adjacency with the neighbor
                                     router was not already established.";
                            }

                            leaf rx-bad-checksum-discard {
                                type yang:counter32;
                                description
                                    "The number of PIM messages received on this interface which were discarded because
                                     of bad checksum.";
                            }

                            leaf rx-bad-version-discard {
                                type yang:counter32;
                                description "The number of PIM messages with bad versions received on this interface.";
                            }

                            leaf rx-bad-encodings {
                                type yang:counter32;
                                description "The number of PIM messages with bad encodings received on this interface.";
                            }

                            leaf join-policy-drops {
                                type yang:counter32;
                                description
                                    "The number of times the join policy match resulted in dropping PIM Join-Prune
                                     Message or one of the source group contained in the message.";
                            }

                            leaf rx-join-prune-errors {
                                type yang:counter32;
                                description
                                    "The number of errors while processing Join-Prune messages received on this
                                     interface.";
                            }

                        } // container statistics

                        list neighbor {
                            key "neighbor-address";
                            description "Enter the neighbor list instance";

                            leaf neighbor-address {
                                type types-sros:ipv4-address;
                                description "This value indicates the IPv4 address of the PIM neighbor.";
                            }

                            leaf dr-priority {
                                type uint32;
                                description
                                    "This value indicates neighbor's DR priority which is received
                                     in the hello message. If the Hello Message did not contain
                                     the DR priority field, the value of priority will be '1'.";
                            }

                            leaf dr-priority-present {
                                type boolean;
                                description
                                    "This value of indicates whether the DR priority field was present
                                     in the Hello message received from the PIM neighbor.";
                            }

                            leaf tracking-support {
                                type boolean;
                                description
                                    "This value indicates whether the T bit in the LAN Prune Delay
                                     option was present in the Hello message. This indicates the
                                     neighbor's capability to disable Join message suppression.";
                            }

                            leaf lan-delay {
                                type uint32;
                                units "milliseconds";
                                description
                                    "This value indicates the value of lan delay field present in
                                     the Hello message received from the neighbor. ";
                            }

                            leaf lan-delay-present {
                                type boolean;
                                description
                                    "This value indicates whether the Hello message received from
                                     the neighbor contained the Lan Delay field.";
                            }

                            leaf generated-id {
                                type uint32;
                                description
                                    "This value indicates a randomly generated 32-bit value that is
                                     regenerated each time PIM forwarding is started or restarted on
                                     the interface, including when the router itself restarts.";
                            }

                            leaf override-interval {
                                type uint32;
                                units "milliseconds";
                                description
                                    "This value indicates the value of the override interval present
                                     in the Hello message.";
                            }

                            leaf up-time {
                                type uint32;
                                units "seconds";
                                description
                                    "This value indicates the time since this PIM neighbor (last)
                                     became a neighbor of the local router.";
                            }

                            leaf expiry-time {
                                type uint32;
                                units "seconds";
                                description
                                    "This value indicates the minimum time remaining before this
                                     PIM neighbor will be aged out.";
                            }

                            leaf hold-time {
                                type uint32;
                                units "seconds";
                                description
                                    "This value indicates the value of the hold time present in the
                                     Hello message.";
                            }

                            leaf join-attribute-support {
                                type boolean;
                                description
                                    "This value indicates whether the Hello Message received from
                                     the neighbor contained the Join Attribute field.";
                            }

                            list secondary-neighbor {
                                key "secondary-neighbor-address";
                                description "Enter the secondary-neighbor list instance";

                                leaf secondary-neighbor-address {
                                    type types-sros:ipv4-address;
                                    description
                                        "This value indicates the IPv4 address of the secondary PIM
                                         neighbor.";
                                }

                            } // list secondary-neighbor

                        } // list neighbor

                        list sg {
                            key "group-address source-address";
                            description "Enter the sg list instance";

                            leaf group-address {
                                type types-sros:ipv4-address;
                                description "The multicast group address of the entry.";
                            }

                            leaf source-address {
                                type types-sros:ipv4-address;
                                description "The source address of the multicast sender.";
                            }

                            leaf up-time {
                                type uint32;
                                units "seconds";
                                description "The time since this source group entry got created.";
                            }

                            leaf join-prune-state {
                                type types-pim:join-prune-state;
                                description
                                    "The Join Prune state for this entry on the interface.

                                     PIM Join or Prune messages are sent by the downstream routers
                                     towards the RPF' neighbor.";
                            }

                            leaf join-prune-timer {
                                type uint32;
                                units "seconds";
                                description
                                    "The time remaining before the router transitions the value of
                                     join-prune-state to 'no-info'.

                                     The timer is started or restarted when a valid Join message is
                                     received. If the value of this object is zero and
                                     join-prune-state is 'join' state, it means that the
                                     downstream router sent a holdtime of '0xffff'. In this case,
                                     join-prune-state will not transition until an appropriate
                                     cancelling of Join or Prune message is received.";
                            }

                            leaf prune-pending-timer {
                                type uint32;
                                units "seconds";
                                description
                                    "The time remaining before the router transitions the value of
                                     join-prune-state to 'no-info'.

                                     The timer is set when the PIM Prune message is received.";
                            }

                            leaf join-prune-rpt-state {
                                type types-pim:join-prune-state;
                                description
                                    "The Join Prune Rpt state for this entry on the interface.

                                     PIM Join or Prune messages are sent by the downstream routers towards the
                                     RPF' neighbor. (S,G,rpt) state is a result of receiving (S,G, rpt) JP message
                                     from the downstream router on the RP tree.";
                            }

                            leaf join-prune-rpt-timer {
                                type uint32;
                                units "seconds";
                                description
                                    "The time remaining before the router transitions the value of
                                     join-prune-rpt-state to 'no-info'.

                                     The timer is started or restarted when a valid Join message is
                                     received. If the value of this object is zero and
                                     join-prune-rpt-state is in 'join' state, it means that the
                                     downstream router sent a holdtime of '0xffff'. In this case,
                                     join-prune-rpt-state will not transition until an appropriate
                                     cancelling of Join or Prune message is received from the
                                     downstream router.";
                            }

                            leaf join-prune-rpt-pending-timer {
                                type uint32;
                                units "seconds";
                                description
                                    "The time remaining before the router transitions the value of
                                     join-prune-rpt-state to 'no-info'.

                                     The timer is set when the (S,G,rpt) PIM Prune message is received.";
                            }

                        } // list sg

                    } // container ipv4

                    container ipv6 {
                        description "Enter the ipv6 context";

                        leaf oper-state {
                            type types-sros:oper-state;
                            description
                                "The value of the this object indicates the operational
                                 state of PIM for this interface.";
                        }

                        leaf up-time {
                            type uint32;
                            units "seconds";
                            description "The time since this interface became operational.";
                        }

                        leaf group-count {
                            type uint32;
                            description
                                "The number of multicast groups which currently have this
                                 interface as an outgoing interface.";
                        }

                        leaf maximum-groups-until-now {
                            type uint32;
                            description "The highest value that 'group-count' had till now.";
                        }

                        leaf pseudo-wire-forwarder {
                            type boolean;
                            description
                                "Whether this interface is the forwarding interface
                                 of a pair of redundant pseudo-wire ports.";
                        }

                        container statistics {
                            description "Enter the statistics context";

                            leaf rx-packets {
                                type yang:counter32;
                                description "The number of multicast data packets received on this interface.";
                            }

                            leaf rx-hellos {
                                type yang:counter32;
                                description "The number of PIM hello messages received on this interface.";
                            }

                            leaf rx-join-prunes {
                                type yang:counter32;
                                description
                                    "The number of PIM
                                     Join Prune messages received on this interface.";
                            }

                            leaf tx-packets {
                                type yang:counter32;
                                description "The number of multicast data packets transmitted on this interface.";
                            }

                            leaf tx-join-prunes {
                                type yang:counter32;
                                description
                                    "The number of PIM
                                     Join Prune messages transmitted on this interface.";
                            }

                            leaf rx-hellos-dropped {
                                type yang:counter32;
                                description
                                    "The number of PIM Hello messages which were received on this interface but were
                                     dropped.";
                            }

                            leaf rx-neighbor-unknown {
                                type yang:counter32;
                                description
                                    "The number of PIM messages (other than Hello messages) which were received on this
                                     interface and were rejected because the adjacency with the neighbor
                                     router was not already established.";
                            }

                            leaf rx-bad-checksum-discard {
                                type yang:counter32;
                                description
                                    "The number of PIM messages received on this interface which were discarded because
                                     of bad checksum.";
                            }

                            leaf rx-bad-version-discard {
                                type yang:counter32;
                                description "The number of PIM messages with bad versions received on this interface.";
                            }

                            leaf rx-bad-encodings {
                                type yang:counter32;
                                description "The number of PIM messages with bad encodings received on this interface.";
                            }

                            leaf join-policy-drops {
                                type yang:counter32;
                                description
                                    "The number of times the join policy match resulted in dropping PIM Join-Prune
                                     Message or one of the source group contained in the message.";
                            }

                            leaf rx-join-prune-errors {
                                type yang:counter32;
                                description
                                    "The number of errors while processing Join-Prune messages received on this
                                     interface.";
                            }

                        } // container statistics

                        list neighbor {
                            key "neighbor-address";
                            description "Enter the neighbor list instance";

                            leaf neighbor-address {
                                type types-sros:ipv6-address;
                                description "This value indicates the IPv6 address of the PIM neighbor.";
                            }

                            leaf dr-priority {
                                type uint32;
                                description
                                    "This value indicates neighbor's DR priority which is received
                                     in the hello message. If the Hello Message did not contain
                                     the DR priority field, the value of priority will be '1'.";
                            }

                            leaf dr-priority-present {
                                type boolean;
                                description
                                    "This value of indicates whether the DR priority field was present
                                     in the Hello message received from the PIM neighbor.";
                            }

                            leaf tracking-support {
                                type boolean;
                                description
                                    "This value indicates whether the T bit in the LAN Prune Delay
                                     option was present in the Hello message. This indicates the
                                     neighbor's capability to disable Join message suppression.";
                            }

                            leaf lan-delay {
                                type uint32;
                                units "milliseconds";
                                description
                                    "This value indicates the value of lan delay field present in
                                     the Hello message received from the neighbor. ";
                            }

                            leaf lan-delay-present {
                                type boolean;
                                description
                                    "This value indicates whether the Hello message received from
                                     the neighbor contained the Lan Delay field.";
                            }

                            leaf generated-id {
                                type uint32;
                                description
                                    "This value indicates a randomly generated 32-bit value that is
                                     regenerated each time PIM forwarding is started or restarted on
                                     the interface, including when the router itself restarts.";
                            }

                            leaf override-interval {
                                type uint32;
                                units "milliseconds";
                                description
                                    "This value indicates the value of the override interval present
                                     in the Hello message.";
                            }

                            leaf up-time {
                                type uint32;
                                units "seconds";
                                description
                                    "This value indicates the time since this PIM neighbor (last)
                                     became a neighbor of the local router.";
                            }

                            leaf expiry-time {
                                type uint32;
                                units "seconds";
                                description
                                    "This value indicates the minimum time remaining before this
                                     PIM neighbor will be aged out.";
                            }

                            leaf hold-time {
                                type uint32;
                                units "seconds";
                                description
                                    "This value indicates the value of the hold time present in the
                                     Hello message.";
                            }

                            leaf join-attribute-support {
                                type boolean;
                                description
                                    "This value indicates whether the Hello Message received from
                                     the neighbor contained the Join Attribute field.";
                            }

                            list secondary-neighbor {
                                key "secondary-neighbor-address";
                                description "Enter the secondary-neighbor list instance";

                                leaf secondary-neighbor-address {
                                    type types-sros:ipv6-address;
                                    description
                                        "This value indicates the IPv6 address of the secondary PIM
                                         neighbor.";
                                }

                            } // list secondary-neighbor

                        } // list neighbor

                        list sg {
                            key "group-address source-address";
                            description "Enter the sg list instance";

                            leaf group-address {
                                type types-sros:ipv6-address;
                                description "The multicast group address of the entry.";
                            }

                            leaf source-address {
                                type types-sros:ipv6-address;
                                description "The source address of the multicast sender.";
                            }

                            leaf up-time {
                                type uint32;
                                units "seconds";
                                description "The time since this source group entry got created.";
                            }

                            leaf join-prune-state {
                                type types-pim:join-prune-state;
                                description
                                    "The Join Prune state for this entry on the interface.

                                     PIM Join or Prune messages are sent by the downstream routers
                                     towards the RPF' neighbor.";
                            }

                            leaf join-prune-timer {
                                type uint32;
                                units "seconds";
                                description
                                    "The time remaining before the router transitions the value of
                                     join-prune-state to 'no-info'.

                                     The timer is started or restarted when a valid Join message is
                                     received. If the value of this object is zero and
                                     join-prune-state is 'join' state, it means that the
                                     downstream router sent a holdtime of '0xffff'. In this case,
                                     join-prune-state will not transition until an appropriate
                                     cancelling of Join or Prune message is received.";
                            }

                            leaf prune-pending-timer {
                                type uint32;
                                units "seconds";
                                description
                                    "The time remaining before the router transitions the value of
                                     join-prune-state to 'no-info'.

                                     The timer is set when the PIM Prune message is received.";
                            }

                            leaf join-prune-rpt-state {
                                type types-pim:join-prune-state;
                                description
                                    "The Join Prune Rpt state for this entry on the interface.

                                     PIM Join or Prune messages are sent by the downstream routers towards the
                                     RPF' neighbor. (S,G,rpt) state is a result of receiving (S,G, rpt) JP message
                                     from the downstream router on the RP tree.";
                            }

                            leaf join-prune-rpt-timer {
                                type uint32;
                                units "seconds";
                                description
                                    "The time remaining before the router transitions the value of
                                     join-prune-rpt-state to 'no-info'.

                                     The timer is started or restarted when a valid Join message is
                                     received. If the value of this object is zero and
                                     join-prune-rpt-state is in 'join' state, it means that the
                                     downstream router sent a holdtime of '0xffff'. In this case,
                                     join-prune-rpt-state will not transition until an appropriate
                                     cancelling of Join or Prune message is received from the
                                     downstream router.";
                            }

                            leaf join-prune-rpt-pending-timer {
                                type uint32;
                                units "seconds";
                                description
                                    "The time remaining before the router transitions the value of
                                     join-prune-rpt-state to 'no-info'.

                                     The timer is set when the (S,G,rpt) PIM Prune message is received.";
                            }

                        } // list sg

                    } // container ipv6

                } // container evpn-mpls

                container routed-vpls {
                    description "Enter the routed-vpls context";

                    container ipv4 {
                        description "Enter the ipv4 context";

                        leaf oper-state {
                            type types-sros:oper-state;
                            description
                                "The value of the this object indicates the operational
                                 state of PIM for this interface.";
                        }

                        leaf up-time {
                            type uint32;
                            units "seconds";
                            description "The time since this interface became operational.";
                        }

                        leaf group-count {
                            type uint32;
                            description
                                "The number of multicast groups which currently have this
                                 interface as an outgoing interface.";
                        }

                        leaf maximum-groups-until-now {
                            type uint32;
                            description "The highest value that 'group-count' had till now.";
                        }

                        leaf pseudo-wire-forwarder {
                            type boolean;
                            description
                                "Whether this interface is the forwarding interface
                                 of a pair of redundant pseudo-wire ports.";
                        }

                        container statistics {
                            description "Enter the statistics context";

                            leaf rx-packets {
                                type yang:counter32;
                                description "The number of multicast data packets received on this interface.";
                            }

                            leaf rx-hellos {
                                type yang:counter32;
                                description "The number of PIM hello messages received on this interface.";
                            }

                            leaf rx-join-prunes {
                                type yang:counter32;
                                description
                                    "The number of PIM
                                     Join Prune messages received on this interface.";
                            }

                            leaf tx-packets {
                                type yang:counter32;
                                description "The number of multicast data packets transmitted on this interface.";
                            }

                            leaf tx-join-prunes {
                                type yang:counter32;
                                description
                                    "The number of PIM
                                     Join Prune messages transmitted on this interface.";
                            }

                            leaf rx-hellos-dropped {
                                type yang:counter32;
                                description
                                    "The number of PIM Hello messages which were received on this interface but were
                                     dropped.";
                            }

                            leaf rx-neighbor-unknown {
                                type yang:counter32;
                                description
                                    "The number of PIM messages (other than Hello messages) which were received on this
                                     interface and were rejected because the adjacency with the neighbor
                                     router was not already established.";
                            }

                            leaf rx-bad-checksum-discard {
                                type yang:counter32;
                                description
                                    "The number of PIM messages received on this interface which were discarded because
                                     of bad checksum.";
                            }

                            leaf rx-bad-version-discard {
                                type yang:counter32;
                                description "The number of PIM messages with bad versions received on this interface.";
                            }

                            leaf rx-bad-encodings {
                                type yang:counter32;
                                description "The number of PIM messages with bad encodings received on this interface.";
                            }

                            leaf join-policy-drops {
                                type yang:counter32;
                                description
                                    "The number of times the join policy match resulted in dropping PIM Join-Prune
                                     Message or one of the source group contained in the message.";
                            }

                            leaf rx-join-prune-errors {
                                type yang:counter32;
                                description
                                    "The number of errors while processing Join-Prune messages received on this
                                     interface.";
                            }

                        } // container statistics

                        list neighbor {
                            key "neighbor-address";
                            description "Enter the neighbor list instance";

                            leaf neighbor-address {
                                type types-sros:ipv4-address;
                                description "This value indicates the IPv4 address of the PIM neighbor.";
                            }

                            leaf dr-priority {
                                type uint32;
                                description
                                    "This value indicates neighbor's DR priority which is received
                                     in the hello message. If the Hello Message did not contain
                                     the DR priority field, the value of priority will be '1'.";
                            }

                            leaf dr-priority-present {
                                type boolean;
                                description
                                    "This value of indicates whether the DR priority field was present
                                     in the Hello message received from the PIM neighbor.";
                            }

                            leaf tracking-support {
                                type boolean;
                                description
                                    "This value indicates whether the T bit in the LAN Prune Delay
                                     option was present in the Hello message. This indicates the
                                     neighbor's capability to disable Join message suppression.";
                            }

                            leaf lan-delay {
                                type uint32;
                                units "milliseconds";
                                description
                                    "This value indicates the value of lan delay field present in
                                     the Hello message received from the neighbor. ";
                            }

                            leaf lan-delay-present {
                                type boolean;
                                description
                                    "This value indicates whether the Hello message received from
                                     the neighbor contained the Lan Delay field.";
                            }

                            leaf generated-id {
                                type uint32;
                                description
                                    "This value indicates a randomly generated 32-bit value that is
                                     regenerated each time PIM forwarding is started or restarted on
                                     the interface, including when the router itself restarts.";
                            }

                            leaf override-interval {
                                type uint32;
                                units "milliseconds";
                                description
                                    "This value indicates the value of the override interval present
                                     in the Hello message.";
                            }

                            leaf up-time {
                                type uint32;
                                units "seconds";
                                description
                                    "This value indicates the time since this PIM neighbor (last)
                                     became a neighbor of the local router.";
                            }

                            leaf expiry-time {
                                type uint32;
                                units "seconds";
                                description
                                    "This value indicates the minimum time remaining before this
                                     PIM neighbor will be aged out.";
                            }

                            leaf hold-time {
                                type uint32;
                                units "seconds";
                                description
                                    "This value indicates the value of the hold time present in the
                                     Hello message.";
                            }

                            leaf join-attribute-support {
                                type boolean;
                                description
                                    "This value indicates whether the Hello Message received from
                                     the neighbor contained the Join Attribute field.";
                            }

                            list secondary-neighbor {
                                key "secondary-neighbor-address";
                                description "Enter the secondary-neighbor list instance";

                                leaf secondary-neighbor-address {
                                    type types-sros:ipv4-address;
                                    description
                                        "This value indicates the IPv4 address of the secondary PIM
                                         neighbor.";
                                }

                            } // list secondary-neighbor

                        } // list neighbor

                        list sg {
                            key "group-address source-address";
                            description "Enter the sg list instance";

                            leaf group-address {
                                type types-sros:ipv4-address;
                                description "The multicast group address of the entry.";
                            }

                            leaf source-address {
                                type types-sros:ipv4-address;
                                description "The source address of the multicast sender.";
                            }

                            leaf up-time {
                                type uint32;
                                units "seconds";
                                description "The time since this source group entry got created.";
                            }

                            leaf join-prune-state {
                                type types-pim:join-prune-state;
                                description
                                    "The Join Prune state for this entry on the interface.

                                     PIM Join or Prune messages are sent by the downstream routers
                                     towards the RPF' neighbor.";
                            }

                            leaf join-prune-timer {
                                type uint32;
                                units "seconds";
                                description
                                    "The time remaining before the router transitions the value of
                                     join-prune-state to 'no-info'.

                                     The timer is started or restarted when a valid Join message is
                                     received. If the value of this object is zero and
                                     join-prune-state is 'join' state, it means that the
                                     downstream router sent a holdtime of '0xffff'. In this case,
                                     join-prune-state will not transition until an appropriate
                                     cancelling of Join or Prune message is received.";
                            }

                            leaf prune-pending-timer {
                                type uint32;
                                units "seconds";
                                description
                                    "The time remaining before the router transitions the value of
                                     join-prune-state to 'no-info'.

                                     The timer is set when the PIM Prune message is received.";
                            }

                            leaf join-prune-rpt-state {
                                type types-pim:join-prune-state;
                                description
                                    "The Join Prune Rpt state for this entry on the interface.

                                     PIM Join or Prune messages are sent by the downstream routers towards the
                                     RPF' neighbor. (S,G,rpt) state is a result of receiving (S,G, rpt) JP message
                                     from the downstream router on the RP tree.";
                            }

                            leaf join-prune-rpt-timer {
                                type uint32;
                                units "seconds";
                                description
                                    "The time remaining before the router transitions the value of
                                     join-prune-rpt-state to 'no-info'.

                                     The timer is started or restarted when a valid Join message is
                                     received. If the value of this object is zero and
                                     join-prune-rpt-state is in 'join' state, it means that the
                                     downstream router sent a holdtime of '0xffff'. In this case,
                                     join-prune-rpt-state will not transition until an appropriate
                                     cancelling of Join or Prune message is received from the
                                     downstream router.";
                            }

                            leaf join-prune-rpt-pending-timer {
                                type uint32;
                                units "seconds";
                                description
                                    "The time remaining before the router transitions the value of
                                     join-prune-rpt-state to 'no-info'.

                                     The timer is set when the (S,G,rpt) PIM Prune message is received.";
                            }

                        } // list sg

                    } // container ipv4

                    container ipv6 {
                        description "Enter the ipv6 context";

                        leaf oper-state {
                            type types-sros:oper-state;
                            description
                                "The value of the this object indicates the operational
                                 state of PIM for this interface.";
                        }

                        leaf up-time {
                            type uint32;
                            units "seconds";
                            description "The time since this interface became operational.";
                        }

                        leaf group-count {
                            type uint32;
                            description
                                "The number of multicast groups which currently have this
                                 interface as an outgoing interface.";
                        }

                        leaf maximum-groups-until-now {
                            type uint32;
                            description "The highest value that 'group-count' had till now.";
                        }

                        leaf pseudo-wire-forwarder {
                            type boolean;
                            description
                                "Whether this interface is the forwarding interface
                                 of a pair of redundant pseudo-wire ports.";
                        }

                        container statistics {
                            description "Enter the statistics context";

                            leaf rx-packets {
                                type yang:counter32;
                                description "The number of multicast data packets received on this interface.";
                            }

                            leaf rx-hellos {
                                type yang:counter32;
                                description "The number of PIM hello messages received on this interface.";
                            }

                            leaf rx-join-prunes {
                                type yang:counter32;
                                description
                                    "The number of PIM
                                     Join Prune messages received on this interface.";
                            }

                            leaf tx-packets {
                                type yang:counter32;
                                description "The number of multicast data packets transmitted on this interface.";
                            }

                            leaf tx-join-prunes {
                                type yang:counter32;
                                description
                                    "The number of PIM
                                     Join Prune messages transmitted on this interface.";
                            }

                            leaf rx-hellos-dropped {
                                type yang:counter32;
                                description
                                    "The number of PIM Hello messages which were received on this interface but were
                                     dropped.";
                            }

                            leaf rx-neighbor-unknown {
                                type yang:counter32;
                                description
                                    "The number of PIM messages (other than Hello messages) which were received on this
                                     interface and were rejected because the adjacency with the neighbor
                                     router was not already established.";
                            }

                            leaf rx-bad-checksum-discard {
                                type yang:counter32;
                                description
                                    "The number of PIM messages received on this interface which were discarded because
                                     of bad checksum.";
                            }

                            leaf rx-bad-version-discard {
                                type yang:counter32;
                                description "The number of PIM messages with bad versions received on this interface.";
                            }

                            leaf rx-bad-encodings {
                                type yang:counter32;
                                description "The number of PIM messages with bad encodings received on this interface.";
                            }

                            leaf join-policy-drops {
                                type yang:counter32;
                                description
                                    "The number of times the join policy match resulted in dropping PIM Join-Prune
                                     Message or one of the source group contained in the message.";
                            }

                            leaf rx-join-prune-errors {
                                type yang:counter32;
                                description
                                    "The number of errors while processing Join-Prune messages received on this
                                     interface.";
                            }

                        } // container statistics

                        list neighbor {
                            key "neighbor-address";
                            description "Enter the neighbor list instance";

                            leaf neighbor-address {
                                type types-sros:ipv6-address;
                                description "This value indicates the IPv6 address of the PIM neighbor.";
                            }

                            leaf dr-priority {
                                type uint32;
                                description
                                    "This value indicates neighbor's DR priority which is received
                                     in the hello message. If the Hello Message did not contain
                                     the DR priority field, the value of priority will be '1'.";
                            }

                            leaf dr-priority-present {
                                type boolean;
                                description
                                    "This value of indicates whether the DR priority field was present
                                     in the Hello message received from the PIM neighbor.";
                            }

                            leaf tracking-support {
                                type boolean;
                                description
                                    "This value indicates whether the T bit in the LAN Prune Delay
                                     option was present in the Hello message. This indicates the
                                     neighbor's capability to disable Join message suppression.";
                            }

                            leaf lan-delay {
                                type uint32;
                                units "milliseconds";
                                description
                                    "This value indicates the value of lan delay field present in
                                     the Hello message received from the neighbor. ";
                            }

                            leaf lan-delay-present {
                                type boolean;
                                description
                                    "This value indicates whether the Hello message received from
                                     the neighbor contained the Lan Delay field.";
                            }

                            leaf generated-id {
                                type uint32;
                                description
                                    "This value indicates a randomly generated 32-bit value that is
                                     regenerated each time PIM forwarding is started or restarted on
                                     the interface, including when the router itself restarts.";
                            }

                            leaf override-interval {
                                type uint32;
                                units "milliseconds";
                                description
                                    "This value indicates the value of the override interval present
                                     in the Hello message.";
                            }

                            leaf up-time {
                                type uint32;
                                units "seconds";
                                description
                                    "This value indicates the time since this PIM neighbor (last)
                                     became a neighbor of the local router.";
                            }

                            leaf expiry-time {
                                type uint32;
                                units "seconds";
                                description
                                    "This value indicates the minimum time remaining before this
                                     PIM neighbor will be aged out.";
                            }

                            leaf hold-time {
                                type uint32;
                                units "seconds";
                                description
                                    "This value indicates the value of the hold time present in the
                                     Hello message.";
                            }

                            leaf join-attribute-support {
                                type boolean;
                                description
                                    "This value indicates whether the Hello Message received from
                                     the neighbor contained the Join Attribute field.";
                            }

                            list secondary-neighbor {
                                key "secondary-neighbor-address";
                                description "Enter the secondary-neighbor list instance";

                                leaf secondary-neighbor-address {
                                    type types-sros:ipv6-address;
                                    description
                                        "This value indicates the IPv6 address of the secondary PIM
                                         neighbor.";
                                }

                            } // list secondary-neighbor

                        } // list neighbor

                        list sg {
                            key "group-address source-address";
                            description "Enter the sg list instance";

                            leaf group-address {
                                type types-sros:ipv6-address;
                                description "The multicast group address of the entry.";
                            }

                            leaf source-address {
                                type types-sros:ipv6-address;
                                description "The source address of the multicast sender.";
                            }

                            leaf up-time {
                                type uint32;
                                units "seconds";
                                description "The time since this source group entry got created.";
                            }

                            leaf join-prune-state {
                                type types-pim:join-prune-state;
                                description
                                    "The Join Prune state for this entry on the interface.

                                     PIM Join or Prune messages are sent by the downstream routers
                                     towards the RPF' neighbor.";
                            }

                            leaf join-prune-timer {
                                type uint32;
                                units "seconds";
                                description
                                    "The time remaining before the router transitions the value of
                                     join-prune-state to 'no-info'.

                                     The timer is started or restarted when a valid Join message is
                                     received. If the value of this object is zero and
                                     join-prune-state is 'join' state, it means that the
                                     downstream router sent a holdtime of '0xffff'. In this case,
                                     join-prune-state will not transition until an appropriate
                                     cancelling of Join or Prune message is received.";
                            }

                            leaf prune-pending-timer {
                                type uint32;
                                units "seconds";
                                description
                                    "The time remaining before the router transitions the value of
                                     join-prune-state to 'no-info'.

                                     The timer is set when the PIM Prune message is received.";
                            }

                            leaf join-prune-rpt-state {
                                type types-pim:join-prune-state;
                                description
                                    "The Join Prune Rpt state for this entry on the interface.

                                     PIM Join or Prune messages are sent by the downstream routers towards the
                                     RPF' neighbor. (S,G,rpt) state is a result of receiving (S,G, rpt) JP message
                                     from the downstream router on the RP tree.";
                            }

                            leaf join-prune-rpt-timer {
                                type uint32;
                                units "seconds";
                                description
                                    "The time remaining before the router transitions the value of
                                     join-prune-rpt-state to 'no-info'.

                                     The timer is started or restarted when a valid Join message is
                                     received. If the value of this object is zero and
                                     join-prune-rpt-state is in 'join' state, it means that the
                                     downstream router sent a holdtime of '0xffff'. In this case,
                                     join-prune-rpt-state will not transition until an appropriate
                                     cancelling of Join or Prune message is received from the
                                     downstream router.";
                            }

                            leaf join-prune-rpt-pending-timer {
                                type uint32;
                                units "seconds";
                                description
                                    "The time remaining before the router transitions the value of
                                     join-prune-rpt-state to 'no-info'.

                                     The timer is set when the (S,G,rpt) PIM Prune message is received.";
                            }

                        } // list sg

                    } // container ipv6

                } // container routed-vpls

            } // container pim-snooping

            container bgp-evpn {
                description "Enter the bgp-evpn context";

                leaf creation-origin {
                    type types-sros:creation-origin;
                    description "Creation origin of BGP-EVPN in the service";
                }

                leaf tunnel-next-hop-usage-high {
                    type boolean;
                    description "Indicates if the number of EVPN tunnels next-hops exceeds the high limit of the system";
                }

                container mac-duplication {
                    description "Enter the mac-duplication context";

                    leaf num-duplicate-macs {
                        type uint32;
                        description "Number of duplicate MAC addresses";
                    }

                    container duplicate-macs {
                        description "Enter the duplicate-macs context";

                        list address {
                            key "mac";
                            description "Enter the address list instance";

                            leaf mac {
                                type yang:mac-address;
                                description "Mac address";
                            }

                            leaf time-detected {
                                type types-sros:date-time;
                                description "Indicates the time when the MAC address was detected as duplicate.";
                            }

                        } // list address

                    } // container duplicate-macs

                } // container mac-duplication

                list local-learned-trusted-mac {
                    key "mac-address";
                    description "Enter the local-learned-trusted-mac list instance";

                    leaf mac-address {
                        type yang:mac-address;
                        description "MAC Address";
                    }

                    leaf trust-time {
                        type uint64;
                        units "seconds";
                        description "Trusted duration";
                    }

                } // list local-learned-trusted-mac

                container tunnel {
                    description "Enter the tunnel context";

                    leaf interface-next-hop {
                        type int32;
                        description "EVPN VPLS tunnel interface IP next hop";
                    }

                    leaf martian-next-hop-limit {
                        type int32;
                        description "EVPN VPLS martian tunnel interface IP next hop limit";
                    }

                } // container tunnel

                list segment-routing-v6 {
                    key "bgp-instance";
                    description "Enter the segment-routing-v6 list instance";

                    leaf bgp-instance {
                        type int32 {
                            range "1..2";
                        }
                        description "BGP instance";
                    }

                    container destinations {
                        status obsolete;
                        description "Enter the destinations context";

                        list ethernet-segment-destination {
                            status obsolete;
                            key "esi";
                            description "Enter the ethernet-segment-destination list instance";

                            leaf esi {
                                status obsolete;
                                type string;
                                description "Ethernet segment identifier";
                            }

                            leaf last-update {
                                status obsolete;
                                type types-sros:date-time;
                                description "Time this entry was last updated.";
                            }

                            list tep {
                                status obsolete;
                                key "tep-address sid-address";
                                description "Enter the tep list instance";

                                leaf tep-address {
                                    status obsolete;
                                    type types-sros:ip-address;
                                    description "Tunnel endpoint ip-address";
                                }

                                leaf sid-address {
                                    status obsolete;
                                    type types-sros:ipv6-address;
                                    description "SID ip-address";
                                }

                                leaf last-update {
                                    status obsolete;
                                    type types-sros:date-time;
                                    description "Time this entry was last updated.";
                                }

                                leaf oper-state {
                                    status obsolete;
                                    type types-sros:up-down-status;
                                    description "Operational status of srv6 tunnel endpoint";
                                }

                                leaf oper-flags {
                                    status obsolete;
                                    type types-services:oper-flags;
                                    description "Conditions affecting the operational status of the srv6 tunnel endpoint";
                                }

                            } // list tep

                        } // list ethernet-segment-destination

                        list non-ethernet-segment-destination {
                            status obsolete;
                            key "tep-address sid-address";
                            description "Enter the non-ethernet-segment-destination list instance";

                            leaf tep-address {
                                status obsolete;
                                type types-sros:ip-address;
                                description "Tunnel endpoint ip-address";
                            }

                            leaf sid-address {
                                status obsolete;
                                type types-sros:ipv6-address;
                                description "SID ip-address";
                            }

                            leaf srv6-type {
                                status obsolete;
                                type enumeration {
                                    enum none                           { value 0; }
                                    enum static                         { value 1; }
                                    enum evpn                           { value 2; }
                                }
                                description "Type of SRv6 instance created";
                            }

                            leaf oper-state {
                                status obsolete;
                                type types-sros:up-down-status;
                                description "Operational status of srv6 tunnel endpoint";
                            }

                            leaf oper-flags {
                                status obsolete;
                                type types-services:oper-flags;
                                description "Conditions affecting the operational status of the srv6 tunnel endpoint";
                            }

                            leaf last-update {
                                status obsolete;
                                type types-sros:date-time;
                                description "Time this entry was last updated.";
                            }

                        } // list non-ethernet-segment-destination

                    } // container destinations

                    list tep {
                        key "tep-address";
                        description "Enter the tep list instance";

                        leaf tep-address {
                            type types-sros:ip-address;
                            description "Tunnel endpoint ip-address";
                        }

                        leaf oper-state {
                            type types-sros:up-down-status;
                            description "Operational status of EVPN tunnel endpoint";
                        }

                        leaf oper-flags {
                            type types-services:oper-flags;
                            description "Conditions affecting the operational status of the EVPN tunnel endpoint";
                        }

                    } // list tep

                    container statistics {
                        description "Enter the statistics context";

                        leaf last-cleared {
                            type types-sros:date-time;
                            description "Indicates the time of the last clearing of vpls evpn srv6 statistics.";
                        }

                        leaf tep-egress-bind-failure-statistics {
                            type types-sros:date-time;
                            description "Indicates the TEP egress bind failure statistics time";
                        }

                        leaf tep {
                            type uint32;
                            description "Indicates the number of TEPs";
                        }

                        leaf service-multicast-limit {
                            type uint32;
                            description "Indicates the evpn srv6 TLS multicast limit";
                        }

                        leaf system-limit {
                            type uint32;
                            description "Indicates the system limit";
                        }

                        leaf egress-multicast-limit {
                            type uint32;
                            description "indicates the egress multicast system limit";
                        }

                    } // container statistics

                } // list segment-routing-v6

                list vxlan {
                    key "bgp-instance";
                    description "Enter the vxlan list instance";

                    leaf bgp-instance {
                        type int32 {
                            range "1..2";
                        }
                        description "BGP instance.";
                    }

                    list tep {
                        key "tep-address";
                        description "Enter the tep list instance";

                        leaf tep-address {
                            type types-sros:ip-address;
                            description "Tunnel endpoint ip-address";
                        }

                        leaf oper-state {
                            type types-sros:up-down-status;
                            description "Operational status of EVPN tunnel endpoint";
                        }

                        leaf oper-flags {
                            type types-services:oper-flags;
                            description "Conditions affecting the operational status of the EVPN tunnel endpoint";
                        }

                    } // list tep

                } // list vxlan

                list mpls {
                    key "bgp-instance";
                    description "Enter the mpls list instance";

                    leaf bgp-instance {
                        type int32 {
                            range "1..2";
                        }
                        description "BGP instance.";
                    }

                    leaf mcast-dest-usage-high {
                        type boolean;
                        description "Indicates if the number of EVPN MPLS tunnel endpoint-egress multicast exceeds the high per-service limit";
                    }

                    container ingress {
                        description "Enter the ingress context";

                        leaf unicast-label {
                            type int32;
                            description "Label advertised for ingress unicast traffic";
                        }

                        leaf bum-label {
                            type int32;
                            description "Label advertised for ingress BUM traffic";
                        }

                    } // container ingress

                    container destinations {
                        description "Enter the destinations context";

                        list non-ethernet-segment-destination {
                            key "ip-address label";
                            description "Enter the non-ethernet-segment-destination list instance";

                            leaf ip-address {
                                type types-sros:ip-address;
                                description "IP address of Tunnel Endpoint";
                            }

                            leaf label {
                                type uint32;
                                description "Label associated with Tunnel Endpoint";
                            }

                            list tunnel-id {
                                key "tunnel-id";
                                description "Enter the tunnel-id list instance";

                                leaf tunnel-id {
                                    type uint32;
                                    description "Tunnel identifier associated with Tunnel Endpoint";
                                }

                                leaf mac-count {
                                    type uint32;
                                    description "Number of MAC addresses";
                                }

                                leaf multicast {
                                    type boolean;
                                    description "Indicates if TEP and egress label is included in the multicast list";
                                }

                                leaf transport-type {
                                    type types-mpls:mpls-transport-type;
                                    description "Indicates transport type associated with Tunnel Endpoint";
                                }

                                leaf oper-state {
                                    type types-sros:up-down-status;
                                    description "Operational status of evpn-mpls tunnel endpoint";
                                }

                                leaf oper-flags {
                                    type types-services:oper-flags;
                                    description "Conditions affecting the operational status of the evpn-mpls tunnel endpoint";
                                }

                                leaf supplementary-broadcast-domain {
                                    type boolean;
                                    description "Indicates if the  TEP and egress label is included in the supplementery broadcast-list multicast";
                                }

                                leaf multicast-forwarding-type {
                                    type types-services:multicast-forwarding-type;
                                    description "Indicates multicast forwarding type";
                                }

                                container igmp-snooping {
                                    description "Enter the igmp-snooping context";

                                    container statistics {
                                        description "Enter the statistics context";

                                        container received {
                                            description "Enter the received context";

                                            leaf general-queries {
                                                type yang:counter32;
                                                description "General Queries.";
                                            }

                                            leaf group-queries {
                                                type yang:counter32;
                                                description "Group Specific Queries.";
                                            }

                                            leaf group-source-queries {
                                                type yang:counter32;
                                                description "Group and Source Specific Queries.";
                                            }

                                            leaf v1-reports {
                                                type yang:counter32;
                                                description "V1 Reports.";
                                            }

                                            leaf v2-reports {
                                                type yang:counter32;
                                                description "V2 Reports.";
                                            }

                                            leaf v3-reports {
                                                type yang:counter32;
                                                description "V3 Reports.";
                                            }

                                            leaf leaves {
                                                type yang:counter32;
                                                description "Leaves.";
                                            }

                                            leaf drops {
                                                type yang:counter32;
                                                description "Total number of dropped packets.";
                                            }

                                            leaf bgp-smet-routes {
                                                type yang:counter32;
                                                description "Total number of BGP SMET routes.";
                                            }

                                            leaf bgp-join-sync-routes {
                                                type yang:counter32;
                                                description "Total number of BGP JOIN SYNC routes.";
                                            }

                                            leaf bgp-leave-sync-routes {
                                                type yang:counter32;
                                                description "Total number of BGP LEAVE SYNC routes.";
                                            }

                                        } // container received

                                        container transmitted {
                                            description "Enter the transmitted context";

                                            leaf general-queries {
                                                type yang:counter32;
                                                description "General Queries.";
                                            }

                                            leaf group-queries {
                                                type yang:counter32;
                                                description "Group Specific Queries.";
                                            }

                                            leaf group-source-queries {
                                                type yang:counter32;
                                                description "Group and Source Specific Queries.";
                                            }

                                            leaf v1-reports {
                                                type yang:counter32;
                                                description "V1 Reports.";
                                            }

                                            leaf v2-reports {
                                                type yang:counter32;
                                                description "V2 Reports.";
                                            }

                                            leaf v3-reports {
                                                type yang:counter32;
                                                description "V3 Reports.";
                                            }

                                            leaf leaves {
                                                type yang:counter32;
                                                description "Leaves.";
                                            }

                                            leaf drops {
                                                type yang:counter32;
                                                description "Total number of dropped packets.";
                                            }

                                            leaf errors {
                                                type yang:counter32;
                                                description "Transmission Errors.";
                                            }

                                            leaf bgp-join-sync-routes {
                                                type yang:counter32;
                                                description "Total number of BGP JOIN SYNC routes.";
                                            }

                                            leaf bgp-leave-sync-routes {
                                                type yang:counter32;
                                                description "Total number of BGP LEAVE SYNC routes.";
                                            }

                                        } // container transmitted

                                        container forwarded {
                                            description "Enter the forwarded context";

                                            leaf general-queries {
                                                type yang:counter32;
                                                description "General Queries.";
                                            }

                                            leaf group-queries {
                                                type yang:counter32;
                                                description "Group Specific Queries.";
                                            }

                                            leaf group-source-queries {
                                                type yang:counter32;
                                                description "Group and Source Specific Queries.";
                                            }

                                            leaf v1-reports {
                                                type yang:counter32;
                                                description "V1 Reports.";
                                            }

                                            leaf v2-reports {
                                                type yang:counter32;
                                                description "V2 Reports.";
                                            }

                                            leaf v3-reports {
                                                type yang:counter32;
                                                description "V3 Reports.";
                                            }

                                            leaf leaves {
                                                type yang:counter32;
                                                description "Leaves.";
                                            }

                                            leaf drops {
                                                type yang:counter32;
                                                description "Total number of dropped packets.";
                                            }

                                            leaf unknown-types {
                                                type yang:counter32;
                                                description "Unknown types.";
                                            }

                                            leaf errors {
                                                type yang:counter32;
                                                description "Forwarding Errors.";
                                            }

                                        } // container forwarded

                                        container error {
                                            description "Enter the error context";

                                            leaf bad-length {
                                                type yang:counter32;
                                                description "Bad length.";
                                            }

                                            leaf bad-ip-checksum {
                                                type yang:counter32;
                                                description "Bad Ip checksum.";
                                            }

                                            leaf unknown-type {
                                                type yang:counter32;
                                                description "Unknown type.";
                                            }

                                            leaf wrong-version {
                                                type yang:counter32;
                                                description "Wrong version.";
                                            }

                                            leaf import-policy-drops {
                                                type yang:counter32;
                                                description
                                                    "Number of times we matched the host IP address or group or
                                                     source addresses specified in the import policy.";
                                            }

                                            leaf missing-router-alert {
                                                type yang:counter32;
                                                description "Router alert flag is not set.";
                                            }

                                            leaf bad-encoding {
                                                type yang:counter32;
                                                description "Badly encoded.";
                                            }

                                            leaf local-scope {
                                                type yang:counter32;
                                                description "Link-local scope multicast group address.";
                                            }

                                            leaf mcac-policy-drops {
                                                type yang:counter32;
                                                description
                                                    "Number of times a join is dropped because of applying a
                                                     multicast CAC policy.";
                                            }

                                            leaf reached-maximum-number-groups {
                                                type yang:counter32;
                                                description
                                                    "Number of times a join is dropped because we reached the maximum
                                                     number of groups.";
                                            }

                                            leaf reached-maximum-number-group-sources {
                                                type yang:counter32;
                                                description
                                                    "Number of times a join is dropped because we reached the maximum
                                                     number group-source combinations.";
                                            }

                                            leaf reached-maximum-number-sources {
                                                type yang:counter32;
                                                description
                                                    "Number of times a join is dropped because we reached the maximum
                                                     number of sources per group.";
                                            }

                                            leaf out-of-memory-drops {
                                                type yang:counter32;
                                                description "Number of times a join is dropped because we ran out of memory.";
                                            }

                                            leaf mcs-failures {
                                                type yang:counter32;
                                                description "Number of times a group could not be synced through multi chassis synchronisation (MCS).";
                                            }

                                            leaf bad-igmp-checksum {
                                                type yang:counter32;
                                                description
                                                    "Number of times a packet is dropped because of a bad IGMP
                                                     header checksum.";
                                            }

                                            leaf zero-source-ip-addr {
                                                type yang:counter32;
                                                description "Number of times a packet is dropped because it has a zero source ip address.";
                                            }

                                            leaf send-query-cfg-drops {
                                                type yang:counter32;
                                                description "Number of times a query is dropped because send-queries is configured.";
                                            }

                                            leaf mvr-from-vpls-cfg-drops {
                                                type yang:counter32;
                                                description "Number of times a packet is dropped because mvr from-vpls could not be applied.";
                                            }

                                            leaf mvr-to-sap-cfg-drops {
                                                type yang:counter32;
                                                description "Number of times a packet is dropped because it has mvr to-sap configuration.";
                                            }

                                            leaf dropped-bgp-smet-routes {
                                                type yang:counter32;
                                                description "Total number of dropped BGP SMET routes.";
                                            }

                                            leaf dropped-bgp-join-sync-routes {
                                                type yang:counter32;
                                                description "Total number of dropped BGP JOIN SYNC routes.";
                                            }

                                            leaf dropped-bgp-leave-sync-routes {
                                                type yang:counter32;
                                                description "Total number of dropped BGP LEAVE SYNC routes.";
                                            }

                                        } // container error

                                    } // container statistics

                                    list group {
                                        key "group-address";
                                        description "Enter the group list instance";

                                        leaf group-address {
                                            type types-sros:ipv4-multicast-address;
                                            description "Group address of multicast channel.";
                                        }

                                        leaf group-type {
                                            type types-igmp:learn-type;
                                        }

                                        leaf filter-mode {
                                            type types-igmp:filter-mode;
                                        }

                                        leaf expiry-time {
                                            type uint32;
                                            units "seconds";
                                            description "The time left before multicast group timeout.";
                                        }

                                        leaf up-time {
                                            type uint32;
                                            units "seconds";
                                            description "The time elapsed since this entry was created.";
                                        }

                                        leaf v1-host-timer {
                                            type uint32;
                                            units "seconds";
                                            description
                                                "The time remaining until the local router will assume that
                                                 there are no longer any version 1 members.";
                                        }

                                        leaf v2-host-timer {
                                            type uint32;
                                            units "seconds";
                                            description
                                                "The time remaining until the local router will assume that
                                                 there are no longer any version 2 members.";
                                        }

                                        leaf igmp-compatibility-mode {
                                            type types-igmp:igmp-version;
                                            description "Compatibility with older version routers.";
                                        }

                                        list source {
                                            key "source-address";
                                            description "Enter the source list instance";

                                            leaf source-address {
                                                type types-sros:ipv4-address;
                                                description "Source address of multicast channel.";
                                            }

                                            leaf source-type {
                                                type types-igmp:learn-type;
                                            }

                                            leaf forwarding-state {
                                                type types-igmp:forwarding-state;
                                                description "Traffic forwardeding state on this port.";
                                            }

                                            leaf expiry-time {
                                                type uint32;
                                                units "seconds";
                                                description "The time left before multicast group timeout.";
                                            }

                                            leaf up-time {
                                                type uint32;
                                                units "seconds";
                                                description "The time elapsed since this entry was created.";
                                            }

                                        } // list source

                                    } // list group

                                } // container igmp-snooping

                                container mld-snooping {
                                    description "Enter the mld-snooping context";

                                    container statistics {
                                        description "Enter the statistics context";

                                        container received {
                                            description "Enter the received context";

                                            leaf general-queries {
                                                type yang:counter32;
                                                description "General Queries.";
                                            }

                                            leaf group-queries {
                                                type yang:counter32;
                                                description "Group Specific Queries.";
                                            }

                                            leaf group-source-queries {
                                                type yang:counter32;
                                                description "Group and Source Specific Queries.";
                                            }

                                            leaf v1-reports {
                                                type yang:counter32;
                                                description "V1 Reports.";
                                            }

                                            leaf v2-reports {
                                                type yang:counter32;
                                                description "V2 Reports.";
                                            }

                                            leaf leaves {
                                                type yang:counter32;
                                                description "Leaves.";
                                            }

                                            leaf drops {
                                                type yang:counter32;
                                                description "Total number of dropped packets.";
                                            }

                                            leaf bgp-smet-routes {
                                                type yang:counter32;
                                                description "Total number of BGP SMET routes.";
                                            }

                                            leaf bgp-join-sync-routes {
                                                type yang:counter32;
                                                description "Total number of BGP JOIN SYNC routes.";
                                            }

                                            leaf bgp-leave-sync-routes {
                                                type yang:counter32;
                                                description "Total number of BGP LEAVE SYNC routes.";
                                            }

                                        } // container received

                                        container transmitted {
                                            description "Enter the transmitted context";

                                            leaf general-queries {
                                                type yang:counter32;
                                                description "General Queries.";
                                            }

                                            leaf group-queries {
                                                type yang:counter32;
                                                description "Group Specific Queries.";
                                            }

                                            leaf group-source-queries {
                                                type yang:counter32;
                                                description "Group and Source Specific Queries.";
                                            }

                                            leaf v1-reports {
                                                type yang:counter32;
                                                description "V1 Reports.";
                                            }

                                            leaf v2-reports {
                                                type yang:counter32;
                                                description "V2 Reports.";
                                            }

                                            leaf leaves {
                                                type yang:counter32;
                                                description "Leaves.";
                                            }

                                            leaf drops {
                                                type yang:counter32;
                                                description "Total number of dropped packets.";
                                            }

                                            leaf errors {
                                                type yang:counter32;
                                                description "Transmission Errors.";
                                            }

                                            leaf bgp-join-sync-routes {
                                                type yang:counter32;
                                                description "Total number of BGP JOIN SYNC routes.";
                                            }

                                            leaf bgp-leave-sync-routes {
                                                type yang:counter32;
                                                description "Total number of BGP LEAVE SYNC routes.";
                                            }

                                        } // container transmitted

                                        container forwarded {
                                            description "Enter the forwarded context";

                                            leaf general-queries {
                                                type yang:counter32;
                                                description "General Queries.";
                                            }

                                            leaf group-queries {
                                                type yang:counter32;
                                                description "Group Specific Queries.";
                                            }

                                            leaf group-source-queries {
                                                type yang:counter32;
                                                description "Group and Source Specific Queries.";
                                            }

                                            leaf v1-reports {
                                                type yang:counter32;
                                                description "V1 Reports.";
                                            }

                                            leaf v2-reports {
                                                type yang:counter32;
                                                description "V2 Reports.";
                                            }

                                            leaf leaves {
                                                type yang:counter32;
                                                description "Leaves.";
                                            }

                                            leaf drops {
                                                type yang:counter32;
                                                description "Total number of dropped packets.";
                                            }

                                            leaf unknown-types {
                                                type yang:counter32;
                                                description "Unknown types.";
                                            }

                                            leaf errors {
                                                type yang:counter32;
                                                description "Forwarding Errors.";
                                            }

                                        } // container forwarded

                                        container error {
                                            description "Enter the error context";

                                            leaf bad-length {
                                                type yang:counter32;
                                                description "Bad length.";
                                            }

                                            leaf unknown-type {
                                                type yang:counter32;
                                                description "Unknown type.";
                                            }

                                            leaf wrong-version {
                                                type yang:counter32;
                                                description "Wrong version.";
                                            }

                                            leaf import-policy-drops {
                                                type yang:counter32;
                                                description
                                                    "Number of times we matched the host IP address or group or
                                                     source addresses specified in the import policy.";
                                            }

                                            leaf missing-router-alert {
                                                type yang:counter32;
                                                description "Router alert flag is not set.";
                                            }

                                            leaf bad-encoding {
                                                type yang:counter32;
                                                description "Badly encoded.";
                                            }

                                            leaf local-scope {
                                                type yang:counter32;
                                                description "Link-local scope multicast group address.";
                                            }

                                            leaf reserved-scope {
                                                type yang:counter32;
                                                description "Reserved scope multicast group address.";
                                            }

                                            leaf reached-maximum-number-groups {
                                                type yang:counter32;
                                                description
                                                    "Number of times a join is dropped because we reached the maximum
                                                     number of groups.";
                                            }

                                            leaf reached-maximum-number-group-sources {
                                                type yang:counter32;
                                                description
                                                    "Number of times a join is dropped because we reached the maximum
                                                     number group-source combinations.";
                                            }

                                            leaf reached-maximum-number-sources {
                                                type yang:counter32;
                                                description
                                                    "Number of times a join is dropped because we reached the maximum
                                                     number of sources per group.";
                                            }

                                            leaf out-of-memory-drops {
                                                type yang:counter32;
                                                description "Number of times a join is dropped because we ran out of memory.";
                                            }

                                            leaf bad-mld-checksum {
                                                type yang:counter32;
                                                description
                                                    "Number of times a packet is dropped because of a bad MLD
                                                     header checksum.";
                                            }

                                            leaf zero-source-ip-addr {
                                                type yang:counter32;
                                                description "Number of times a packet is dropped because it has a zero source ip address.";
                                            }

                                            leaf send-query-cfg-drops {
                                                type yang:counter32;
                                                description "Number of times a query is dropped because send-queries is configured.";
                                            }

                                            leaf dropped-bgp-smet-routes {
                                                type yang:counter32;
                                                description "Total number of dropped BGP SMET routes.";
                                            }

                                            leaf dropped-bgp-join-sync-routes {
                                                type yang:counter32;
                                                description "Total number of dropped BGP JOIN SYNC routes.";
                                            }

                                            leaf dropped-bgp-leave-sync-routes {
                                                type yang:counter32;
                                                description "Total number of dropped BGP LEAVE SYNC routes.";
                                            }

                                        } // container error

                                    } // container statistics

                                    list group {
                                        key "group-address";
                                        description "Enter the group list instance";

                                        leaf group-address {
                                            type types-sros:ipv6-multicast-address;
                                            description "Group address of multicast channel.";
                                        }

                                        leaf group-type {
                                            type types-igmp:learn-type;
                                        }

                                        leaf filter-mode {
                                            type types-igmp:filter-mode;
                                        }

                                        leaf expiry-time {
                                            type uint32;
                                            units "seconds";
                                            description "The time left before multicast group timeout.";
                                        }

                                        leaf up-time {
                                            type uint32;
                                            units "seconds";
                                            description "The time elapsed since this entry was created.";
                                        }

                                        leaf v1-host-timer {
                                            type uint32;
                                            units "seconds";
                                            description
                                                "The time remaining until the local router will assume that
                                                 there are no longer any version 1 members.";
                                        }

                                        leaf mld-compatibility-mode {
                                            type types-igmp:mld-version;
                                            description "Compatibility with older version routers.";
                                        }

                                        list source {
                                            key "source-address";
                                            description "Enter the source list instance";

                                            leaf source-address {
                                                type types-sros:ipv6-address;
                                                description "Source address of multicast channel.";
                                            }

                                            leaf source-type {
                                                type types-igmp:learn-type;
                                            }

                                            leaf forwarding-state {
                                                type types-igmp:forwarding-state;
                                                description "Traffic forwardeding state on this port.";
                                            }

                                            leaf expiry-time {
                                                type uint32;
                                                units "seconds";
                                                description "The time left before multicast group timeout.";
                                            }

                                            leaf up-time {
                                                type uint32;
                                                units "seconds";
                                                description "The time elapsed since this entry was created.";
                                            }

                                        } // list source

                                    } // list group

                                } // container mld-snooping

                            } // list tunnel-id

                        } // list non-ethernet-segment-destination

                        list ethernet-segment-destination {
                            key "esi";
                            description "Enter the ethernet-segment-destination list instance";

                            leaf esi {
                                type string;
                                description "Ethernet segment identifier";
                            }

                            leaf mac-count {
                                type uint32;
                                description "Number of MAC addresses";
                            }

                            list tep {
                                key "ip-address label";
                                description "Enter the tep list instance";

                                leaf ip-address {
                                    type types-sros:ip-address;
                                    description "IP address of Tunnel Endpoint";
                                }

                                leaf label {
                                    type uint32;
                                    description "Label associated with Tunnel Endpoint";
                                }

                                leaf transport-type {
                                    type types-mpls:mpls-transport-type;
                                    description "Indicates transport type associated with Tunnel Endpoint";
                                }

                                leaf tunnel-id {
                                    type uint32;
                                    description "Indicates tunnel identifier associated with Tunnel Endpoint";
                                }

                                leaf oper-state {
                                    type types-sros:up-down-status;
                                    description "Operational status of evpn-mpls tunnel endpoint";
                                }

                                leaf oper-flags {
                                    type types-services:oper-flags;
                                    description "Conditions affecting the operational status of the evpn-mpls tunnel endpoint";
                                }

                            } // list tep

                        } // list ethernet-segment-destination

                        list ethernet-segment-bmac-destination {
                            key "backbone-mac-address";
                            description "Enter the ethernet-segment-bmac-destination list instance";

                            leaf backbone-mac-address {
                                type yang:mac-address;
                                description "Binding backbone mac-address";
                            }

                            list tep {
                                key "ip-address label";
                                description "Enter the tep list instance";

                                leaf ip-address {
                                    type types-sros:ip-address;
                                    description "IP address of Tunnel Endpoint";
                                }

                                leaf label {
                                    type uint32;
                                    description "Label associated with Tunnel Endpoint";
                                }

                                leaf transport-type {
                                    type types-mpls:mpls-transport-type;
                                    description "Indicates transport type associated with Tunnel Endpoint";
                                }

                                leaf tunnel-id {
                                    type uint32;
                                    description "Indicates tunnel identifier associated with Tunnel Endpoint";
                                }

                            } // list tep

                        } // list ethernet-segment-bmac-destination

                    } // container destinations

                    list tep {
                        key "tep-address";
                        description "Enter the tep list instance";

                        leaf tep-address {
                            type types-sros:ip-address;
                            description "Tunnel endpoint ip-address";
                        }

                        leaf oper-state {
                            type types-sros:up-down-status;
                            description "Operational status of EVPN tunnel endpoint";
                        }

                        leaf oper-flags {
                            type types-services:oper-flags;
                            description "Conditions affecting the operational status of the EVPN tunnel endpoint";
                        }

                    } // list tep

                    container statistics {
                        description "Enter the statistics context";

                        leaf last-cleared {
                            type types-sros:date-time;
                            description "Indicates the time of the last clearing of vpls evpn-mpls statistics.";
                        }

                        leaf tep-egress-bind-failure-statistics {
                            type types-sros:date-time;
                            description "Indicates the TEP egress bind failure statistics time";
                        }

                        leaf tep {
                            type uint32;
                            description "Indicates the number of TEPs";
                        }

                        leaf service-multicast-limit {
                            type uint32;
                            description "Indicates the evpn-mpls TLS multicast limit";
                        }

                        leaf system-limit {
                            type uint32;
                            description "Indicates the system limit";
                        }

                        leaf pmsi {
                            type uint32;
                            description "indicates the PMSI limit";
                        }

                        leaf hardware-life-limit {
                            type uint32;
                            description "indicates the hardware life limit";
                        }

                    } // container statistics

                } // list mpls

            } // container bgp-evpn

            container bgp-vpls {
                description "Enter the bgp-vpls context";

                leaf l2-vpn-ext-community-pw-template {
                    type string;
                    description "Name of PW template used in transmitting BGP-VPWS NLRI informatoin for this VPWS edge";
                }

                list routes {
                    key "ve-id route-distinguisher next-hop-address";
                    description "Enter the routes list instance";

                    leaf ve-id {
                        type int32 {
                            range "1..65535";
                        }
                        description "Low-order 4 bytes of Virtual Switch Instance identifier (VSI-id) of L2 route.";
                    }

                    leaf route-distinguisher {
                        type types-services:state-vpn-rd;
                        description "High-order 6 bytes of Virtual Switch Instance identifier (VSI-id) of L2 route.";
                    }

                    leaf next-hop-address {
                        type types-sros:ip-address;
                        description "The next hop address of L2 route.";
                    }

                    leaf sdp-bind-id {
                        type types-services:sdp-bind-id;
                        description "SDP binding information";
                    }

                    leaf pw-template {
                        type string;
                        description "The PW template associated with the SDP bind.";
                    }

                    leaf error-message {
                        type string {
                            length "0..255";
                        }
                        description "Describes the L2 Route error condition in human readable form.";
                    }

                    leaf last-error-time {
                        type yang:date-and-time;
                        description "The date and time when leaf error was last updated.";
                    }

                    leaf control-word {
                        type uint32;
                        description "Control word advertised for this route.";
                    }

                    leaf path-mtu {
                        type int32;
                        description "Layer-2 path MTU for the psuedo-wire to the PE.";
                    }

                    leaf state {
                        type enumeration {
                            enum up                             { value 1; }
                            enum down                           { value 2; }
                        }
                        description "The state of the object.";
                    }

                    leaf sequenced-delivery {
                        type uint32;
                        description "Sequenced delivery flag advertised for this route.";
                    }

                    leaf route-status {
                        type enumeration {
                            enum active                         { value 1; }
                            enum inactive                       { value 2; }
                        }
                        description "The status of the route.";
                    }

                    leaf send-flow-label {
                        type uint32;
                        description "The T-bit advertised for this route.";
                    }

                    leaf receive-flow-label {
                        type uint32;
                        description "The R-bit advertised for this route.";
                    }

                    leaf df-bit {
                        type boolean;
                        description "DF bit associated with this BGP VPLS L2 route entry.";
                    }

                } // list routes

            } // container bgp-vpls

            list endpoint {
                key "name";
                description "Enter the endpoint list instance";

                leaf name {
                    type types-sros:named-item;
                    description "Name of the service endpoint";
                }

                leaf revert-time-count-down {
                    type types-services:revert-time;
                    units "seconds";
                    description
                        "The count down timer that is used before reverting back to the primary spoke-sdp
                         defined on this service endpoint, after having failed over to
                         a backup spoke-sdp.

                         This count down timer begins after primary Spoke SDP becomes
                         operational.";
                }

                leaf creation-origin {
                    type enumeration {
                        enum manual                         { value 0; }
                        enum bgp-vpws                       { value 1; }
                    }
                    description "The origin mechanism used to create this endpoint.";
                }

                container tx-active {
                    description "Enter the tx-active context";

                    leaf type {
                        type enumeration {
                            enum none                           { value 0; }
                            enum sap                            { value 1; }
                            enum sdp-bind                       { value 2; }
                            enum sdp-fec                        { value 3; }
                            enum evpn                           { value 4; }
                        }
                        description "The type of endpoint object that is current transmit active. ";
                    }

                    leaf object {
                        type string;
                        description "The object that is transmit active";
                    }

                    leaf change-count {
                        type uint32;
                        description "The number of times active transmit change has taken place.";
                    }

                    leaf up-time {
                        type uint32;
                        units "centiseconds";
                        description
                            "The active 'up' time of the endpoint object
                             that is current transmit active.";
                    }

                } // container tx-active

                list mc-endpoint {
                    key "mc-ep-id";
                    description "Enter the mc-endpoint list instance";

                    leaf mc-ep-id {
                        type uint32 {
                            range "1..4294967295";
                        }
                        description "Multi-chassis end-point identifier.";
                    }

                    leaf passive-mode {
                        type boolean;
                        description "Whether passive-mode behavior is currently active on this multi-chassis endpoint.";
                    }

                } // list mc-endpoint

            } // list endpoint

            container eth-cfm {
                description "Enter the eth-cfm context";

                list mep {
                    key "md-admin-name ma-admin-name mep-id";
                    description "Enter the mep list instance";

                    leaf md-admin-name {
                        type leafref {
                            path "../../../../../eth-cfm/domain/md-admin-name";
                        }
                        description "A unique administratively assigned name used to identify a domain.";
                    }

                    leaf ma-admin-name {
                        type leafref {
                            path "../../../../../eth-cfm/domain[md-admin-name=current()/../md-admin-name]/association/ma-admin-name";
                        }
                        description "A unique administratively assigned name used to identify an association.";
                    }

                    leaf mep-id {
                        type types-eth-cfm:mep-id-type;
                        description
                            "A CFM Virtual Maintenance Endpoint

                             Specifies a local Maintenance association End Point identifier unique
                             over a given maintanance association.";
                    }

                    leaf if-index {
                        type uint32;
                        description "Port ID of the MEP.";
                    }

                    leaf oper-mac-address {
                        type yang:mac-address;
                        description "Operational MAC address of the MEP.";
                    }

                    container grace {
                        description "Enter the grace context";

                        container transmitted {
                            description "Enter the transmitted context";

                            leaf grace-notification {
                                type enumeration {
                                    enum no-transmit                    { value 0; }
                                    enum grace                          { value 1; }
                                    enum eth-ed                         { value 2; }
                                }
                                description "Indicates the state of the MEP grace period PDU transmission.";
                            }

                        } // container transmitted

                        container received {
                            description "Enter the received context";

                            leaf process-grace-notification {
                                type boolean;
                                description
                                    "Indicates whether the local MEP is receiving and processing grace notifications
                                     from one or more peer MEPs. A value of 'true ' indicates the local MEP is
                                     receiving and processing grace from at least one peer MEP. A value
                                     of 'false' indicates that no peer grace notifications are being
                                     received and processed.";
                            }

                        } // container received

                    } // container grace

                    container ccm-states {
                        description "Enter the ccm-states context";

                        leaf transmit-status {
                            type enumeration {
                                enum no-transmit                    { value 0; }
                                enum transmit                       { value 1; }
                                enum suppressed                     { value 2; }
                            }
                            description
                                "Indicates the state of the MEP CCM PDU transmission.

                                 Values:
                                    noTransmit (0) - no CCM PDUs are being transmitted by the MEP
                                    transmit   (1) - MEP is currently transmitting CCM PDUs
                                    suppressed (2) - MEP should be transmitting CCM PDUs but is suppressing
                                                    them due to an internal condition";
                        }

                        leaf sequence-error {
                            type yang:counter32;
                            description "The total number of out-of-sequence CCMs received from all remote MEPs.";
                        }

                        leaf fng-state {
                            type types-eth-cfm:fng-state-type;
                            description "Current state of the MEP Fault Notification Generator State Machine.";
                        }

                        container transmitted {
                            description "Enter the transmitted context";

                            leaf count {
                                type yang:counter32;
                                description "Total number of CCMs transmitted.";
                            }

                            leaf interface-status {
                                type types-eth-cfm:interface-status;
                                description
                                    "Indicates the interface status TLV information included in the most
                                     recent Connectivity Check Message (CCM) transmission from the local MEP.
                                     If the local MEP CCM transmissions are not enabled, or if no interface
                                     status TLV was included in the most recent transmission, then
                                     ccm-tx-if-status will return a value of is-no-interface-status-tlv (0).";
                            }

                            leaf port-status {
                                type types-eth-cfm:port-status;
                                description
                                    "Indicates the port status TLV information included in the most recent
                                     Connectivity Check Message (CCM) transmission from the local MEP.

                                     If the local MEP CCM transmissions are not enabled, or if no port
                                     status TLV was included in the most recent transmission, then
                                     ccm-tx-port-status will return a value of ps-no-port-state-tlv (0).";
                            }

                            leaf remote-defect-indicator {
                                type boolean;
                                description
                                    "Indicates whether or not the Remote Defect Indication (RDI) bit was set
                                     on the most recent Connectivity Check Message (CCM) transmission from the
                                     local MEP.

                                     If the local MEP CCM transmissions are not eanbled, or if the RDI bit
                                     was not set in the most recent transmission, then ccm-tx-rdi will return
                                     a value of 'false (2)'.";
                            }

                        } // container transmitted

                        container received {
                            description "Enter the received context";

                            leaf highest-priority-defect {
                                type types-eth-cfm:highest-priority-defect-type;
                                description
                                    "The highest priority defect that has been present since the
                                     MEPs Fault Notification Generator State Machine was last in
                                     the reset state.";
                            }

                            leaf defect-flags {
                                type types-eth-cfm:mep-defect-flags;
                                description "A vector of boolean error conditions, any of which may be true.";
                            }

                            list remote-mep-peer {
                                key "remote-mep-id";
                                description "Enter the remote-mep-peer list instance";

                                leaf remote-mep-id {
                                    type types-eth-cfm:mep-id-type;
                                    description "The Remote MEP ID within the same Maintenance Association.";
                                }

                                leaf auto-discovered {
                                    type boolean;
                                    description
                                        "Specifies whether or not the remote peer was automatically discovered
                                         ('true') or not. Auto-discovered remote peers are created by the system
                                         only, and are of a 'volatile' storage type. Specifying the value of
                                         'false' will mark an auto-discovered remote peer as permanently configured.";
                                }

                                leaf receiving-ccm {
                                    type types-eth-cfm:remote-mep-state-type;
                                    description "The operational CCM receiving state of the remote MEP.";
                                }

                                leaf ccm-status-since {
                                    type yang:date-and-time;
                                    description
                                        "The time at which the Remote MEP
                                         last entered either the mep-failed or mep-ok state. ";
                                }

                                leaf peer-mac-address {
                                    type yang:mac-address;
                                    description "The MAC address of the remote MEP.";
                                }

                                leaf receiving-remote-defect-indicator {
                                    type boolean;
                                    description
                                        "State of the RDI bit in the last received CCM (true for rdi=1), or false
                                         if none has been received.";
                                }

                                leaf port-status-tlv {
                                    type types-eth-cfm:port-status;
                                    description
                                        "An enumerated value of the Port status TLV received in the
                                         last CCM from the remote MEP or the default value
                                         ps-no-port-state-tlv indicating either no CCM has been received,
                                         or that no port status TLV was received in the last CCM. ";
                                }

                                leaf interface-status-tlv {
                                    type types-eth-cfm:interface-status;
                                    description
                                        "An enumerated value of the Interface status TLV received
                                         in the last CCM from the remote MEP or the default value
                                         is-no-interface-status-tlv indicating either no CCM has been
                                         received, or that no interface status TLV was received in
                                         the last CCM.";
                                }

                            } // list remote-mep-peer

                        } // container received

                    } // container ccm-states

                    container mc-lag {
                        description "Enter the mc-lag context";

                        leaf inactive-state {
                            type enumeration {
                                enum not-applicable                 { value 0; }
                                enum standby                        { value 1; }
                                enum active                         { value 2; }
                            }
                            description
                                "Indicates the MC-LAG inactive state of the mep.  The value of
                                 system/eth-cfm/redundancy/mc-lag/standby-mep must be 'true (1)' 
                                 on the node for this leaf to have meaning.";
                        }

                    } // container mc-lag

                    container statistics {
                        description "Enter the statistics context";

                        list opcode {
                            key "opcode-name";
                            description "Enter the opcode list instance";

                            leaf opcode-name {
                                type types-eth-cfm:statistics-opcode-name;
                                description "Integer that defines which CFM PDU Opcode the statictics refer to.";
                            }

                            leaf transmitted {
                                type yang:counter32;
                                description "The total number of PDUs transmitted from the node with the specified Opcode.";
                            }

                            leaf received {
                                type yang:counter32;
                                description "The total number of PDUs received on the node with the specified Opcode.";
                            }

                        } // list opcode

                    } // container statistics

                } // list mep

            } // container eth-cfm

            list spoke-sdp {
                key "sdp-bind-id";
                description "Enter the spoke-sdp list instance";

                leaf sdp-bind-id {
                    type types-services:sdp-bind-id;
                    description
                        "SDP Binding identifier as <sdp-id>:<vc-id>.
                         sdp-id - [1..32767]
                         vc-id - [1..4294967295].";
                }

                leaf oper-state {
                    type enumeration {
                        enum up                             { value 1; }
                        enum down                           { value 5; }
                    }
                    description "Indicates the operating status of this Service-SDP binding.";
                }

                leaf oper-flags {
                    type bits {
                        bit sdp-bind-admin-down            { position 0; }
                        bit svc-admin-down                 { position 1; }
                        bit stitching-svc-txdown           { position 2; }
                        bit sdp-oper-down                  { position 3; }
                        bit sdp-path-mtu-too-small         { position 4; }
                        bit no-ingress-vc-label            { position 5; }
                        bit no-egress-vc-label             { position 6; }
                        bit svc-mtu-mismatch               { position 7; }
                        bit vc-type-mismatch               { position 8; }
                        bit relearn-limit-exceeded         { position 9; }
                        bit ies-if-admin-down              { position 10; }
                        bit released-ingress-vc-label      { position 11; }
                        bit labels-exhausted               { position 12; }
                        bit svc-param-mismatch             { position 13; }
                        bit insufficient-bandwidth         { position 14; }
                        bit pw-peer-fault-status-bits      { position 15; }
                        bit mesh-sdp-down                  { position 16; }
                        bit not-managed-by-mcring          { position 17; }
                        bit out-of-resource                { position 18; }
                        bit mh-standby                     { position 19; }
                        bit oam-down-mep-fault             { position 20; }
                        bit oam-up-mep-fault               { position 21; }
                        bit standby-sig-slave-tx-down      { position 22; }
                        bit oper-grp-down                  { position 23; }
                        bit withdrawn-ingress-vc-label     { position 24; }
                        bit vpls-pmsi-down                 { position 25; }
                        bit rec-prot-src-mac               { position 26; }
                        bit peer-fault-status-tx-down      { position 27; }
                        bit evpn-route-conflict            { position 28; }
                        bit admin-locked                   { position 29; }
                        bit evpn-p2mp-conflict             { position 30; }
                        bit label-stack-limit-exceeded     { position 31; }
                        bit vccv-bfd-down                  { position 32; }
                        bit stitching-svc-pw-fault         { position 33; }
                        bit out-of-anysec-resource         { position 34; }
                        bit anysec-service-and-tunnel-config-conflict { position 35; }
                        bit anysec-group-or-peer-oper-down { position 36; }
                    }
                    description
                        "This object indicates all the conditions that affect the
                         operating status of this SDP Bind.";
                }

                leaf pw-peer-status-bits {
                    type bits {
                        bit pw-not-forwarding              { position 0; }
                        bit lac-ingress-fault              { position 1; }
                        bit lac-egress-fault               { position 2; }
                        bit psn-ingress-fault              { position 3; }
                        bit psn-egress-fault               { position 4; }
                        bit pw-fwding-standby              { position 5; }
                    }
                    description
                        "Indicates bits set by the LDP peer when there is a fault on its
                         side of the pseudowire";
                }

                leaf pw-local-status-bits {
                    type bits {
                        bit pw-not-forwarding              { position 0; }
                        bit lac-ingress-fault              { position 1; }
                        bit lac-egress-fault               { position 2; }
                        bit psn-ingress-fault              { position 3; }
                        bit psn-egress-fault               { position 4; }
                        bit pw-fwding-standby              { position 5; }
                    }
                    description "Indicates locally set bits when there is a fault.";
                }

                leaf peer-vccv-cv-bits {
                    type bits {
                        bit icmp-ping                      { position 0; }
                        bit lsp-ping                       { position 1; }
                        bit bfd-fault-detection            { position 2; }
                        bit bfd-fault-detection-and-signalling { position 3; }
                    }
                    description "Indicates CV type bits set by the LDP peer if it supports VCCV.";
                }

                leaf peer-vccv-cc-bits {
                    type bits {
                        bit pwe3-control-word              { position 0; }
                        bit mpls-router-alert-label        { position 1; }
                        bit mpls-pw-demultiplex-or-label   { position 2; }
                    }
                    description "Indicates CC type bits set by the LDP peer if it supports VCCV.";
                }

                leaf oper-control-word {
                    type boolean;
                    description "Status of control word.";
                }

                leaf pw-fault-ip-address {
                    type types-sros:ip-address;
                    description "Faulty IP address sent by peer.";
                }

                leaf class-forwarding-oper-state {
                    type types-sros:oper-state;
                    description "Operational state of forwarding-class based forwarding on this SDP bind.";
                }

                leaf creation-origin {
                    type types-sros:creation-origin;
                    description "Creation origin of the service.";
                }

                leaf oper-hash-label {
                    type boolean;
                    description "Indicates the negotiated value of hash label that is used on this SDP binding.";
                }

                leaf min-required-sdp-oper-mtu {
                    type int32;
                    description "Minimum required SDP MTU size used with this SDP binding.";
                }

                leaf bpdus-translated-frames-encap {
                    type enumeration {
                        enum undefined                      { value 1; }
                        enum disabled                       { value 2; }
                        enum pvst                           { value 3; }
                        enum stp                            { value 4; }
                        enum pvst-rw                        { value 5; }
                    }
                    description
                        "Operational BPDU encapsulation used for BPDU
                         translated frames.";
                }

                container ingress {
                    description "Enter the ingress context";

                    leaf oper-label {
                        type uint32;
                        description "MPLS service label used by the far-end device to send packets to the local PEs sdp-bind.";
                    }

                    container statistics {
                        description "Enter the statistics context";

                        leaf forwarded-packets {
                            type yang:counter64;
                            description "Forwarded packets";
                        }

                        leaf forwarded-octets {
                            type yang:counter64;
                            description "Forwarded octets";
                        }

                        leaf dropped-packets {
                            type yang:counter64;
                            description "Dropped packets";
                        }

                        leaf dropped-octets {
                            type yang:counter64;
                            description "Dropped octets";
                        }

                    } // container statistics

                } // container ingress

                container egress {
                    description "Enter the egress context";

                    leaf oper-label {
                        type uint32;
                        description "MPLS service label used to send packets to the far-end device via this sdp-bind.";
                    }

                    container statistics {
                        description "Enter the statistics context";

                        leaf forwarded-packets {
                            type yang:counter64;
                            description "Forwarded packets";
                        }

                        leaf forwarded-octets {
                            type yang:counter64;
                            description "Forwarded octets";
                        }

                    } // container statistics

                } // container egress

                container bfd {
                    description "Enter the bfd context";

                    leaf oper-state {
                        type types-services:bfd-oper-state;
                        description "BFD oper state";
                    }

                    leaf remaining-up-time {
                        type int32;
                        units "seconds";
                        description "Remaining uptime";
                    }

                } // container bfd

                container spb {
                    description "Enter the spb context";

                    leaf interface {
                        type types-sros:interface-name;
                        description "Interface assigned for SPB";
                    }

                    list level {
                        key "id";
                        description "Enter the level list instance";

                        leaf id {
                            type int32 {
                                range "1";
                            }
                            description "Level identifier";
                        }

                        leaf oper-metric {
                            type uint32;
                            description "Operational metric";
                        }

                    } // list level

                    list adjacency {
                        key "adjacency-index";
                        description "Enter the adjacency list instance";

                        leaf adjacency-index {
                            type int32 {
                                range "1..2000000000";
                            }
                            description
                                "A unique value identifying the IS adjacency from all
                                 other such adjacencies on this circuit. This value is
                                 assigned by the system when the adjacency is created
                                 automatically.";
                        }

                        leaf oper-state {
                            type enumeration {
                                enum initializing                   { value 1; }
                                enum up                             { value 2; }
                                enum failed                         { value 3; }
                                enum down                           { value 4; }
                            }
                            description "The state of the adjacency";
                        }

                        leaf usage {
                            type enumeration {
                                enum undefined                      { value 1; }
                                enum level1                         { value 2; }
                                enum level2                         { value 3; }
                                enum level1and2                     { value 4; }
                            }
                            description
                                "An adjacency of type level1 is used for level 1
                                 traffic only. An adjacency of type level2 is used
                                 for level 2 traffic only. An adjacency of type level1and2
                                 is used for both level 1 and level 2 traffic. There
                                 may be two adjacencies (of types level1 and level2)
                                 between the same pair of Intermediate Systems.";
                        }

                        leaf hold-timer {
                            type int32 {
                                range "1..65535";
                            }
                            units "seconds";
                            description
                                "The holding time for this adjacency updated from
                                 received IIH PDUs.";
                        }

                        leaf uptime {
                            type int32;
                            units "seconds";
                            description
                                "If the adjacency is up, the amount of time in seconds
                                 since this adjacency entered state 'up'.  If the adjacency
                                 is not up, the number of seconds since the adjacency was
                                 up, or since the system started, if the adjacency has
                                 never been up.

                                 Note: This can be implemented as start time less
                                 the current time.";
                        }

                        leaf expires-in {
                            type int32 {
                                range "0..65535";
                            }
                            units "seconds";
                            description "The value indicates the time in which the adjacency will expire if no hello packets are received.";
                        }

                        leaf level {
                            type enumeration {
                                enum level1                         { value 1; }
                                enum level2                         { value 2; }
                                enum level1-l2                      { value 3; }
                                enum unknown                        { value 4; }
                            }
                            description "The value indicates the circuit type of the adjacency as advertised.";
                        }

                        container restart {
                            description "Enter the restart context";

                            leaf support {
                                type boolean;
                                description
                                    "The value indicates whether adjacency supports ISIS graceful restart.

                                     If support has a value of 'true' the adjacency
                                     supports graceful restart.";
                            }

                            leaf status {
                                type enumeration {
                                    enum not-helping                    { value 1; }
                                    enum restarting                     { value 2; }
                                    enum restart-complete               { value 3; }
                                    enum helping                        { value 4; }
                                    enum aborted                        { value 5; }
                                }
                                description "The value indicates the graceful restart status of the adjacency.";
                            }

                            leaf suppressed {
                                type boolean;
                                description
                                    "The value indicates if the adjacency has requested this router to suppress advertisement of
                                     the adjacency in this router's LSPs.

                                     If suppressed has a value of 'true' the adjacency
                                     has requested to suppress advertisement of the LSPs.";
                            }

                            leaf num-restarts {
                                type uint32;
                                description "The value indicates the number of times the adjacency has attempted restart.";
                            }

                            leaf last-restart {
                                type yang:date-and-time;
                                description "The value indicates the last time the adjacency attempted restart.";
                            }

                        } // container restart

                        container neighbor {
                            description "Enter the neighbor context";

                            leaf snpa-address {
                                type types-isis:snpa-address;
                                description "The SNPA address of the neighboring system.";
                            }

                            leaf system-type {
                                type enumeration {
                                    enum l1-is                          { value 1; }
                                    enum l2-is                          { value 2; }
                                    enum l1-l2-is                       { value 3; }
                                    enum unknown                        { value 4; }
                                }
                                description "The type of the neighboring system.";
                            }

                            leaf system-id {
                                type string {
                                    length "0..24";
                                }
                                description
                                    "The system ID and 4 byte circuit ID of the
                                     neighboring Intermediate System set from
                                     the source ID field of the Three-Way-Handshake
                                     information from the neighbor's IIH PDUs.";
                            }

                            leaf priority {
                                type int32 {
                                    range "0..127";
                                }
                                description
                                    "Priority of the neighboring Intermediate System for
                                     becoming the LAN Level 1 Designated Intermediate System
                                     if the value of isisISAdjNeighSysType is
                                     L1IntermediateSystem or LAN Level 2 Designated
                                     Intermediate System if the value of
                                     isisISAdjNeighSysType is L2IntermediateSystem.";
                            }

                            leaf ipv4 {
                                type types-sros:ipv4-address;
                                description "The value indicates the ip-address of the neighbor with which adjacency is formed.";
                            }

                            leaf ipv6 {
                                type types-sros:ipv6-address;
                                description
                                    "The value indicates the IP address of the neighbor with which an IPv6-adjacency is formed
                                     this will always be an IPv6 address.";
                            }

                        } // container neighbor

                        container multi-topology {
                            description "Enter the multi-topology context";

                            leaf enabled {
                                type boolean;
                                description
                                    "The value indicates if the ISIS multi-topology protocol is supported on the neighbor.

                                     If the value is 'true', ISIS multi-topology
                                     protocol is enabled on the neighbor.";
                            }

                            container id0 {
                                description "Enter the id0 context";

                                leaf enabled {
                                    type boolean;
                                    description
                                        "The value indicates if the MT x IPvx topology is supported on the neighbor.

                                         If the value of enable is 'true', MT x IPvx topology is
                                         supported on the neighbor.";
                                }

                                leaf bfd-required {
                                    type boolean;
                                    description
                                        "The value indicates if BFD session is required for this Multi Topology before bringing the
                                         adjacency to FULL state, as described in RFC6213.";
                                }

                                leaf bfd-usable {
                                    type boolean;
                                    description
                                        "The value indicates if BFD session for this Multi Topology is usable, that is either not
                                         required or in state UP, as described in RFC6213.";
                                }

                            } // container id0

                            container id2 {
                                description "Enter the id2 context";

                                leaf enabled {
                                    type boolean;
                                    description
                                        "The value indicates if the MT x IPvx topology is supported on the neighbor.

                                         If the value of enable is 'true', MT x IPvx topology is
                                         supported on the neighbor.";
                                }

                                leaf bfd-required {
                                    type boolean;
                                    description
                                        "The value indicates if BFD session is required for this Multi Topology before bringing the
                                         adjacency to FULL state, as described in RFC6213.";
                                }

                                leaf bfd-usable {
                                    type boolean;
                                    description
                                        "The value indicates if BFD session for this Multi Topology is usable, that is either not
                                         required or in state UP, as described in RFC6213.";
                                }

                            } // container id2

                            container id3 {
                                description "Enter the id3 context";

                                leaf enabled {
                                    type boolean;
                                    description
                                        "The value indicates if the MT x IPvx topology is supported on the neighbor.

                                         If the value of enable is 'true', MT x IPvx topology is
                                         supported on the neighbor.";
                                }

                                leaf bfd-required {
                                    type boolean;
                                    description
                                        "The value indicates if BFD session is required for this Multi Topology before bringing the
                                         adjacency to FULL state, as described in RFC6213.";
                                }

                                leaf bfd-usable {
                                    type boolean;
                                    description
                                        "The value indicates if BFD session for this Multi Topology is usable, that is either not
                                         required or in state UP, as described in RFC6213.";
                                }

                            } // container id3

                            container id4 {
                                description "Enter the id4 context";

                                leaf enabled {
                                    type boolean;
                                    description
                                        "The value indicates if the MT x IPvx topology is supported on the neighbor.

                                         If the value of enable is 'true', MT x IPvx topology is
                                         supported on the neighbor.";
                                }

                                leaf bfd-required {
                                    type boolean;
                                    description
                                        "The value indicates if BFD session is required for this Multi Topology before bringing the
                                         adjacency to FULL state, as described in RFC6213.";
                                }

                                leaf bfd-usable {
                                    type boolean;
                                    description
                                        "The value indicates if BFD session for this Multi Topology is usable, that is either not
                                         required or in state UP, as described in RFC6213.";
                                }

                            } // container id4

                        } // container multi-topology

                    } // list adjacency

                } // container spb

                container ethernet-segment {
                    description "Enter the ethernet-segment context";

                    leaf name {
                        type types-sros:named-item-or-empty;
                        description "Ethernet segment name.";
                    }

                    leaf oper-state {
                        type types-services:evpn-mh-es-status;
                        description "Operational status of the ethernet-segment.";
                    }

                } // container ethernet-segment

                container mvpls {
                    description "Enter the mvpls context";

                    leaf prune-state {
                        type types-services:mvpls-prune-state;
                        description
                            "MVPLS prune state of the spoke SDP. The leaf
                             will be set to not-applicable if the spoke SDP is
                             not managed by a MVPLS. If the SDP is managed the state
                             reflects whether or not it is pruned by the STP instance
                             running in the MVPLS instance.";
                    }

                    leaf managing-service {
                        type types-sros:named-item-or-empty;
                        description
                            "Service where the STP instance is running that is managing this
                             spoke SDP. This leaf is only valid if mvpls-prune-state is
                             different from not-applicable.";
                    }

                    leaf managing-sdp-bind {
                        type types-services:state-sdp-bind-id-or-zero;
                        description
                            "SDP bind id in the mVPLS instance specified in mgmt-service that
                             is controlling this SDP. This leaf is only valid if
                             mvpls-prune-state is different from not-applicable.";
                    }

                } // container mvpls

                container topology-change-bit {
                    description "Enter the topology-change-bit context";

                    leaf in-bpdus {
                        type uint32;
                        description
                            "Number BPDUs received on this SDP Bind
                             with the Topology Change bit set.";
                    }

                    leaf out-bpdus {
                        type uint32;
                        description
                            "Number BPDUs sent out this SDP Bind
                             with the Topology Change bit set.";
                    }

                } // container topology-change-bit

                container fdb {
                    description "Enter the fdb context";

                    leaf protected-mac-address-received {
                        type yang:mac-address;
                        description "The protected MAC address received";
                    }

                    leaf protected-mac-address-received-last-changed {
                        type yang:date-and-time;
                        description "Timestamp when the protected MAC address was receieved";
                    }

                    leaf pbb-protected-mac-address-received {
                        type yang:mac-address;
                        description "The PBB protected MAC address received";
                    }

                    leaf pbb-protected-mac-address-received-last-changed {
                        type yang:date-and-time;
                        description "Timestamp when the PBB protected MAC address was receieved";
                    }

                    leaf table-high-utilization {
                        type boolean;
                        description "Set to 'true' when the FDB table utilization reaches the high watermark and 'false' when it reaches the low watermark.";
                    }

                    leaf non-blockable-move-rate-exceeded-mac-address {
                        type yang:mac-address;
                        description "The non-blocking MAC address of the SAP that exceeds the maximum move rate";
                    }

                    leaf non-blockable-move-rate-exceeded-mac-address-last-changed {
                        type yang:date-and-time;
                        description "Timestamp when the non-blocking MAC addresses was detected";
                    }

                    container statistics {
                        description "Enter the statistics context";

                        leaf total {
                            type int32;
                            description "Number of entries allocated in the FDB ";
                        }

                        leaf static {
                            type int32;
                            description "Number of static entries in the FDB";
                        }

                        leaf learned {
                            type int32;
                            description "Number of learned entries in the FDB";
                        }

                        leaf oam {
                            type int32;
                            description "Number of OAM entries in the FDB";
                        }

                        leaf conditional-static {
                            type int32;
                            description "Number of conditional static entries in the FDB";
                        }

                        leaf dhcp {
                            type int32;
                            description "Number of dhcp-learned entries in the FDB";
                        }

                        leaf host {
                            type int32;
                            description "Number of host-learned entries in the FDB";
                        }

                        leaf interface {
                            type int32;
                            description "Number of interface entries in the FDB";
                        }

                        leaf bgp-evpn {
                            type int32;
                            description "Number of bgp-evpn entries in the FDB";
                        }

                        leaf evpn-static {
                            type int32;
                            description "Number of evpn static entries in the FDB";
                        }

                        leaf spb {
                            type int32;
                            description "Number of SPB entries in the FDB";
                        }

                        leaf eth-cfm {
                            type int32;
                            description "Number of eth-cfm entries in FDB";
                        }

                    } // container statistics

                    container protected-src-mac-violation {
                        description "Enter the protected-src-mac-violation context";

                        leaf oper-state {
                            type boolean;
                            description "Operational state of the protected-source MAC feature.";
                        }

                        leaf oper-action {
                            type enumeration {
                                enum oper-down                      { value 1; }
                                enum alarm-only                     { value 2; }
                                enum discard-frame                  { value 3; }
                            }
                            description "Operational state of the protected-source MAC violation action.";
                        }

                    } // container protected-src-mac-violation

                    container mac-move {
                        description "Enter the mac-move context";

                        leaf remaining-down-time {
                            type union {
                                type uint32 {
                                    range "1..65534";
                                }
                                type enumeration {
                                    enum never                          { value 0; }
                                    enum indefinite                     { value 65535; }
                                }
                            }
                            units "seconds";
                            description
                                "The time remaining until the relearn-limit-exceeded oper-flag is cleared.
                                 When the value is 'indefinite', this flag will not be cleared automatically.
                                 Relearn-limit-exceeded oper-flag is set when sdp-bind is brought down 
                                 when mac-move max-rate is exceeded.";
                        }

                        leaf remaining-retry-reset-time {
                            type union {
                                type uint32 {
                                    range "1..4294967295";
                                }
                                type enumeration {
                                    enum never                          { value 0; }
                                }
                            }
                            units "seconds";
                            description
                                "The time remaining to reset the mac-move retries-left
                                 when the oper-state of sdp-bind is up.";
                        }

                        leaf rate-exceed-times-left {
                            type union {
                                type uint32 {
                                    range "1..4294967294";
                                }
                                type enumeration {
                                    enum unlimited                      { value -1; }
                                    enum none                           { value 0; }
                                }
                            }
                            description
                                "Counts down the number of times this SDP bind can exceed the
                                 VPLS mac-move max-rate and still be automatically
                                 brought up.";
                        }

                    } // container mac-move

                } // container fdb

                container stp {
                    description "Enter the stp context";

                    leaf bpdu-encap {
                        type enumeration {
                            enum dynamic                        { value 1; }
                            enum dot1d                          { value 2; }
                            enum pvst                           { value 3; }
                        }
                        description "B-PDU Encap";
                    }

                    leaf port-state {
                        type enumeration {
                            enum disabled                       { value 1; }
                            enum blocking                       { value 2; }
                            enum listening                      { value 3; }
                            enum learning                       { value 4; }
                            enum forwarding                     { value 5; }
                            enum broken                         { value 6; }
                            enum discarding                     { value 7; }
                        }
                        description "The PIP uplink's current state";
                    }

                    leaf designated-port {
                        type int32;
                        description "The identifier of the port on the designated bridge";
                    }

                    leaf forward-transitions {
                        type uint32;
                        description "The number of times the port has transitioned from learned state to forwarding state";
                    }

                    leaf designated-bridge {
                        type types-sros:bridge-id;
                        description "The identifier of the designated bridge of the PIP uplink";
                    }

                    leaf config-bpdus-received {
                        type uint32;
                        description "The number of configuration BPDUs received on this PIP uplink";
                    }

                    leaf bad-bpdus-received {
                        type uint32;
                        description "The number of bad BPDUs received on this PIP uplink";
                    }

                    leaf config-bpdus-transmitted {
                        type uint32;
                        description "The number of configuration BPDUs transmitted on this PIP uplink";
                    }

                    leaf tcn-bpdus-received {
                        type uint32;
                        description "Topology-change B-PDU received";
                    }

                    leaf tcn-bpdus-transmitted {
                        type uint32;
                        description "Topology-change B-PDU transmitted";
                    }

                    leaf oper-bpdu-encap {
                        type enumeration {
                            enum dot1d                          { value 2; }
                            enum pvst                           { value 3; }
                        }
                        description "Oper B-PDU Encap";
                    }

                    leaf vpn-id {
                        type uint32;
                        description "Associated vpn identifier";
                    }

                    leaf customer-name {
                        type string;
                        description "Associated customer name";
                    }

                    leaf oper-edge {
                        type boolean;
                        description "Oper edge";
                    }

                    leaf port-role {
                        type enumeration {
                            enum master                         { value 0; }
                            enum root                           { value 1; }
                            enum designated                     { value 2; }
                            enum alternate                      { value 3; }
                            enum backup                         { value 4; }
                            enum disabled                       { value 5; }
                        }
                        description "The current role of the PIP uplink";
                    }

                    leaf oper-protocol {
                        type enumeration {
                            enum not-applicable                 { value 0; }
                            enum stp                            { value 1; }
                            enum rstp                           { value 2; }
                            enum mstp                           { value 3; }
                        }
                        description "The protocol running on this PIP uplink";
                    }

                    leaf rst-bpdus-received {
                        type uint32;
                        description "The number of RST BPDUs recieved on this PIP uplink";
                    }

                    leaf rst-bpdus-transmitted {
                        type uint32;
                        description "The number of RST BPDUs transmitted on this PIP uplink";
                    }

                    leaf exception {
                        type enumeration {
                            enum none                           { value 1; }
                            enum one-way-communication          { value 2; }
                            enum downstream-loop-detected       { value 3; }
                        }
                        description "Indicates if an stp exception is present on the pip";
                    }

                    leaf mst-bpdus-received {
                        type uint32;
                        description "The number of MST BPDUs received on this PIP uplink";
                    }

                    leaf mst-bpdus-transmitted {
                        type uint32;
                        description "The number of MST BPDUs transmitted on this PIP uplink";
                    }

                    leaf receive-designated-bridge {
                        type types-sros:bridge-id;
                        description "The identifier of the designated bridge of the PIP uplink";
                    }

                } // container stp

                container l2pt {
                    description "Enter the l2pt context";

                    container stp {
                        description "Enter the stp context";

                        leaf config-bpdus-received {
                            type uint32;
                            description "The number of configuration BPDUs received on this PIP uplink";
                        }

                        leaf config-bpdus-transmitted {
                            type uint32;
                            description "The number of configuration BPDUs transmitted on this PIP uplink";
                        }

                        leaf rst-bpdus-received {
                            type uint32;
                            description "The number of RST BPDUs recieved on this PIP uplink";
                        }

                        leaf rst-bpdus-transmitted {
                            type uint32;
                            description "The number of RST BPDUs transmitted on this PIP uplink";
                        }

                        leaf tcn-bpdus-received {
                            type uint32;
                            description "Topology-change B-PDU received";
                        }

                        leaf tcn-bpdus-transmitted {
                            type uint32;
                            description "Topology-change B-PDU transmitted";
                        }

                        container encap {
                            description "Enter the encap context";

                            leaf config-bpdus-received {
                                type uint32;
                                description "The number of configuration BPDUs received on this PIP uplink";
                            }

                            leaf config-bpdus-transmitted {
                                type uint32;
                                description "The number of configuration BPDUs transmitted on this PIP uplink";
                            }

                            leaf rst-bpdus-received {
                                type uint32;
                                description "The number of RST BPDUs recieved on this PIP uplink";
                            }

                            leaf rst-bpdus-transmitted {
                                type uint32;
                                description "The number of RST BPDUs transmitted on this PIP uplink";
                            }

                            leaf tcn-bpdus-received {
                                type uint32;
                                description "Topology-change B-PDU received";
                            }

                            leaf tcn-bpdus-transmitted {
                                type uint32;
                                description "Topology-change B-PDU transmitted";
                            }

                        } // container encap

                    } // container stp

                } // container l2pt

                container igmp-snooping {
                    description "Enter the igmp-snooping context";

                    container mcac {
                        description "Enter the mcac context";

                        leaf in-use-mandatory-bandwidth {
                            type uint32;
                            units "kilobps";
                            description
                                "The in-use bandwidth for the mandatory channels for this
                                 protocol interface instance.";
                        }

                        leaf in-use-optional-bandwidth {
                            type uint32;
                            units "kilobps";
                            description
                                "The in-use bandwidth for the optional channels for this
                                 protocol interface instance.";
                        }

                        leaf available-mandatory-bandwidth {
                            type uint32;
                            units "kilobps";
                            description
                                "The pre-reserved bandwidth for the mandatory channels for
                                 this interface instance.";
                        }

                        leaf available-optional-bandwidth {
                            type uint32;
                            units "kilobps";
                            description "The available bandwidth for this interface instance.";
                        }

                        leaf values-in-transit {
                            type boolean;
                            description
                                "The operational (available and in-use mandatory/optional) value for the
                                 following objects is in transition due to configuration change:
                                 - available-mandatory-bandwidth
                                 - available-bandwidth
                                 - in-use-mandatory-bandwidth
                                 - in-use-optional-bandwidth.";
                        }

                    } // container mcac

                    container statistics {
                        description "Enter the statistics context";

                        container received {
                            description "Enter the received context";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                        } // container received

                        container transmitted {
                            description "Enter the transmitted context";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                            leaf errors {
                                type yang:counter32;
                                description "Transmission Errors.";
                            }

                        } // container transmitted

                        container forwarded {
                            description "Enter the forwarded context";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                            leaf unknown-types {
                                type yang:counter32;
                                description "Unknown types.";
                            }

                            leaf errors {
                                type yang:counter32;
                                description "Forwarding Errors.";
                            }

                        } // container forwarded

                        container error {
                            description "Enter the error context";

                            leaf bad-length {
                                type yang:counter32;
                                description "Bad length.";
                            }

                            leaf bad-ip-checksum {
                                type yang:counter32;
                                description "Bad Ip checksum.";
                            }

                            leaf unknown-type {
                                type yang:counter32;
                                description "Unknown type.";
                            }

                            leaf wrong-version {
                                type yang:counter32;
                                description "Wrong version.";
                            }

                            leaf import-policy-drops {
                                type yang:counter32;
                                description
                                    "Number of times we matched the host IP address or group or
                                     source addresses specified in the import policy.";
                            }

                            leaf missing-router-alert {
                                type yang:counter32;
                                description "Router alert flag is not set.";
                            }

                            leaf bad-encoding {
                                type yang:counter32;
                                description "Badly encoded.";
                            }

                            leaf local-scope {
                                type yang:counter32;
                                description "Link-local scope multicast group address.";
                            }

                            leaf mcac-policy-drops {
                                type yang:counter32;
                                description
                                    "Number of times a join is dropped because of applying a
                                     multicast CAC policy.";
                            }

                            leaf reached-maximum-number-groups {
                                type yang:counter32;
                                description
                                    "Number of times a join is dropped because we reached the maximum
                                     number of groups.";
                            }

                            leaf reached-maximum-number-group-sources {
                                type yang:counter32;
                                description
                                    "Number of times a join is dropped because we reached the maximum
                                     number group-source combinations.";
                            }

                            leaf reached-maximum-number-sources {
                                type yang:counter32;
                                description
                                    "Number of times a join is dropped because we reached the maximum
                                     number of sources per group.";
                            }

                            leaf out-of-memory-drops {
                                type yang:counter32;
                                description "Number of times a join is dropped because we ran out of memory.";
                            }

                            leaf bad-igmp-checksum {
                                type yang:counter32;
                                description
                                    "Number of times a packet is dropped because of a bad IGMP
                                     header checksum.";
                            }

                            leaf zero-source-ip-addr {
                                type yang:counter32;
                                description "Number of times a packet is dropped because it has a zero source ip address.";
                            }

                            leaf send-query-cfg-drops {
                                type yang:counter32;
                                description "Number of times a query is dropped because send-queries is configured.";
                            }

                        } // container error

                    } // container statistics

                    list group {
                        key "group-address";
                        description "Enter the group list instance";

                        leaf group-address {
                            type types-sros:ipv4-multicast-address;
                            description "Group address of multicast channel.";
                        }

                        leaf group-type {
                            type types-igmp:learn-type;
                        }

                        leaf filter-mode {
                            type types-igmp:filter-mode;
                        }

                        leaf expiry-time {
                            type uint32;
                            units "seconds";
                            description "The time left before multicast group timeout.";
                        }

                        leaf up-time {
                            type uint32;
                            units "seconds";
                            description "The time elapsed since this entry was created.";
                        }

                        leaf v1-host-timer {
                            type uint32;
                            units "seconds";
                            description
                                "The time remaining until the local router will assume that
                                 there are no longer any version 1 members.";
                        }

                        leaf v2-host-timer {
                            type uint32;
                            units "seconds";
                            description
                                "The time remaining until the local router will assume that
                                 there are no longer any version 2 members.";
                        }

                        leaf igmp-compatibility-mode {
                            type types-igmp:igmp-version;
                            description "Compatibility with older version routers.";
                        }

                        list source {
                            key "source-address";
                            description "Enter the source list instance";

                            leaf source-address {
                                type types-sros:ipv4-address;
                                description "Source address of multicast channel.";
                            }

                            leaf source-type {
                                type types-igmp:learn-type;
                            }

                            leaf forwarding-state {
                                type types-igmp:forwarding-state;
                                description "Traffic forwardeding state on this port.";
                            }

                            leaf expiry-time {
                                type uint32;
                                units "seconds";
                                description "The time left before multicast group timeout.";
                            }

                            leaf up-time {
                                type uint32;
                                units "seconds";
                                description "The time elapsed since this entry was created.";
                            }

                        } // list source

                    } // list group

                } // container igmp-snooping

                container mld-snooping {
                    description "Enter the mld-snooping context";

                    container statistics {
                        description "Enter the statistics context";

                        container received {
                            description "Enter the received context";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf leaves {
                                type yang:counter32;
                                description "Leaves.";
                            }

                            leaf drops {
                                type yang:counter32;
                                description "Total number of dropped packets.";
                            }

                        } // container received

                        container transmitted {
                            description "Enter the transmitted context";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf leaves {
                                type yang:counter32;
                                description "Leaves.";
                            }

                            leaf drops {
                                type yang:counter32;
                                description "Total number of dropped packets.";
                            }

                            leaf errors {
                                type yang:counter32;
                                description "Transmission Errors.";
                            }

                        } // container transmitted

                        container forwarded {
                            description "Enter the forwarded context";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf leaves {
                                type yang:counter32;
                                description "Leaves.";
                            }

                            leaf drops {
                                type yang:counter32;
                                description "Total number of dropped packets.";
                            }

                            leaf unknown-types {
                                type yang:counter32;
                                description "Unknown types.";
                            }

                            leaf errors {
                                type yang:counter32;
                                description "Forwarding Errors.";
                            }

                        } // container forwarded

                        container error {
                            description "Enter the error context";

                            leaf bad-length {
                                type yang:counter32;
                                description "Bad length.";
                            }

                            leaf unknown-type {
                                type yang:counter32;
                                description "Unknown type.";
                            }

                            leaf wrong-version {
                                type yang:counter32;
                                description "Wrong version.";
                            }

                            leaf import-policy-drops {
                                type yang:counter32;
                                description
                                    "Number of times we matched the host IP address or group or
                                     source addresses specified in the import policy.";
                            }

                            leaf missing-router-alert {
                                type yang:counter32;
                                description "Router alert flag is not set.";
                            }

                            leaf bad-encoding {
                                type yang:counter32;
                                description "Badly encoded.";
                            }

                            leaf local-scope {
                                type yang:counter32;
                                description "Link-local scope multicast group address.";
                            }

                            leaf reserved-scope {
                                type yang:counter32;
                                description "Reserved scope multicast group address.";
                            }

                            leaf reached-maximum-number-groups {
                                type yang:counter32;
                                description
                                    "Number of times a join is dropped because we reached the maximum
                                     number of groups.";
                            }

                            leaf reached-maximum-number-group-sources {
                                type yang:counter32;
                                description
                                    "Number of times a join is dropped because we reached the maximum
                                     number group-source combinations.";
                            }

                            leaf reached-maximum-number-sources {
                                type yang:counter32;
                                description
                                    "Number of times a join is dropped because we reached the maximum
                                     number of sources per group.";
                            }

                            leaf out-of-memory-drops {
                                type yang:counter32;
                                description "Number of times a join is dropped because we ran out of memory.";
                            }

                            leaf bad-mld-checksum {
                                type yang:counter32;
                                description
                                    "Number of times a packet is dropped because of a bad MLD
                                     header checksum.";
                            }

                            leaf zero-source-ip-addr {
                                type yang:counter32;
                                description "Number of times a packet is dropped because it has a zero source ip address.";
                            }

                            leaf send-query-cfg-drops {
                                type yang:counter32;
                                description "Number of times a query is dropped because send-queries is configured.";
                            }

                        } // container error

                    } // container statistics

                    list group {
                        key "group-address";
                        description "Enter the group list instance";

                        leaf group-address {
                            type types-sros:ipv6-multicast-address;
                            description "Group address of multicast channel.";
                        }

                        leaf group-type {
                            type types-igmp:learn-type;
                        }

                        leaf filter-mode {
                            type types-igmp:filter-mode;
                        }

                        leaf expiry-time {
                            type uint32;
                            units "seconds";
                            description "The time left before multicast group timeout.";
                        }

                        leaf up-time {
                            type uint32;
                            units "seconds";
                            description "The time elapsed since this entry was created.";
                        }

                        leaf v1-host-timer {
                            type uint32;
                            units "seconds";
                            description
                                "The time remaining until the local router will assume that
                                 there are no longer any version 1 members.";
                        }

                        leaf mld-compatibility-mode {
                            type types-igmp:mld-version;
                            description "Compatibility with older version routers.";
                        }

                        list source {
                            key "source-address";
                            description "Enter the source list instance";

                            leaf source-address {
                                type types-sros:ipv6-address;
                                description "Source address of multicast channel.";
                            }

                            leaf source-type {
                                type types-igmp:learn-type;
                            }

                            leaf forwarding-state {
                                type types-igmp:forwarding-state;
                                description "Traffic forwardeding state on this port.";
                            }

                            leaf expiry-time {
                                type uint32;
                                units "seconds";
                                description "The time left before multicast group timeout.";
                            }

                            leaf up-time {
                                type uint32;
                                units "seconds";
                                description "The time elapsed since this entry was created.";
                            }

                        } // list source

                    } // list group

                } // container mld-snooping

                container pim-snooping {
                    description "Enter the pim-snooping context";

                    container ipv4 {
                        description "Enter the ipv4 context";

                        leaf oper-state {
                            type types-sros:oper-state;
                            description
                                "The value of the this object indicates the operational
                                 state of PIM for this interface.";
                        }

                        leaf up-time {
                            type uint32;
                            units "seconds";
                            description "The time since this interface became operational.";
                        }

                        leaf group-count {
                            type uint32;
                            description
                                "The number of multicast groups which currently have this
                                 interface as an outgoing interface.";
                        }

                        leaf maximum-groups-until-now {
                            type uint32;
                            description "The highest value that 'group-count' had till now.";
                        }

                        leaf pseudo-wire-forwarder {
                            type boolean;
                            description
                                "Whether this interface is the forwarding interface
                                 of a pair of redundant pseudo-wire ports.";
                        }

                        container statistics {
                            description "Enter the statistics context";

                            leaf rx-packets {
                                type yang:counter32;
                                description "The number of multicast data packets received on this interface.";
                            }

                            leaf rx-hellos {
                                type yang:counter32;
                                description "The number of PIM hello messages received on this interface.";
                            }

                            leaf rx-join-prunes {
                                type yang:counter32;
                                description
                                    "The number of PIM
                                     Join Prune messages received on this interface.";
                            }

                            leaf tx-packets {
                                type yang:counter32;
                                description "The number of multicast data packets transmitted on this interface.";
                            }

                            leaf tx-join-prunes {
                                type yang:counter32;
                                description
                                    "The number of PIM
                                     Join Prune messages transmitted on this interface.";
                            }

                            leaf rx-hellos-dropped {
                                type yang:counter32;
                                description
                                    "The number of PIM Hello messages which were received on this interface but were
                                     dropped.";
                            }

                            leaf rx-neighbor-unknown {
                                type yang:counter32;
                                description
                                    "The number of PIM messages (other than Hello messages) which were received on this
                                     interface and were rejected because the adjacency with the neighbor
                                     router was not already established.";
                            }

                            leaf rx-bad-checksum-discard {
                                type yang:counter32;
                                description
                                    "The number of PIM messages received on this interface which were discarded because
                                     of bad checksum.";
                            }

                            leaf rx-bad-version-discard {
                                type yang:counter32;
                                description "The number of PIM messages with bad versions received on this interface.";
                            }

                            leaf rx-bad-encodings {
                                type yang:counter32;
                                description "The number of PIM messages with bad encodings received on this interface.";
                            }

                            leaf join-policy-drops {
                                type yang:counter32;
                                description
                                    "The number of times the join policy match resulted in dropping PIM Join-Prune
                                     Message or one of the source group contained in the message.";
                            }

                            leaf rx-join-prune-errors {
                                type yang:counter32;
                                description
                                    "The number of errors while processing Join-Prune messages received on this
                                     interface.";
                            }

                        } // container statistics

                        list neighbor {
                            key "neighbor-address";
                            description "Enter the neighbor list instance";

                            leaf neighbor-address {
                                type types-sros:ipv4-address;
                                description "This value indicates the IPv4 address of the PIM neighbor.";
                            }

                            leaf dr-priority {
                                type uint32;
                                description
                                    "This value indicates neighbor's DR priority which is received
                                     in the hello message. If the Hello Message did not contain
                                     the DR priority field, the value of priority will be '1'.";
                            }

                            leaf dr-priority-present {
                                type boolean;
                                description
                                    "This value of indicates whether the DR priority field was present
                                     in the Hello message received from the PIM neighbor.";
                            }

                            leaf tracking-support {
                                type boolean;
                                description
                                    "This value indicates whether the T bit in the LAN Prune Delay
                                     option was present in the Hello message. This indicates the
                                     neighbor's capability to disable Join message suppression.";
                            }

                            leaf lan-delay {
                                type uint32;
                                units "milliseconds";
                                description
                                    "This value indicates the value of lan delay field present in
                                     the Hello message received from the neighbor. ";
                            }

                            leaf lan-delay-present {
                                type boolean;
                                description
                                    "This value indicates whether the Hello message received from
                                     the neighbor contained the Lan Delay field.";
                            }

                            leaf generated-id {
                                type uint32;
                                description
                                    "This value indicates a randomly generated 32-bit value that is
                                     regenerated each time PIM forwarding is started or restarted on
                                     the interface, including when the router itself restarts.";
                            }

                            leaf override-interval {
                                type uint32;
                                units "milliseconds";
                                description
                                    "This value indicates the value of the override interval present
                                     in the Hello message.";
                            }

                            leaf up-time {
                                type uint32;
                                units "seconds";
                                description
                                    "This value indicates the time since this PIM neighbor (last)
                                     became a neighbor of the local router.";
                            }

                            leaf expiry-time {
                                type uint32;
                                units "seconds";
                                description
                                    "This value indicates the minimum time remaining before this
                                     PIM neighbor will be aged out.";
                            }

                            leaf hold-time {
                                type uint32;
                                units "seconds";
                                description
                                    "This value indicates the value of the hold time present in the
                                     Hello message.";
                            }

                            leaf join-attribute-support {
                                type boolean;
                                description
                                    "This value indicates whether the Hello Message received from
                                     the neighbor contained the Join Attribute field.";
                            }

                            list secondary-neighbor {
                                key "secondary-neighbor-address";
                                description "Enter the secondary-neighbor list instance";

                                leaf secondary-neighbor-address {
                                    type types-sros:ipv4-address;
                                    description
                                        "This value indicates the IPv4 address of the secondary PIM
                                         neighbor.";
                                }

                            } // list secondary-neighbor

                        } // list neighbor

                        list sg {
                            key "group-address source-address";
                            description "Enter the sg list instance";

                            leaf group-address {
                                type types-sros:ipv4-address;
                                description "The multicast group address of the entry.";
                            }

                            leaf source-address {
                                type types-sros:ipv4-address;
                                description "The source address of the multicast sender.";
                            }

                            leaf up-time {
                                type uint32;
                                units "seconds";
                                description "The time since this source group entry got created.";
                            }

                            leaf join-prune-state {
                                type types-pim:join-prune-state;
                                description
                                    "The Join Prune state for this entry on the interface.

                                     PIM Join or Prune messages are sent by the downstream routers
                                     towards the RPF' neighbor.";
                            }

                            leaf join-prune-timer {
                                type uint32;
                                units "seconds";
                                description
                                    "The time remaining before the router transitions the value of
                                     join-prune-state to 'no-info'.

                                     The timer is started or restarted when a valid Join message is
                                     received. If the value of this object is zero and
                                     join-prune-state is 'join' state, it means that the
                                     downstream router sent a holdtime of '0xffff'. In this case,
                                     join-prune-state will not transition until an appropriate
                                     cancelling of Join or Prune message is received.";
                            }

                            leaf prune-pending-timer {
                                type uint32;
                                units "seconds";
                                description
                                    "The time remaining before the router transitions the value of
                                     join-prune-state to 'no-info'.

                                     The timer is set when the PIM Prune message is received.";
                            }

                            leaf join-prune-rpt-state {
                                type types-pim:join-prune-state;
                                description
                                    "The Join Prune Rpt state for this entry on the interface.

                                     PIM Join or Prune messages are sent by the downstream routers towards the
                                     RPF' neighbor. (S,G,rpt) state is a result of receiving (S,G, rpt) JP message
                                     from the downstream router on the RP tree.";
                            }

                            leaf join-prune-rpt-timer {
                                type uint32;
                                units "seconds";
                                description
                                    "The time remaining before the router transitions the value of
                                     join-prune-rpt-state to 'no-info'.

                                     The timer is started or restarted when a valid Join message is
                                     received. If the value of this object is zero and
                                     join-prune-rpt-state is in 'join' state, it means that the
                                     downstream router sent a holdtime of '0xffff'. In this case,
                                     join-prune-rpt-state will not transition until an appropriate
                                     cancelling of Join or Prune message is received from the
                                     downstream router.";
                            }

                            leaf join-prune-rpt-pending-timer {
                                type uint32;
                                units "seconds";
                                description
                                    "The time remaining before the router transitions the value of
                                     join-prune-rpt-state to 'no-info'.

                                     The timer is set when the (S,G,rpt) PIM Prune message is received.";
                            }

                        } // list sg

                    } // container ipv4

                    container ipv6 {
                        description "Enter the ipv6 context";

                        leaf oper-state {
                            type types-sros:oper-state;
                            description
                                "The value of the this object indicates the operational
                                 state of PIM for this interface.";
                        }

                        leaf up-time {
                            type uint32;
                            units "seconds";
                            description "The time since this interface became operational.";
                        }

                        leaf group-count {
                            type uint32;
                            description
                                "The number of multicast groups which currently have this
                                 interface as an outgoing interface.";
                        }

                        leaf maximum-groups-until-now {
                            type uint32;
                            description "The highest value that 'group-count' had till now.";
                        }

                        leaf pseudo-wire-forwarder {
                            type boolean;
                            description
                                "Whether this interface is the forwarding interface
                                 of a pair of redundant pseudo-wire ports.";
                        }

                        container statistics {
                            description "Enter the statistics context";

                            leaf rx-packets {
                                type yang:counter32;
                                description "The number of multicast data packets received on this interface.";
                            }

                            leaf rx-hellos {
                                type yang:counter32;
                                description "The number of PIM hello messages received on this interface.";
                            }

                            leaf rx-join-prunes {
                                type yang:counter32;
                                description
                                    "The number of PIM
                                     Join Prune messages received on this interface.";
                            }

                            leaf tx-packets {
                                type yang:counter32;
                                description "The number of multicast data packets transmitted on this interface.";
                            }

                            leaf tx-join-prunes {
                                type yang:counter32;
                                description
                                    "The number of PIM
                                     Join Prune messages transmitted on this interface.";
                            }

                            leaf rx-hellos-dropped {
                                type yang:counter32;
                                description
                                    "The number of PIM Hello messages which were received on this interface but were
                                     dropped.";
                            }

                            leaf rx-neighbor-unknown {
                                type yang:counter32;
                                description
                                    "The number of PIM messages (other than Hello messages) which were received on this
                                     interface and were rejected because the adjacency with the neighbor
                                     router was not already established.";
                            }

                            leaf rx-bad-checksum-discard {
                                type yang:counter32;
                                description
                                    "The number of PIM messages received on this interface which were discarded because
                                     of bad checksum.";
                            }

                            leaf rx-bad-version-discard {
                                type yang:counter32;
                                description "The number of PIM messages with bad versions received on this interface.";
                            }

                            leaf rx-bad-encodings {
                                type yang:counter32;
                                description "The number of PIM messages with bad encodings received on this interface.";
                            }

                            leaf join-policy-drops {
                                type yang:counter32;
                                description
                                    "The number of times the join policy match resulted in dropping PIM Join-Prune
                                     Message or one of the source group contained in the message.";
                            }

                            leaf rx-join-prune-errors {
                                type yang:counter32;
                                description
                                    "The number of errors while processing Join-Prune messages received on this
                                     interface.";
                            }

                        } // container statistics

                        list neighbor {
                            key "neighbor-address";
                            description "Enter the neighbor list instance";

                            leaf neighbor-address {
                                type types-sros:ipv6-address;
                                description "This value indicates the IPv6 address of the PIM neighbor.";
                            }

                            leaf dr-priority {
                                type uint32;
                                description
                                    "This value indicates neighbor's DR priority which is received
                                     in the hello message. If the Hello Message did not contain
                                     the DR priority field, the value of priority will be '1'.";
                            }

                            leaf dr-priority-present {
                                type boolean;
                                description
                                    "This value of indicates whether the DR priority field was present
                                     in the Hello message received from the PIM neighbor.";
                            }

                            leaf tracking-support {
                                type boolean;
                                description
                                    "This value indicates whether the T bit in the LAN Prune Delay
                                     option was present in the Hello message. This indicates the
                                     neighbor's capability to disable Join message suppression.";
                            }

                            leaf lan-delay {
                                type uint32;
                                units "milliseconds";
                                description
                                    "This value indicates the value of lan delay field present in
                                     the Hello message received from the neighbor. ";
                            }

                            leaf lan-delay-present {
                                type boolean;
                                description
                                    "This value indicates whether the Hello message received from
                                     the neighbor contained the Lan Delay field.";
                            }

                            leaf generated-id {
                                type uint32;
                                description
                                    "This value indicates a randomly generated 32-bit value that is
                                     regenerated each time PIM forwarding is started or restarted on
                                     the interface, including when the router itself restarts.";
                            }

                            leaf override-interval {
                                type uint32;
                                units "milliseconds";
                                description
                                    "This value indicates the value of the override interval present
                                     in the Hello message.";
                            }

                            leaf up-time {
                                type uint32;
                                units "seconds";
                                description
                                    "This value indicates the time since this PIM neighbor (last)
                                     became a neighbor of the local router.";
                            }

                            leaf expiry-time {
                                type uint32;
                                units "seconds";
                                description
                                    "This value indicates the minimum time remaining before this
                                     PIM neighbor will be aged out.";
                            }

                            leaf hold-time {
                                type uint32;
                                units "seconds";
                                description
                                    "This value indicates the value of the hold time present in the
                                     Hello message.";
                            }

                            leaf join-attribute-support {
                                type boolean;
                                description
                                    "This value indicates whether the Hello Message received from
                                     the neighbor contained the Join Attribute field.";
                            }

                            list secondary-neighbor {
                                key "secondary-neighbor-address";
                                description "Enter the secondary-neighbor list instance";

                                leaf secondary-neighbor-address {
                                    type types-sros:ipv6-address;
                                    description
                                        "This value indicates the IPv6 address of the secondary PIM
                                         neighbor.";
                                }

                            } // list secondary-neighbor

                        } // list neighbor

                        list sg {
                            key "group-address source-address";
                            description "Enter the sg list instance";

                            leaf group-address {
                                type types-sros:ipv6-address;
                                description "The multicast group address of the entry.";
                            }

                            leaf source-address {
                                type types-sros:ipv6-address;
                                description "The source address of the multicast sender.";
                            }

                            leaf up-time {
                                type uint32;
                                units "seconds";
                                description "The time since this source group entry got created.";
                            }

                            leaf join-prune-state {
                                type types-pim:join-prune-state;
                                description
                                    "The Join Prune state for this entry on the interface.

                                     PIM Join or Prune messages are sent by the downstream routers
                                     towards the RPF' neighbor.";
                            }

                            leaf join-prune-timer {
                                type uint32;
                                units "seconds";
                                description
                                    "The time remaining before the router transitions the value of
                                     join-prune-state to 'no-info'.

                                     The timer is started or restarted when a valid Join message is
                                     received. If the value of this object is zero and
                                     join-prune-state is 'join' state, it means that the
                                     downstream router sent a holdtime of '0xffff'. In this case,
                                     join-prune-state will not transition until an appropriate
                                     cancelling of Join or Prune message is received.";
                            }

                            leaf prune-pending-timer {
                                type uint32;
                                units "seconds";
                                description
                                    "The time remaining before the router transitions the value of
                                     join-prune-state to 'no-info'.

                                     The timer is set when the PIM Prune message is received.";
                            }

                            leaf join-prune-rpt-state {
                                type types-pim:join-prune-state;
                                description
                                    "The Join Prune Rpt state for this entry on the interface.

                                     PIM Join or Prune messages are sent by the downstream routers towards the
                                     RPF' neighbor. (S,G,rpt) state is a result of receiving (S,G, rpt) JP message
                                     from the downstream router on the RP tree.";
                            }

                            leaf join-prune-rpt-timer {
                                type uint32;
                                units "seconds";
                                description
                                    "The time remaining before the router transitions the value of
                                     join-prune-rpt-state to 'no-info'.

                                     The timer is started or restarted when a valid Join message is
                                     received. If the value of this object is zero and
                                     join-prune-rpt-state is in 'join' state, it means that the
                                     downstream router sent a holdtime of '0xffff'. In this case,
                                     join-prune-rpt-state will not transition until an appropriate
                                     cancelling of Join or Prune message is received from the
                                     downstream router.";
                            }

                            leaf join-prune-rpt-pending-timer {
                                type uint32;
                                units "seconds";
                                description
                                    "The time remaining before the router transitions the value of
                                     join-prune-rpt-state to 'no-info'.

                                     The timer is set when the (S,G,rpt) PIM Prune message is received.";
                            }

                        } // list sg

                    } // container ipv6

                } // container pim-snooping

                container eth-cfm {
                    description "Enter the eth-cfm context";

                    list mep {
                        key "md-admin-name ma-admin-name mep-id";
                        description "Enter the mep list instance";

                        leaf md-admin-name {
                            type leafref {
                                path "../../../../../../eth-cfm/domain/md-admin-name";
                            }
                            description "A unique administratively assigned name used to identify a domain.";
                        }

                        leaf ma-admin-name {
                            type leafref {
                                path "../../../../../../eth-cfm/domain[md-admin-name=current()/../md-admin-name]/association/ma-admin-name";
                            }
                            description "A unique administratively assigned name used to identify an association.";
                        }

                        leaf mep-id {
                            type types-eth-cfm:mep-id-type;
                            description
                                "A CFM Virtual Maintenance Endpoint

                                 Specifies a local Maintenance association End Point identifier unique
                                 over a given maintanance association.";
                        }

                        leaf if-index {
                            type uint32;
                            description "Port ID of the MEP.";
                        }

                        leaf oper-mac-address {
                            type yang:mac-address;
                            description "Operational MAC address of the MEP.";
                        }

                        container ais {
                            description "Enter the ais context";

                            container received {
                                description "Enter the received context";

                                leaf ais-packet {
                                    type boolean;
                                    description "Indicates if the MEP is receiving AIS test frames from one or more of its sub-layer MEPs.";
                                }

                                leaf interval {
                                    type uint32 {
                                        range "1|60";
                                    }
                                    units "seconds";
                                    description "Indicates the AIS Interval received in the last AIS Frame.";
                                }

                            } // container received

                            container transmitted {
                                description "Enter the transmitted context";

                                leaf ais-packet {
                                    type enumeration {
                                        enum no-transmit                    { value 0; }
                                        enum transmit                       { value 1; }
                                        enum pending                        { value 2; }
                                    }
                                    description "Indicates if the MEP is transmitting AIS test frames from one or more of its sub-layer MEPs.";
                                }

                            } // container transmitted

                        } // container ais

                        container csf {
                            description "Enter the csf context";

                            container received {
                                description "Enter the received context";

                                leaf state {
                                    type enumeration {
                                        enum los                            { value 0; }
                                        enum ais                            { value 1; }
                                        enum rdi                            { value 2; }
                                        enum dci                            { value 3; }
                                    }
                                    description
                                        "Indicates the state of the received CSF frames for the MEP.
                                            los (0) - Client Loss of Signal
                                            ais (1) - Client Forward Defect Indication
                                            rdi (2) - Client Reverse Defect Indication
                                            dci (3) - Client Defect Clear Indication.";
                                }

                                leaf interval {
                                    type uint32 {
                                        range "1|60";
                                    }
                                    units "seconds";
                                    description "Indicates the CSF Interval received in the most recent CSF frame.";
                                }

                            } // container received

                        } // container csf

                        container grace {
                            description "Enter the grace context";

                            container transmitted {
                                description "Enter the transmitted context";

                                leaf grace-notification {
                                    type enumeration {
                                        enum no-transmit                    { value 0; }
                                        enum grace                          { value 1; }
                                        enum eth-ed                         { value 2; }
                                    }
                                    description "Indicates the state of the MEP grace period PDU transmission.";
                                }

                            } // container transmitted

                            container received {
                                description "Enter the received context";

                                leaf process-grace-notification {
                                    type boolean;
                                    description
                                        "Indicates whether the local MEP is receiving and processing grace notifications
                                         from one or more peer MEPs. A value of 'true ' indicates the local MEP is
                                         receiving and processing grace from at least one peer MEP. A value
                                         of 'false' indicates that no peer grace notifications are being
                                         received and processed.";
                                }

                            } // container received

                        } // container grace

                        container ccm-states {
                            description "Enter the ccm-states context";

                            leaf transmit-status {
                                type enumeration {
                                    enum no-transmit                    { value 0; }
                                    enum transmit                       { value 1; }
                                    enum suppressed                     { value 2; }
                                }
                                description
                                    "Indicates the state of the MEP CCM PDU transmission.

                                     Values:
                                        noTransmit (0) - no CCM PDUs are being transmitted by the MEP
                                        transmit   (1) - MEP is currently transmitting CCM PDUs
                                        suppressed (2) - MEP should be transmitting CCM PDUs but is suppressing
                                                        them due to an internal condition";
                            }

                            leaf sequence-error {
                                type yang:counter32;
                                description "The total number of out-of-sequence CCMs received from all remote MEPs.";
                            }

                            leaf fng-state {
                                type types-eth-cfm:fng-state-type;
                                description "Current state of the MEP Fault Notification Generator State Machine.";
                            }

                            container transmitted {
                                description "Enter the transmitted context";

                                leaf count {
                                    type yang:counter32;
                                    description "Total number of CCMs transmitted.";
                                }

                                leaf interface-status {
                                    type types-eth-cfm:interface-status;
                                    description
                                        "Indicates the interface status TLV information included in the most
                                         recent Connectivity Check Message (CCM) transmission from the local MEP.
                                         If the local MEP CCM transmissions are not enabled, or if no interface
                                         status TLV was included in the most recent transmission, then
                                         ccm-tx-if-status will return a value of is-no-interface-status-tlv (0).";
                                }

                                leaf port-status {
                                    type types-eth-cfm:port-status;
                                    description
                                        "Indicates the port status TLV information included in the most recent
                                         Connectivity Check Message (CCM) transmission from the local MEP.

                                         If the local MEP CCM transmissions are not enabled, or if no port
                                         status TLV was included in the most recent transmission, then
                                         ccm-tx-port-status will return a value of ps-no-port-state-tlv (0).";
                                }

                                leaf remote-defect-indicator {
                                    type boolean;
                                    description
                                        "Indicates whether or not the Remote Defect Indication (RDI) bit was set
                                         on the most recent Connectivity Check Message (CCM) transmission from the
                                         local MEP.

                                         If the local MEP CCM transmissions are not eanbled, or if the RDI bit
                                         was not set in the most recent transmission, then ccm-tx-rdi will return
                                         a value of 'false (2)'.";
                                }

                            } // container transmitted

                            container received {
                                description "Enter the received context";

                                leaf highest-priority-defect {
                                    type types-eth-cfm:highest-priority-defect-type;
                                    description
                                        "The highest priority defect that has been present since the
                                         MEPs Fault Notification Generator State Machine was last in
                                         the reset state.";
                                }

                                leaf defect-flags {
                                    type types-eth-cfm:mep-defect-flags;
                                    description "A vector of boolean error conditions, any of which may be true.";
                                }

                                list remote-mep-peer {
                                    key "remote-mep-id";
                                    description "Enter the remote-mep-peer list instance";

                                    leaf remote-mep-id {
                                        type types-eth-cfm:mep-id-type;
                                        description "The Remote MEP ID within the same Maintenance Association.";
                                    }

                                    leaf auto-discovered {
                                        type boolean;
                                        description
                                            "Specifies whether or not the remote peer was automatically discovered
                                             ('true') or not. Auto-discovered remote peers are created by the system
                                             only, and are of a 'volatile' storage type. Specifying the value of
                                             'false' will mark an auto-discovered remote peer as permanently configured.";
                                    }

                                    leaf receiving-ccm {
                                        type types-eth-cfm:remote-mep-state-type;
                                        description "The operational CCM receiving state of the remote MEP.";
                                    }

                                    leaf ccm-status-since {
                                        type yang:date-and-time;
                                        description
                                            "The time at which the Remote MEP
                                             last entered either the mep-failed or mep-ok state. ";
                                    }

                                    leaf peer-mac-address {
                                        type yang:mac-address;
                                        description "The MAC address of the remote MEP.";
                                    }

                                    leaf receiving-remote-defect-indicator {
                                        type boolean;
                                        description
                                            "State of the RDI bit in the last received CCM (true for rdi=1), or false
                                             if none has been received.";
                                    }

                                    leaf port-status-tlv {
                                        type types-eth-cfm:port-status;
                                        description
                                            "An enumerated value of the Port status TLV received in the
                                             last CCM from the remote MEP or the default value
                                             ps-no-port-state-tlv indicating either no CCM has been received,
                                             or that no port status TLV was received in the last CCM. ";
                                    }

                                    leaf interface-status-tlv {
                                        type types-eth-cfm:interface-status;
                                        description
                                            "An enumerated value of the Interface status TLV received
                                             in the last CCM from the remote MEP or the default value
                                             is-no-interface-status-tlv indicating either no CCM has been
                                             received, or that no interface status TLV was received in
                                             the last CCM.";
                                    }

                                } // list remote-mep-peer

                            } // container received

                        } // container ccm-states

                        container mc-lag {
                            description "Enter the mc-lag context";

                            leaf inactive-state {
                                type enumeration {
                                    enum not-applicable                 { value 0; }
                                    enum standby                        { value 1; }
                                    enum active                         { value 2; }
                                }
                                description
                                    "Indicates the MC-LAG inactive state of the mep.  The value of
                                     system/eth-cfm/redundancy/mc-lag/standby-mep must be 'true (1)' 
                                     on the node for this leaf to have meaning.";
                            }

                        } // container mc-lag

                        container statistics {
                            description "Enter the statistics context";

                            list opcode {
                                key "opcode-name";
                                description "Enter the opcode list instance";

                                leaf opcode-name {
                                    type types-eth-cfm:statistics-opcode-name;
                                    description "Integer that defines which CFM PDU Opcode the statictics refer to.";
                                }

                                leaf transmitted {
                                    type yang:counter32;
                                    description "The total number of PDUs transmitted from the node with the specified Opcode.";
                                }

                                leaf received {
                                    type yang:counter32;
                                    description "The total number of PDUs received on the node with the specified Opcode.";
                                }

                            } // list opcode

                        } // container statistics

                    } // list mep

                    list mip {
                        key "primary-vlan";
                        description "Enter the mip list instance";

                        leaf primary-vlan {
                            type types-eth-cfm:vlan-id-or-none;
                            description "The VLAN ID to which the MIP is attached or none.";
                        }

                        leaf instantiated {
                            type boolean;
                            description "Indicates if the MIP is instanstiated or not.";
                        }

                        leaf direction {
                            type enumeration {
                                enum both                           { value 0; }
                            }
                            description "Indicates the direction in which the MIP faces on the Bridge Port.";
                        }

                        leaf level {
                            type types-eth-cfm:mp-level;
                            description "Indicate the MD (Maintenance Domain) Level at which MHFs (MIP Half Function) are created.";
                        }

                        leaf level-authority {
                            type types-eth-cfm:mip-authority;
                            description "Indicates the authority context used for leaf level of the instatiated MIP.";
                        }

                        leaf mhf-creation {
                            type enumeration {
                                enum none                           { value 1; }
                                enum default                        { value 2; }
                                enum explicit                       { value 3; }
                                enum defer                          { value 4; }
                                enum static                         { value 32; }
                            }
                            description
                                "A value indicating if the Management entity can create MHFs
                                 (MIP Half Function).";
                        }

                        leaf mhf-creation-authority {
                            type types-eth-cfm:mip-authority;
                            description "Indicates the authority context used for leaf mhf-creation of the instatiated MIP.";
                        }

                        leaf id-permission {
                            type types-eth-cfm:permission-type;
                            description "Indicates the sender ID TLV permissions for the instantiated MIP.";
                        }

                        leaf id-permission-authority {
                            type types-eth-cfm:mip-authority;
                            description "Indicates the authority context used for leaf id-permission of the instatiated MIP.";
                        }

                        leaf mip-ltr-priority {
                            type types-eth-cfm:frame-priority;
                            description "Indicates the priority to use in linktrace response frames to be transmitted for this MIP.";
                        }

                        leaf mip-ltr-priority-authority {
                            type types-eth-cfm:mip-authority;
                            description "Indicates the authority context used for leaf mip-ltr-priority of the instatiated MIP.";
                        }

                    } // list mip

                } // container eth-cfm

                container mrp {
                    description "Enter the mrp context";

                    leaf received-packets {
                        type yang:counter32;
                        description "The number of received MRP packets on this SDP Bind.";
                    }

                    leaf dropped-packets {
                        type yang:counter32;
                        description "The number of dropped MRP packets on this SDP Bind.";
                    }

                    leaf transmitted-packets {
                        type yang:counter32;
                        description "The number of transmitted MRP packets on this SDP Bind.";
                    }

                    leaf received-new-events {
                        type yang:counter32;
                        description "The number of received new MRP events on this SDP Bind.";
                    }

                    leaf received-join-in-events {
                        type yang:counter32;
                        description "The number of received join-in MRP events on this SDP Bind.";
                    }

                    leaf received-in-events {
                        type yang:counter32;
                        description "The number of received in MRP events on this SDP Bind.";
                    }

                    leaf received-join-empty-events {
                        type yang:counter32;
                        description "The number of received join-empty MRP events on this SDP Bind.";
                    }

                    leaf received-empty-events {
                        type yang:counter32;
                        description "The number of received empty MRP events on this SDP Bind.";
                    }

                    leaf received-leave-events {
                        type yang:counter32;
                        description "The number of received leave MRP events on this SDP Bind.";
                    }

                    leaf transmitted-new-events {
                        type yang:counter32;
                        description "The number of transmitted new MRP events on this SDP Bind.";
                    }

                    leaf transmitted-join-in-events {
                        type yang:counter32;
                        description "The number of transmitted join-in MRP events on this SDP Bind.";
                    }

                    leaf transmitted-in-events {
                        type yang:counter32;
                        description "The number of transmitted in MRP events on this SDP Bind.";
                    }

                    leaf transmitted-join-empty-events {
                        type yang:counter32;
                        description "The number of transmitted join-empty MRP events on this SDP Bind.";
                    }

                    leaf transmitted-empty-events {
                        type yang:counter32;
                        description "The number of transmitted empty MRP events on this SDP Bind.";
                    }

                    leaf transmitted-leave-events {
                        type yang:counter32;
                        description "The number of transmitted leave MRP events on this SDP Bind.";
                    }

                } // container mrp

            } // list spoke-sdp

            list mesh-sdp {
                key "sdp-bind-id";
                description "Enter the mesh-sdp list instance";

                leaf sdp-bind-id {
                    type types-services:sdp-bind-id;
                    description
                        "SDP Binding identifier as <sdp-id>:<vc-id>.
                         sdp-id - [1..32767]
                         vc-id - [1..4294967295].";
                }

                leaf oper-state {
                    type enumeration {
                        enum up                             { value 1; }
                        enum down                           { value 5; }
                    }
                    description "Indicates the operating status of this Service-SDP binding.";
                }

                leaf oper-flags {
                    type bits {
                        bit sdp-bind-admin-down            { position 0; }
                        bit svc-admin-down                 { position 1; }
                        bit stitching-svc-txdown           { position 2; }
                        bit sdp-oper-down                  { position 3; }
                        bit sdp-path-mtu-too-small         { position 4; }
                        bit no-ingress-vc-label            { position 5; }
                        bit no-egress-vc-label             { position 6; }
                        bit svc-mtu-mismatch               { position 7; }
                        bit vc-type-mismatch               { position 8; }
                        bit relearn-limit-exceeded         { position 9; }
                        bit ies-if-admin-down              { position 10; }
                        bit released-ingress-vc-label      { position 11; }
                        bit labels-exhausted               { position 12; }
                        bit svc-param-mismatch             { position 13; }
                        bit insufficient-bandwidth         { position 14; }
                        bit pw-peer-fault-status-bits      { position 15; }
                        bit mesh-sdp-down                  { position 16; }
                        bit not-managed-by-mcring          { position 17; }
                        bit out-of-resource                { position 18; }
                        bit mh-standby                     { position 19; }
                        bit oam-down-mep-fault             { position 20; }
                        bit oam-up-mep-fault               { position 21; }
                        bit standby-sig-slave-tx-down      { position 22; }
                        bit oper-grp-down                  { position 23; }
                        bit withdrawn-ingress-vc-label     { position 24; }
                        bit vpls-pmsi-down                 { position 25; }
                        bit rec-prot-src-mac               { position 26; }
                        bit peer-fault-status-tx-down      { position 27; }
                        bit evpn-route-conflict            { position 28; }
                        bit admin-locked                   { position 29; }
                        bit evpn-p2mp-conflict             { position 30; }
                        bit label-stack-limit-exceeded     { position 31; }
                        bit vccv-bfd-down                  { position 32; }
                        bit stitching-svc-pw-fault         { position 33; }
                        bit out-of-anysec-resource         { position 34; }
                        bit anysec-service-and-tunnel-config-conflict { position 35; }
                        bit anysec-group-or-peer-oper-down { position 36; }
                    }
                    description
                        "This object indicates all the conditions that affect the
                         operating status of this SDP Bind.";
                }

                leaf pw-peer-status-bits {
                    type bits {
                        bit pw-not-forwarding              { position 0; }
                        bit lac-ingress-fault              { position 1; }
                        bit lac-egress-fault               { position 2; }
                        bit psn-ingress-fault              { position 3; }
                        bit psn-egress-fault               { position 4; }
                        bit pw-fwding-standby              { position 5; }
                    }
                    description
                        "Indicates bits set by the LDP peer when there is a fault on its
                         side of the pseudowire";
                }

                leaf pw-local-status-bits {
                    type bits {
                        bit pw-not-forwarding              { position 0; }
                        bit lac-ingress-fault              { position 1; }
                        bit lac-egress-fault               { position 2; }
                        bit psn-ingress-fault              { position 3; }
                        bit psn-egress-fault               { position 4; }
                        bit pw-fwding-standby              { position 5; }
                    }
                    description "Indicates locally set bits when there is a fault.";
                }

                leaf peer-vccv-cv-bits {
                    type bits {
                        bit icmp-ping                      { position 0; }
                        bit lsp-ping                       { position 1; }
                        bit bfd-fault-detection            { position 2; }
                        bit bfd-fault-detection-and-signalling { position 3; }
                    }
                    description "Indicates CV type bits set by the LDP peer if it supports VCCV.";
                }

                leaf peer-vccv-cc-bits {
                    type bits {
                        bit pwe3-control-word              { position 0; }
                        bit mpls-router-alert-label        { position 1; }
                        bit mpls-pw-demultiplex-or-label   { position 2; }
                    }
                    description "Indicates CC type bits set by the LDP peer if it supports VCCV.";
                }

                leaf oper-control-word {
                    type boolean;
                    description "Status of control word.";
                }

                leaf pw-fault-ip-address {
                    type types-sros:ip-address;
                    description "Faulty IP address sent by peer.";
                }

                leaf class-forwarding-oper-state {
                    type types-sros:oper-state;
                    description "Operational state of forwarding-class based forwarding on this SDP bind.";
                }

                leaf creation-origin {
                    type types-sros:creation-origin;
                    description "Creation origin of the service.";
                }

                leaf oper-hash-label {
                    type boolean;
                    description "Indicates the negotiated value of hash label that is used on this SDP binding.";
                }

                leaf min-required-sdp-oper-mtu {
                    type int32;
                    description "Minimum required SDP MTU size used with this SDP binding.";
                }

                container ingress {
                    description "Enter the ingress context";

                    leaf oper-label {
                        type uint32;
                        description "MPLS service label used by the far-end device to send packets to the local PEs sdp-bind.";
                    }

                    container statistics {
                        description "Enter the statistics context";

                        leaf forwarded-packets {
                            type yang:counter64;
                            description "Forwarded packets";
                        }

                        leaf forwarded-octets {
                            type yang:counter64;
                            description "Forwarded octets";
                        }

                        leaf dropped-packets {
                            type yang:counter64;
                            description "Dropped packets";
                        }

                        leaf dropped-octets {
                            type yang:counter64;
                            description "Dropped octets";
                        }

                    } // container statistics

                } // container ingress

                container egress {
                    description "Enter the egress context";

                    leaf oper-label {
                        type uint32;
                        description "MPLS service label used to send packets to the far-end device via this sdp-bind.";
                    }

                    container statistics {
                        description "Enter the statistics context";

                        leaf forwarded-packets {
                            type yang:counter64;
                            description "Forwarded packets";
                        }

                        leaf forwarded-octets {
                            type yang:counter64;
                            description "Forwarded octets";
                        }

                    } // container statistics

                } // container egress

                container bfd {
                    description "Enter the bfd context";

                    leaf oper-state {
                        type types-services:bfd-oper-state;
                        description "BFD oper state";
                    }

                } // container bfd

                container fdb {
                    description "Enter the fdb context";

                    container statistics {
                        description "Enter the statistics context";

                        leaf static {
                            type int32;
                            description "Number of static entries in the FDB";
                        }

                        leaf learned {
                            type int32;
                            description "Number of learned entries in the FDB";
                        }

                        leaf oam {
                            type int32;
                            description "Number of OAM entries in the FDB";
                        }

                        leaf conditional-static {
                            type int32;
                            description "Number of conditional static entries in the FDB";
                        }

                    } // container statistics

                    container protected-src-mac-violation {
                        description "Enter the protected-src-mac-violation context";

                        leaf oper-state {
                            type boolean;
                            description "Operational state of the protected-source MAC feature.";
                        }

                        leaf oper-action {
                            type enumeration {
                                enum oper-down                      { value 1; }
                                enum alarm-only                     { value 2; }
                                enum discard-frame                  { value 3; }
                            }
                            description "Operational state of the protected-source MAC violation action.";
                        }

                    } // container protected-src-mac-violation

                } // container fdb

                container ethernet-segment {
                    description "Enter the ethernet-segment context";

                    leaf name {
                        type types-sros:named-item-or-empty;
                        description "Ethernet segment name.";
                    }

                    leaf oper-state {
                        type types-services:evpn-mh-es-status;
                        description "Operational status of the ethernet-segment.";
                    }

                } // container ethernet-segment

                container stp {
                    description "Enter the stp context";

                    leaf port-state {
                        type enumeration {
                            enum disabled                       { value 1; }
                            enum blocking                       { value 2; }
                            enum listening                      { value 3; }
                            enum learning                       { value 4; }
                            enum forwarding                     { value 5; }
                            enum broken                         { value 6; }
                            enum discarding                     { value 7; }
                        }
                        description "The PIP uplink's current state";
                    }

                    leaf hold-down-timer {
                        type enumeration {
                            enum not-active                     { value 1; }
                            enum active                         { value 2; }
                        }
                        description
                            "When the hold-down timer is active, all traffic coming
                             from this mesh sdp will be blocked. This timer will be
                             activated for any of the following cases:
                             1. when a mesh SDP becomes operational;
                             2. when a 'disputed' BPDU is received over this mesh sdp;
                                This is typically a symptom of one way communication
                                (the peer at the other side of the mesh sdp does not
                                receive our BPDUs).
                             3. when a MSTP BPDU from outside the region is received
                                over this mesh SDP.";
                    }

                    leaf transition-state {
                        type enumeration {
                            enum not-applicable                 { value 1; }
                            enum waiting-for-agreement          { value 2; }
                            enum agreement-received             { value 3; }
                        }
                        description
                            "Whether we already received an
                             agreement from the peer connected via this mesh sdp. RSTP
                             expects an agreement from every peer after sending a
                             proposal over the VCP when it wants to transition the latter
                             to the forwarding state. This object is only relevant when
                             the role of the VCP is 'designated'. Not receiving an
                             agreement is typically caused by an improperly configured
                             sdp or by a non rstp enabled peer.";
                    }

                    leaf not-in-mst-region {
                        type boolean;
                        description
                            "Whether we received a BPDU from another MST-region on this mesh SDP.
                             It is up to the operator to make sure bridges connected
                             via mesh SDPs are in the same MST-region. If not the mesh
                             will NOT become operational.";
                    }

                } // container stp

                container igmp-snooping {
                    description "Enter the igmp-snooping context";

                    container mcac {
                        description "Enter the mcac context";

                        leaf in-use-mandatory-bandwidth {
                            type uint32;
                            units "kilobps";
                            description
                                "The in-use bandwidth for the mandatory channels for this
                                 protocol interface instance.";
                        }

                        leaf in-use-optional-bandwidth {
                            type uint32;
                            units "kilobps";
                            description
                                "The in-use bandwidth for the optional channels for this
                                 protocol interface instance.";
                        }

                        leaf available-mandatory-bandwidth {
                            type uint32;
                            units "kilobps";
                            description
                                "The pre-reserved bandwidth for the mandatory channels for
                                 this interface instance.";
                        }

                        leaf available-optional-bandwidth {
                            type uint32;
                            units "kilobps";
                            description "The available bandwidth for this interface instance.";
                        }

                        leaf values-in-transit {
                            type boolean;
                            description
                                "The operational (available and in-use mandatory/optional) value for the
                                 following objects is in transition due to configuration change:
                                 - available-mandatory-bandwidth
                                 - available-bandwidth
                                 - in-use-mandatory-bandwidth
                                 - in-use-optional-bandwidth.";
                        }

                    } // container mcac

                    container statistics {
                        description "Enter the statistics context";

                        container received {
                            description "Enter the received context";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                        } // container received

                        container transmitted {
                            description "Enter the transmitted context";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                            leaf errors {
                                type yang:counter32;
                                description "Transmission Errors.";
                            }

                        } // container transmitted

                        container forwarded {
                            description "Enter the forwarded context";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                            leaf unknown-types {
                                type yang:counter32;
                                description "Unknown types.";
                            }

                            leaf errors {
                                type yang:counter32;
                                description "Forwarding Errors.";
                            }

                        } // container forwarded

                        container error {
                            description "Enter the error context";

                            leaf bad-length {
                                type yang:counter32;
                                description "Bad length.";
                            }

                            leaf bad-ip-checksum {
                                type yang:counter32;
                                description "Bad Ip checksum.";
                            }

                            leaf unknown-type {
                                type yang:counter32;
                                description "Unknown type.";
                            }

                            leaf wrong-version {
                                type yang:counter32;
                                description "Wrong version.";
                            }

                            leaf import-policy-drops {
                                type yang:counter32;
                                description
                                    "Number of times we matched the host IP address or group or
                                     source addresses specified in the import policy.";
                            }

                            leaf missing-router-alert {
                                type yang:counter32;
                                description "Router alert flag is not set.";
                            }

                            leaf bad-encoding {
                                type yang:counter32;
                                description "Badly encoded.";
                            }

                            leaf local-scope {
                                type yang:counter32;
                                description "Link-local scope multicast group address.";
                            }

                            leaf mcac-policy-drops {
                                type yang:counter32;
                                description
                                    "Number of times a join is dropped because of applying a
                                     multicast CAC policy.";
                            }

                            leaf reached-maximum-number-groups {
                                type yang:counter32;
                                description
                                    "Number of times a join is dropped because we reached the maximum
                                     number of groups.";
                            }

                            leaf reached-maximum-number-group-sources {
                                type yang:counter32;
                                description
                                    "Number of times a join is dropped because we reached the maximum
                                     number group-source combinations.";
                            }

                            leaf reached-maximum-number-sources {
                                type yang:counter32;
                                description
                                    "Number of times a join is dropped because we reached the maximum
                                     number of sources per group.";
                            }

                            leaf out-of-memory-drops {
                                type yang:counter32;
                                description "Number of times a join is dropped because we ran out of memory.";
                            }

                            leaf bad-igmp-checksum {
                                type yang:counter32;
                                description
                                    "Number of times a packet is dropped because of a bad IGMP
                                     header checksum.";
                            }

                            leaf zero-source-ip-addr {
                                type yang:counter32;
                                description "Number of times a packet is dropped because it has a zero source ip address.";
                            }

                            leaf send-query-cfg-drops {
                                type yang:counter32;
                                description "Number of times a query is dropped because send-queries is configured.";
                            }

                        } // container error

                    } // container statistics

                    list group {
                        key "group-address";
                        description "Enter the group list instance";

                        leaf group-address {
                            type types-sros:ipv4-multicast-address;
                            description "Group address of multicast channel.";
                        }

                        leaf group-type {
                            type types-igmp:learn-type;
                        }

                        leaf filter-mode {
                            type types-igmp:filter-mode;
                        }

                        leaf expiry-time {
                            type uint32;
                            units "seconds";
                            description "The time left before multicast group timeout.";
                        }

                        leaf up-time {
                            type uint32;
                            units "seconds";
                            description "The time elapsed since this entry was created.";
                        }

                        leaf v1-host-timer {
                            type uint32;
                            units "seconds";
                            description
                                "The time remaining until the local router will assume that
                                 there are no longer any version 1 members.";
                        }

                        leaf v2-host-timer {
                            type uint32;
                            units "seconds";
                            description
                                "The time remaining until the local router will assume that
                                 there are no longer any version 2 members.";
                        }

                        leaf igmp-compatibility-mode {
                            type types-igmp:igmp-version;
                            description "Compatibility with older version routers.";
                        }

                        list source {
                            key "source-address";
                            description "Enter the source list instance";

                            leaf source-address {
                                type types-sros:ipv4-address;
                                description "Source address of multicast channel.";
                            }

                            leaf source-type {
                                type types-igmp:learn-type;
                            }

                            leaf forwarding-state {
                                type types-igmp:forwarding-state;
                                description "Traffic forwardeding state on this port.";
                            }

                            leaf expiry-time {
                                type uint32;
                                units "seconds";
                                description "The time left before multicast group timeout.";
                            }

                            leaf up-time {
                                type uint32;
                                units "seconds";
                                description "The time elapsed since this entry was created.";
                            }

                        } // list source

                    } // list group

                } // container igmp-snooping

                container mld-snooping {
                    description "Enter the mld-snooping context";

                    container statistics {
                        description "Enter the statistics context";

                        container received {
                            description "Enter the received context";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf leaves {
                                type yang:counter32;
                                description "Leaves.";
                            }

                            leaf drops {
                                type yang:counter32;
                                description "Total number of dropped packets.";
                            }

                        } // container received

                        container transmitted {
                            description "Enter the transmitted context";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf leaves {
                                type yang:counter32;
                                description "Leaves.";
                            }

                            leaf drops {
                                type yang:counter32;
                                description "Total number of dropped packets.";
                            }

                            leaf errors {
                                type yang:counter32;
                                description "Transmission Errors.";
                            }

                        } // container transmitted

                        container forwarded {
                            description "Enter the forwarded context";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf leaves {
                                type yang:counter32;
                                description "Leaves.";
                            }

                            leaf drops {
                                type yang:counter32;
                                description "Total number of dropped packets.";
                            }

                            leaf unknown-types {
                                type yang:counter32;
                                description "Unknown types.";
                            }

                            leaf errors {
                                type yang:counter32;
                                description "Forwarding Errors.";
                            }

                        } // container forwarded

                        container error {
                            description "Enter the error context";

                            leaf bad-length {
                                type yang:counter32;
                                description "Bad length.";
                            }

                            leaf unknown-type {
                                type yang:counter32;
                                description "Unknown type.";
                            }

                            leaf wrong-version {
                                type yang:counter32;
                                description "Wrong version.";
                            }

                            leaf import-policy-drops {
                                type yang:counter32;
                                description
                                    "Number of times we matched the host IP address or group or
                                     source addresses specified in the import policy.";
                            }

                            leaf missing-router-alert {
                                type yang:counter32;
                                description "Router alert flag is not set.";
                            }

                            leaf bad-encoding {
                                type yang:counter32;
                                description "Badly encoded.";
                            }

                            leaf local-scope {
                                type yang:counter32;
                                description "Link-local scope multicast group address.";
                            }

                            leaf reserved-scope {
                                type yang:counter32;
                                description "Reserved scope multicast group address.";
                            }

                            leaf reached-maximum-number-groups {
                                type yang:counter32;
                                description
                                    "Number of times a join is dropped because we reached the maximum
                                     number of groups.";
                            }

                            leaf reached-maximum-number-group-sources {
                                type yang:counter32;
                                description
                                    "Number of times a join is dropped because we reached the maximum
                                     number group-source combinations.";
                            }

                            leaf reached-maximum-number-sources {
                                type yang:counter32;
                                description
                                    "Number of times a join is dropped because we reached the maximum
                                     number of sources per group.";
                            }

                            leaf out-of-memory-drops {
                                type yang:counter32;
                                description "Number of times a join is dropped because we ran out of memory.";
                            }

                            leaf bad-mld-checksum {
                                type yang:counter32;
                                description
                                    "Number of times a packet is dropped because of a bad MLD
                                     header checksum.";
                            }

                            leaf zero-source-ip-addr {
                                type yang:counter32;
                                description "Number of times a packet is dropped because it has a zero source ip address.";
                            }

                            leaf send-query-cfg-drops {
                                type yang:counter32;
                                description "Number of times a query is dropped because send-queries is configured.";
                            }

                        } // container error

                    } // container statistics

                    list group {
                        key "group-address";
                        description "Enter the group list instance";

                        leaf group-address {
                            type types-sros:ipv6-multicast-address;
                            description "Group address of multicast channel.";
                        }

                        leaf group-type {
                            type types-igmp:learn-type;
                        }

                        leaf filter-mode {
                            type types-igmp:filter-mode;
                        }

                        leaf expiry-time {
                            type uint32;
                            units "seconds";
                            description "The time left before multicast group timeout.";
                        }

                        leaf up-time {
                            type uint32;
                            units "seconds";
                            description "The time elapsed since this entry was created.";
                        }

                        leaf v1-host-timer {
                            type uint32;
                            units "seconds";
                            description
                                "The time remaining until the local router will assume that
                                 there are no longer any version 1 members.";
                        }

                        leaf mld-compatibility-mode {
                            type types-igmp:mld-version;
                            description "Compatibility with older version routers.";
                        }

                        list source {
                            key "source-address";
                            description "Enter the source list instance";

                            leaf source-address {
                                type types-sros:ipv6-address;
                                description "Source address of multicast channel.";
                            }

                            leaf source-type {
                                type types-igmp:learn-type;
                            }

                            leaf forwarding-state {
                                type types-igmp:forwarding-state;
                                description "Traffic forwardeding state on this port.";
                            }

                            leaf expiry-time {
                                type uint32;
                                units "seconds";
                                description "The time left before multicast group timeout.";
                            }

                            leaf up-time {
                                type uint32;
                                units "seconds";
                                description "The time elapsed since this entry was created.";
                            }

                        } // list source

                    } // list group

                } // container mld-snooping

                container pim-snooping {
                    description "Enter the pim-snooping context";

                    container ipv4 {
                        description "Enter the ipv4 context";

                        leaf oper-state {
                            type types-sros:oper-state;
                            description
                                "The value of the this object indicates the operational
                                 state of PIM for this interface.";
                        }

                        leaf up-time {
                            type uint32;
                            units "seconds";
                            description "The time since this interface became operational.";
                        }

                        leaf group-count {
                            type uint32;
                            description
                                "The number of multicast groups which currently have this
                                 interface as an outgoing interface.";
                        }

                        leaf maximum-groups-until-now {
                            type uint32;
                            description "The highest value that 'group-count' had till now.";
                        }

                        leaf pseudo-wire-forwarder {
                            type boolean;
                            description
                                "Whether this interface is the forwarding interface
                                 of a pair of redundant pseudo-wire ports.";
                        }

                        container statistics {
                            description "Enter the statistics context";

                            leaf rx-packets {
                                type yang:counter32;
                                description "The number of multicast data packets received on this interface.";
                            }

                            leaf rx-hellos {
                                type yang:counter32;
                                description "The number of PIM hello messages received on this interface.";
                            }

                            leaf rx-join-prunes {
                                type yang:counter32;
                                description
                                    "The number of PIM
                                     Join Prune messages received on this interface.";
                            }

                            leaf tx-packets {
                                type yang:counter32;
                                description "The number of multicast data packets transmitted on this interface.";
                            }

                            leaf tx-join-prunes {
                                type yang:counter32;
                                description
                                    "The number of PIM
                                     Join Prune messages transmitted on this interface.";
                            }

                            leaf rx-hellos-dropped {
                                type yang:counter32;
                                description
                                    "The number of PIM Hello messages which were received on this interface but were
                                     dropped.";
                            }

                            leaf rx-neighbor-unknown {
                                type yang:counter32;
                                description
                                    "The number of PIM messages (other than Hello messages) which were received on this
                                     interface and were rejected because the adjacency with the neighbor
                                     router was not already established.";
                            }

                            leaf rx-bad-checksum-discard {
                                type yang:counter32;
                                description
                                    "The number of PIM messages received on this interface which were discarded because
                                     of bad checksum.";
                            }

                            leaf rx-bad-version-discard {
                                type yang:counter32;
                                description "The number of PIM messages with bad versions received on this interface.";
                            }

                            leaf rx-bad-encodings {
                                type yang:counter32;
                                description "The number of PIM messages with bad encodings received on this interface.";
                            }

                            leaf join-policy-drops {
                                type yang:counter32;
                                description
                                    "The number of times the join policy match resulted in dropping PIM Join-Prune
                                     Message or one of the source group contained in the message.";
                            }

                            leaf rx-join-prune-errors {
                                type yang:counter32;
                                description
                                    "The number of errors while processing Join-Prune messages received on this
                                     interface.";
                            }

                        } // container statistics

                        list neighbor {
                            key "neighbor-address";
                            description "Enter the neighbor list instance";

                            leaf neighbor-address {
                                type types-sros:ipv4-address;
                                description "This value indicates the IPv4 address of the PIM neighbor.";
                            }

                            leaf dr-priority {
                                type uint32;
                                description
                                    "This value indicates neighbor's DR priority which is received
                                     in the hello message. If the Hello Message did not contain
                                     the DR priority field, the value of priority will be '1'.";
                            }

                            leaf dr-priority-present {
                                type boolean;
                                description
                                    "This value of indicates whether the DR priority field was present
                                     in the Hello message received from the PIM neighbor.";
                            }

                            leaf tracking-support {
                                type boolean;
                                description
                                    "This value indicates whether the T bit in the LAN Prune Delay
                                     option was present in the Hello message. This indicates the
                                     neighbor's capability to disable Join message suppression.";
                            }

                            leaf lan-delay {
                                type uint32;
                                units "milliseconds";
                                description
                                    "This value indicates the value of lan delay field present in
                                     the Hello message received from the neighbor. ";
                            }

                            leaf lan-delay-present {
                                type boolean;
                                description
                                    "This value indicates whether the Hello message received from
                                     the neighbor contained the Lan Delay field.";
                            }

                            leaf generated-id {
                                type uint32;
                                description
                                    "This value indicates a randomly generated 32-bit value that is
                                     regenerated each time PIM forwarding is started or restarted on
                                     the interface, including when the router itself restarts.";
                            }

                            leaf override-interval {
                                type uint32;
                                units "milliseconds";
                                description
                                    "This value indicates the value of the override interval present
                                     in the Hello message.";
                            }

                            leaf up-time {
                                type uint32;
                                units "seconds";
                                description
                                    "This value indicates the time since this PIM neighbor (last)
                                     became a neighbor of the local router.";
                            }

                            leaf expiry-time {
                                type uint32;
                                units "seconds";
                                description
                                    "This value indicates the minimum time remaining before this
                                     PIM neighbor will be aged out.";
                            }

                            leaf hold-time {
                                type uint32;
                                units "seconds";
                                description
                                    "This value indicates the value of the hold time present in the
                                     Hello message.";
                            }

                            leaf join-attribute-support {
                                type boolean;
                                description
                                    "This value indicates whether the Hello Message received from
                                     the neighbor contained the Join Attribute field.";
                            }

                            list secondary-neighbor {
                                key "secondary-neighbor-address";
                                description "Enter the secondary-neighbor list instance";

                                leaf secondary-neighbor-address {
                                    type types-sros:ipv4-address;
                                    description
                                        "This value indicates the IPv4 address of the secondary PIM
                                         neighbor.";
                                }

                            } // list secondary-neighbor

                        } // list neighbor

                        list sg {
                            key "group-address source-address";
                            description "Enter the sg list instance";

                            leaf group-address {
                                type types-sros:ipv4-address;
                                description "The multicast group address of the entry.";
                            }

                            leaf source-address {
                                type types-sros:ipv4-address;
                                description "The source address of the multicast sender.";
                            }

                            leaf up-time {
                                type uint32;
                                units "seconds";
                                description "The time since this source group entry got created.";
                            }

                            leaf join-prune-state {
                                type types-pim:join-prune-state;
                                description
                                    "The Join Prune state for this entry on the interface.

                                     PIM Join or Prune messages are sent by the downstream routers
                                     towards the RPF' neighbor.";
                            }

                            leaf join-prune-timer {
                                type uint32;
                                units "seconds";
                                description
                                    "The time remaining before the router transitions the value of
                                     join-prune-state to 'no-info'.

                                     The timer is started or restarted when a valid Join message is
                                     received. If the value of this object is zero and
                                     join-prune-state is 'join' state, it means that the
                                     downstream router sent a holdtime of '0xffff'. In this case,
                                     join-prune-state will not transition until an appropriate
                                     cancelling of Join or Prune message is received.";
                            }

                            leaf prune-pending-timer {
                                type uint32;
                                units "seconds";
                                description
                                    "The time remaining before the router transitions the value of
                                     join-prune-state to 'no-info'.

                                     The timer is set when the PIM Prune message is received.";
                            }

                            leaf join-prune-rpt-state {
                                type types-pim:join-prune-state;
                                description
                                    "The Join Prune Rpt state for this entry on the interface.

                                     PIM Join or Prune messages are sent by the downstream routers towards the
                                     RPF' neighbor. (S,G,rpt) state is a result of receiving (S,G, rpt) JP message
                                     from the downstream router on the RP tree.";
                            }

                            leaf join-prune-rpt-timer {
                                type uint32;
                                units "seconds";
                                description
                                    "The time remaining before the router transitions the value of
                                     join-prune-rpt-state to 'no-info'.

                                     The timer is started or restarted when a valid Join message is
                                     received. If the value of this object is zero and
                                     join-prune-rpt-state is in 'join' state, it means that the
                                     downstream router sent a holdtime of '0xffff'. In this case,
                                     join-prune-rpt-state will not transition until an appropriate
                                     cancelling of Join or Prune message is received from the
                                     downstream router.";
                            }

                            leaf join-prune-rpt-pending-timer {
                                type uint32;
                                units "seconds";
                                description
                                    "The time remaining before the router transitions the value of
                                     join-prune-rpt-state to 'no-info'.

                                     The timer is set when the (S,G,rpt) PIM Prune message is received.";
                            }

                        } // list sg

                    } // container ipv4

                    container ipv6 {
                        description "Enter the ipv6 context";

                        leaf oper-state {
                            type types-sros:oper-state;
                            description
                                "The value of the this object indicates the operational
                                 state of PIM for this interface.";
                        }

                        leaf up-time {
                            type uint32;
                            units "seconds";
                            description "The time since this interface became operational.";
                        }

                        leaf group-count {
                            type uint32;
                            description
                                "The number of multicast groups which currently have this
                                 interface as an outgoing interface.";
                        }

                        leaf maximum-groups-until-now {
                            type uint32;
                            description "The highest value that 'group-count' had till now.";
                        }

                        leaf pseudo-wire-forwarder {
                            type boolean;
                            description
                                "Whether this interface is the forwarding interface
                                 of a pair of redundant pseudo-wire ports.";
                        }

                        container statistics {
                            description "Enter the statistics context";

                            leaf rx-packets {
                                type yang:counter32;
                                description "The number of multicast data packets received on this interface.";
                            }

                            leaf rx-hellos {
                                type yang:counter32;
                                description "The number of PIM hello messages received on this interface.";
                            }

                            leaf rx-join-prunes {
                                type yang:counter32;
                                description
                                    "The number of PIM
                                     Join Prune messages received on this interface.";
                            }

                            leaf tx-packets {
                                type yang:counter32;
                                description "The number of multicast data packets transmitted on this interface.";
                            }

                            leaf tx-join-prunes {
                                type yang:counter32;
                                description
                                    "The number of PIM
                                     Join Prune messages transmitted on this interface.";
                            }

                            leaf rx-hellos-dropped {
                                type yang:counter32;
                                description
                                    "The number of PIM Hello messages which were received on this interface but were
                                     dropped.";
                            }

                            leaf rx-neighbor-unknown {
                                type yang:counter32;
                                description
                                    "The number of PIM messages (other than Hello messages) which were received on this
                                     interface and were rejected because the adjacency with the neighbor
                                     router was not already established.";
                            }

                            leaf rx-bad-checksum-discard {
                                type yang:counter32;
                                description
                                    "The number of PIM messages received on this interface which were discarded because
                                     of bad checksum.";
                            }

                            leaf rx-bad-version-discard {
                                type yang:counter32;
                                description "The number of PIM messages with bad versions received on this interface.";
                            }

                            leaf rx-bad-encodings {
                                type yang:counter32;
                                description "The number of PIM messages with bad encodings received on this interface.";
                            }

                            leaf join-policy-drops {
                                type yang:counter32;
                                description
                                    "The number of times the join policy match resulted in dropping PIM Join-Prune
                                     Message or one of the source group contained in the message.";
                            }

                            leaf rx-join-prune-errors {
                                type yang:counter32;
                                description
                                    "The number of errors while processing Join-Prune messages received on this
                                     interface.";
                            }

                        } // container statistics

                        list neighbor {
                            key "neighbor-address";
                            description "Enter the neighbor list instance";

                            leaf neighbor-address {
                                type types-sros:ipv6-address;
                                description "This value indicates the IPv6 address of the PIM neighbor.";
                            }

                            leaf dr-priority {
                                type uint32;
                                description
                                    "This value indicates neighbor's DR priority which is received
                                     in the hello message. If the Hello Message did not contain
                                     the DR priority field, the value of priority will be '1'.";
                            }

                            leaf dr-priority-present {
                                type boolean;
                                description
                                    "This value of indicates whether the DR priority field was present
                                     in the Hello message received from the PIM neighbor.";
                            }

                            leaf tracking-support {
                                type boolean;
                                description
                                    "This value indicates whether the T bit in the LAN Prune Delay
                                     option was present in the Hello message. This indicates the
                                     neighbor's capability to disable Join message suppression.";
                            }

                            leaf lan-delay {
                                type uint32;
                                units "milliseconds";
                                description
                                    "This value indicates the value of lan delay field present in
                                     the Hello message received from the neighbor. ";
                            }

                            leaf lan-delay-present {
                                type boolean;
                                description
                                    "This value indicates whether the Hello message received from
                                     the neighbor contained the Lan Delay field.";
                            }

                            leaf generated-id {
                                type uint32;
                                description
                                    "This value indicates a randomly generated 32-bit value that is
                                     regenerated each time PIM forwarding is started or restarted on
                                     the interface, including when the router itself restarts.";
                            }

                            leaf override-interval {
                                type uint32;
                                units "milliseconds";
                                description
                                    "This value indicates the value of the override interval present
                                     in the Hello message.";
                            }

                            leaf up-time {
                                type uint32;
                                units "seconds";
                                description
                                    "This value indicates the time since this PIM neighbor (last)
                                     became a neighbor of the local router.";
                            }

                            leaf expiry-time {
                                type uint32;
                                units "seconds";
                                description
                                    "This value indicates the minimum time remaining before this
                                     PIM neighbor will be aged out.";
                            }

                            leaf hold-time {
                                type uint32;
                                units "seconds";
                                description
                                    "This value indicates the value of the hold time present in the
                                     Hello message.";
                            }

                            leaf join-attribute-support {
                                type boolean;
                                description
                                    "This value indicates whether the Hello Message received from
                                     the neighbor contained the Join Attribute field.";
                            }

                            list secondary-neighbor {
                                key "secondary-neighbor-address";
                                description "Enter the secondary-neighbor list instance";

                                leaf secondary-neighbor-address {
                                    type types-sros:ipv6-address;
                                    description
                                        "This value indicates the IPv6 address of the secondary PIM
                                         neighbor.";
                                }

                            } // list secondary-neighbor

                        } // list neighbor

                        list sg {
                            key "group-address source-address";
                            description "Enter the sg list instance";

                            leaf group-address {
                                type types-sros:ipv6-address;
                                description "The multicast group address of the entry.";
                            }

                            leaf source-address {
                                type types-sros:ipv6-address;
                                description "The source address of the multicast sender.";
                            }

                            leaf up-time {
                                type uint32;
                                units "seconds";
                                description "The time since this source group entry got created.";
                            }

                            leaf join-prune-state {
                                type types-pim:join-prune-state;
                                description
                                    "The Join Prune state for this entry on the interface.

                                     PIM Join or Prune messages are sent by the downstream routers
                                     towards the RPF' neighbor.";
                            }

                            leaf join-prune-timer {
                                type uint32;
                                units "seconds";
                                description
                                    "The time remaining before the router transitions the value of
                                     join-prune-state to 'no-info'.

                                     The timer is started or restarted when a valid Join message is
                                     received. If the value of this object is zero and
                                     join-prune-state is 'join' state, it means that the
                                     downstream router sent a holdtime of '0xffff'. In this case,
                                     join-prune-state will not transition until an appropriate
                                     cancelling of Join or Prune message is received.";
                            }

                            leaf prune-pending-timer {
                                type uint32;
                                units "seconds";
                                description
                                    "The time remaining before the router transitions the value of
                                     join-prune-state to 'no-info'.

                                     The timer is set when the PIM Prune message is received.";
                            }

                            leaf join-prune-rpt-state {
                                type types-pim:join-prune-state;
                                description
                                    "The Join Prune Rpt state for this entry on the interface.

                                     PIM Join or Prune messages are sent by the downstream routers towards the
                                     RPF' neighbor. (S,G,rpt) state is a result of receiving (S,G, rpt) JP message
                                     from the downstream router on the RP tree.";
                            }

                            leaf join-prune-rpt-timer {
                                type uint32;
                                units "seconds";
                                description
                                    "The time remaining before the router transitions the value of
                                     join-prune-rpt-state to 'no-info'.

                                     The timer is started or restarted when a valid Join message is
                                     received. If the value of this object is zero and
                                     join-prune-rpt-state is in 'join' state, it means that the
                                     downstream router sent a holdtime of '0xffff'. In this case,
                                     join-prune-rpt-state will not transition until an appropriate
                                     cancelling of Join or Prune message is received from the
                                     downstream router.";
                            }

                            leaf join-prune-rpt-pending-timer {
                                type uint32;
                                units "seconds";
                                description
                                    "The time remaining before the router transitions the value of
                                     join-prune-rpt-state to 'no-info'.

                                     The timer is set when the (S,G,rpt) PIM Prune message is received.";
                            }

                        } // list sg

                    } // container ipv6

                } // container pim-snooping

                container eth-cfm {
                    description "Enter the eth-cfm context";

                    list mep {
                        key "md-admin-name ma-admin-name mep-id";
                        description "Enter the mep list instance";

                        leaf md-admin-name {
                            type leafref {
                                path "../../../../../../eth-cfm/domain/md-admin-name";
                            }
                            description "A unique administratively assigned name used to identify a domain.";
                        }

                        leaf ma-admin-name {
                            type leafref {
                                path "../../../../../../eth-cfm/domain[md-admin-name=current()/../md-admin-name]/association/ma-admin-name";
                            }
                            description "A unique administratively assigned name used to identify an association.";
                        }

                        leaf mep-id {
                            type types-eth-cfm:mep-id-type;
                            description
                                "A CFM Virtual Maintenance Endpoint

                                 Specifies a local Maintenance association End Point identifier unique
                                 over a given maintanance association.";
                        }

                        leaf if-index {
                            type uint32;
                            description "Port ID of the MEP.";
                        }

                        leaf oper-mac-address {
                            type yang:mac-address;
                            description "Operational MAC address of the MEP.";
                        }

                        container ais {
                            description "Enter the ais context";

                            container received {
                                description "Enter the received context";

                                leaf ais-packet {
                                    type boolean;
                                    description "Indicates if the MEP is receiving AIS test frames from one or more of its sub-layer MEPs.";
                                }

                                leaf interval {
                                    type uint32 {
                                        range "1|60";
                                    }
                                    units "seconds";
                                    description "Indicates the AIS Interval received in the last AIS Frame.";
                                }

                            } // container received

                            container transmitted {
                                description "Enter the transmitted context";

                                leaf ais-packet {
                                    type enumeration {
                                        enum no-transmit                    { value 0; }
                                        enum transmit                       { value 1; }
                                        enum pending                        { value 2; }
                                    }
                                    description "Indicates if the MEP is transmitting AIS test frames from one or more of its sub-layer MEPs.";
                                }

                            } // container transmitted

                        } // container ais

                        container csf {
                            description "Enter the csf context";

                            container received {
                                description "Enter the received context";

                                leaf state {
                                    type enumeration {
                                        enum los                            { value 0; }
                                        enum ais                            { value 1; }
                                        enum rdi                            { value 2; }
                                        enum dci                            { value 3; }
                                    }
                                    description
                                        "Indicates the state of the received CSF frames for the MEP.
                                            los (0) - Client Loss of Signal
                                            ais (1) - Client Forward Defect Indication
                                            rdi (2) - Client Reverse Defect Indication
                                            dci (3) - Client Defect Clear Indication.";
                                }

                                leaf interval {
                                    type uint32 {
                                        range "1|60";
                                    }
                                    units "seconds";
                                    description "Indicates the CSF Interval received in the most recent CSF frame.";
                                }

                            } // container received

                        } // container csf

                        container grace {
                            description "Enter the grace context";

                            container transmitted {
                                description "Enter the transmitted context";

                                leaf grace-notification {
                                    type enumeration {
                                        enum no-transmit                    { value 0; }
                                        enum grace                          { value 1; }
                                        enum eth-ed                         { value 2; }
                                    }
                                    description "Indicates the state of the MEP grace period PDU transmission.";
                                }

                            } // container transmitted

                            container received {
                                description "Enter the received context";

                                leaf process-grace-notification {
                                    type boolean;
                                    description
                                        "Indicates whether the local MEP is receiving and processing grace notifications
                                         from one or more peer MEPs. A value of 'true ' indicates the local MEP is
                                         receiving and processing grace from at least one peer MEP. A value
                                         of 'false' indicates that no peer grace notifications are being
                                         received and processed.";
                                }

                            } // container received

                        } // container grace

                        container ccm-states {
                            description "Enter the ccm-states context";

                            leaf transmit-status {
                                type enumeration {
                                    enum no-transmit                    { value 0; }
                                    enum transmit                       { value 1; }
                                    enum suppressed                     { value 2; }
                                }
                                description
                                    "Indicates the state of the MEP CCM PDU transmission.

                                     Values:
                                        noTransmit (0) - no CCM PDUs are being transmitted by the MEP
                                        transmit   (1) - MEP is currently transmitting CCM PDUs
                                        suppressed (2) - MEP should be transmitting CCM PDUs but is suppressing
                                                        them due to an internal condition";
                            }

                            leaf sequence-error {
                                type yang:counter32;
                                description "The total number of out-of-sequence CCMs received from all remote MEPs.";
                            }

                            leaf fng-state {
                                type types-eth-cfm:fng-state-type;
                                description "Current state of the MEP Fault Notification Generator State Machine.";
                            }

                            container transmitted {
                                description "Enter the transmitted context";

                                leaf count {
                                    type yang:counter32;
                                    description "Total number of CCMs transmitted.";
                                }

                                leaf interface-status {
                                    type types-eth-cfm:interface-status;
                                    description
                                        "Indicates the interface status TLV information included in the most
                                         recent Connectivity Check Message (CCM) transmission from the local MEP.
                                         If the local MEP CCM transmissions are not enabled, or if no interface
                                         status TLV was included in the most recent transmission, then
                                         ccm-tx-if-status will return a value of is-no-interface-status-tlv (0).";
                                }

                                leaf port-status {
                                    type types-eth-cfm:port-status;
                                    description
                                        "Indicates the port status TLV information included in the most recent
                                         Connectivity Check Message (CCM) transmission from the local MEP.

                                         If the local MEP CCM transmissions are not enabled, or if no port
                                         status TLV was included in the most recent transmission, then
                                         ccm-tx-port-status will return a value of ps-no-port-state-tlv (0).";
                                }

                                leaf remote-defect-indicator {
                                    type boolean;
                                    description
                                        "Indicates whether or not the Remote Defect Indication (RDI) bit was set
                                         on the most recent Connectivity Check Message (CCM) transmission from the
                                         local MEP.

                                         If the local MEP CCM transmissions are not eanbled, or if the RDI bit
                                         was not set in the most recent transmission, then ccm-tx-rdi will return
                                         a value of 'false (2)'.";
                                }

                            } // container transmitted

                            container received {
                                description "Enter the received context";

                                leaf highest-priority-defect {
                                    type types-eth-cfm:highest-priority-defect-type;
                                    description
                                        "The highest priority defect that has been present since the
                                         MEPs Fault Notification Generator State Machine was last in
                                         the reset state.";
                                }

                                leaf defect-flags {
                                    type types-eth-cfm:mep-defect-flags;
                                    description "A vector of boolean error conditions, any of which may be true.";
                                }

                                list remote-mep-peer {
                                    key "remote-mep-id";
                                    description "Enter the remote-mep-peer list instance";

                                    leaf remote-mep-id {
                                        type types-eth-cfm:mep-id-type;
                                        description "The Remote MEP ID within the same Maintenance Association.";
                                    }

                                    leaf auto-discovered {
                                        type boolean;
                                        description
                                            "Specifies whether or not the remote peer was automatically discovered
                                             ('true') or not. Auto-discovered remote peers are created by the system
                                             only, and are of a 'volatile' storage type. Specifying the value of
                                             'false' will mark an auto-discovered remote peer as permanently configured.";
                                    }

                                    leaf receiving-ccm {
                                        type types-eth-cfm:remote-mep-state-type;
                                        description "The operational CCM receiving state of the remote MEP.";
                                    }

                                    leaf ccm-status-since {
                                        type yang:date-and-time;
                                        description
                                            "The time at which the Remote MEP
                                             last entered either the mep-failed or mep-ok state. ";
                                    }

                                    leaf peer-mac-address {
                                        type yang:mac-address;
                                        description "The MAC address of the remote MEP.";
                                    }

                                    leaf receiving-remote-defect-indicator {
                                        type boolean;
                                        description
                                            "State of the RDI bit in the last received CCM (true for rdi=1), or false
                                             if none has been received.";
                                    }

                                    leaf port-status-tlv {
                                        type types-eth-cfm:port-status;
                                        description
                                            "An enumerated value of the Port status TLV received in the
                                             last CCM from the remote MEP or the default value
                                             ps-no-port-state-tlv indicating either no CCM has been received,
                                             or that no port status TLV was received in the last CCM. ";
                                    }

                                    leaf interface-status-tlv {
                                        type types-eth-cfm:interface-status;
                                        description
                                            "An enumerated value of the Interface status TLV received
                                             in the last CCM from the remote MEP or the default value
                                             is-no-interface-status-tlv indicating either no CCM has been
                                             received, or that no interface status TLV was received in
                                             the last CCM.";
                                    }

                                } // list remote-mep-peer

                            } // container received

                        } // container ccm-states

                        container mc-lag {
                            description "Enter the mc-lag context";

                            leaf inactive-state {
                                type enumeration {
                                    enum not-applicable                 { value 0; }
                                    enum standby                        { value 1; }
                                    enum active                         { value 2; }
                                }
                                description
                                    "Indicates the MC-LAG inactive state of the mep.  The value of
                                     system/eth-cfm/redundancy/mc-lag/standby-mep must be 'true (1)' 
                                     on the node for this leaf to have meaning.";
                            }

                        } // container mc-lag

                        container statistics {
                            description "Enter the statistics context";

                            list opcode {
                                key "opcode-name";
                                description "Enter the opcode list instance";

                                leaf opcode-name {
                                    type types-eth-cfm:statistics-opcode-name;
                                    description "Integer that defines which CFM PDU Opcode the statictics refer to.";
                                }

                                leaf transmitted {
                                    type yang:counter32;
                                    description "The total number of PDUs transmitted from the node with the specified Opcode.";
                                }

                                leaf received {
                                    type yang:counter32;
                                    description "The total number of PDUs received on the node with the specified Opcode.";
                                }

                            } // list opcode

                        } // container statistics

                    } // list mep

                    list mip {
                        key "primary-vlan";
                        description "Enter the mip list instance";

                        leaf primary-vlan {
                            type types-eth-cfm:vlan-id-or-none;
                            description "The VLAN ID to which the MIP is attached or none.";
                        }

                        leaf instantiated {
                            type boolean;
                            description "Indicates if the MIP is instanstiated or not.";
                        }

                        leaf direction {
                            type enumeration {
                                enum both                           { value 0; }
                            }
                            description "Indicates the direction in which the MIP faces on the Bridge Port.";
                        }

                        leaf level {
                            type types-eth-cfm:mp-level;
                            description "Indicate the MD (Maintenance Domain) Level at which MHFs (MIP Half Function) are created.";
                        }

                        leaf level-authority {
                            type types-eth-cfm:mip-authority;
                            description "Indicates the authority context used for leaf level of the instatiated MIP.";
                        }

                        leaf mhf-creation {
                            type enumeration {
                                enum none                           { value 1; }
                                enum default                        { value 2; }
                                enum explicit                       { value 3; }
                                enum defer                          { value 4; }
                                enum static                         { value 32; }
                            }
                            description
                                "A value indicating if the Management entity can create MHFs
                                 (MIP Half Function).";
                        }

                        leaf mhf-creation-authority {
                            type types-eth-cfm:mip-authority;
                            description "Indicates the authority context used for leaf mhf-creation of the instatiated MIP.";
                        }

                        leaf id-permission {
                            type types-eth-cfm:permission-type;
                            description "Indicates the sender ID TLV permissions for the instantiated MIP.";
                        }

                        leaf id-permission-authority {
                            type types-eth-cfm:mip-authority;
                            description "Indicates the authority context used for leaf id-permission of the instatiated MIP.";
                        }

                        leaf mip-ltr-priority {
                            type types-eth-cfm:frame-priority;
                            description "Indicates the priority to use in linktrace response frames to be transmitted for this MIP.";
                        }

                        leaf mip-ltr-priority-authority {
                            type types-eth-cfm:mip-authority;
                            description "Indicates the authority context used for leaf mip-ltr-priority of the instatiated MIP.";
                        }

                    } // list mip

                } // container eth-cfm

                container mrp {
                    description "Enter the mrp context";

                    leaf received-packets {
                        type yang:counter32;
                        description "The number of received MRP packets on this SDP Bind.";
                    }

                    leaf dropped-packets {
                        type yang:counter32;
                        description "The number of dropped MRP packets on this SDP Bind.";
                    }

                    leaf transmitted-packets {
                        type yang:counter32;
                        description "The number of transmitted MRP packets on this SDP Bind.";
                    }

                    leaf received-new-events {
                        type yang:counter32;
                        description "The number of received new MRP events on this SDP Bind.";
                    }

                    leaf received-join-in-events {
                        type yang:counter32;
                        description "The number of received join-in MRP events on this SDP Bind.";
                    }

                    leaf received-in-events {
                        type yang:counter32;
                        description "The number of received in MRP events on this SDP Bind.";
                    }

                    leaf received-join-empty-events {
                        type yang:counter32;
                        description "The number of received join-empty MRP events on this SDP Bind.";
                    }

                    leaf received-empty-events {
                        type yang:counter32;
                        description "The number of received empty MRP events on this SDP Bind.";
                    }

                    leaf received-leave-events {
                        type yang:counter32;
                        description "The number of received leave MRP events on this SDP Bind.";
                    }

                    leaf transmitted-new-events {
                        type yang:counter32;
                        description "The number of transmitted new MRP events on this SDP Bind.";
                    }

                    leaf transmitted-join-in-events {
                        type yang:counter32;
                        description "The number of transmitted join-in MRP events on this SDP Bind.";
                    }

                    leaf transmitted-in-events {
                        type yang:counter32;
                        description "The number of transmitted in MRP events on this SDP Bind.";
                    }

                    leaf transmitted-join-empty-events {
                        type yang:counter32;
                        description "The number of transmitted join-empty MRP events on this SDP Bind.";
                    }

                    leaf transmitted-empty-events {
                        type yang:counter32;
                        description "The number of transmitted empty MRP events on this SDP Bind.";
                    }

                    leaf transmitted-leave-events {
                        type yang:counter32;
                        description "The number of transmitted leave MRP events on this SDP Bind.";
                    }

                } // container mrp

            } // list mesh-sdp

            list bgp-mh-site {
                key "site-name";
                description "Enter the bgp-mh-site list instance";

                leaf site-name {
                    type types-sros:named-item;
                    description "Name for the specific site";
                }

                leaf oper-state {
                    type enumeration {
                        enum up                             { value 1; }
                        enum down                           { value 2; }
                        enum out-of-resource                { value 3; }
                    }
                    description "Operational status of the site";
                }

                leaf active-timer-remain {
                    type uint32;
                    units "seconds";
                    description "Remaining time in the active-timer";
                }

                leaf boot-timer-remain {
                    type uint32;
                    units "seconds";
                    description "Remaining time in the boot-timer";
                }

                leaf min-down-timer-remain {
                    type uint32;
                    units "seconds";
                    description "Remaining time in the down-timer";
                }

                container designated-forwarder {
                    description "Enter the designated-forwarder context";

                    leaf state {
                        type boolean;
                        description "State of designated forwarder";
                    }

                    leaf up-time {
                        type uint32;
                        units "seconds";
                        description "Uptime of the designated forwarder";
                    }

                    leaf change-count {
                        type uint32;
                        description "Number of times designated forwarder has changed";
                    }

                } // container designated-forwarder

            } // list bgp-mh-site

            list sap {
                key "sap-id";
                description "Enter the sap list instance";

                leaf sap-id {
                    type types-sros:sap;
                    description "SAP identifier";
                }

                leaf oper-state {
                    type enumeration {
                        enum up                             { value 1; }
                        enum down                           { value 2; }
                    }
                    description "Operating state of this SAP";
                }

                leaf oper-flags {
                    type types-services:l2-sap-oper-flags;
                    description "Conditions that affect the operating status of this SAP.";
                }

                leaf mirror-state {
                    type enumeration {
                        enum ingress                        { value 1; }
                        enum egress                         { value 2; }
                        enum ingress-and-egress             { value 3; }
                        enum disabled                       { value 4; }
                    }
                    description "Indicates whether traffic mirroring has been enabled on this SAP";
                }

                leaf template-used {
                    type types-sros:named-item-or-empty;
                    description "Name of the sap-template used to create this sap.";
                }

                leaf bpdu-translated-frames-encap {
                    type enumeration {
                        enum undefined                      { value 1; }
                        enum disabled                       { value 2; }
                        enum pvst                           { value 3; }
                        enum stp                            { value 4; }
                        enum pvst-rw                        { value 5; }
                    }
                    description
                        "Operational bpdu encapsulation used for BPDU
                         translated frames.";
                }

                leaf oper-dist-cpu-prot-policy {
                    type types-sros:named-item-or-empty;
                    description "Operational Distributed CPU Protection Policy.";
                }

                container statistics {
                    description "Enter the statistics context";

                    container authentication {
                        description "Enter the authentication context";

                        leaf discarded-packets {
                            type yang:counter32;
                            description
                                "The number of DHCP packets discarded
                                 as result of authentication.";
                        }

                        leaf success-packets {
                            type yang:counter32;
                            description "The number of DHCP packets successfully authenticated.";
                        }

                    } // container authentication

                } // container statistics

                container ingress {
                    description "Enter the ingress context";

                    container qos {
                        description "Enter the qos context";

                        container sap-ingress {
                            description "Enter the sap-ingress context";

                            container forwarding-engine {
                                description "Enter the forwarding-engine context";

                                container statistics {
                                    description "Enter the statistics context";

                                    leaf dropped-packets {
                                        type yang:counter64;
                                        description
                                            "The number of packets dropped by the
                                             ingress packet processor due to: SAP state,
                                             ingress MAC, IP or IPv6 filter, same segment
                                             discard, bad checksum, etc.";
                                    }

                                    leaf dropped-octets {
                                        type yang:counter64;
                                        description
                                            "The number of octets dropped by the
                                             ingress packet processor due to: SAP state,
                                             ingress MAC, IP or IPv6 filter, same segment
                                             discard, bad checksum, etc.";
                                    }

                                    leaf received-valid-packets {
                                        type yang:counter64;
                                        description
                                            "The value of received-valid indicates
                                             number of received valid packets, as determined by the SAP
                                             ingress QoS policy, offered by the packet processor to the traffic manager.";
                                    }

                                    leaf received-valid-octets {
                                        type yang:counter64;
                                        description
                                            "The value of received-valid indicates
                                             number of received valid octets, as determined by the SAP
                                             ingress QoS policy, offered by the packet processor to the traffic manager.";
                                    }

                                    leaf high-priority-offered-packets {
                                        type yang:counter64;
                                        description
                                            "The number of high priority packets,
                                             as determined by the SAP ingress QoS
                                             policy, offered by the packet processor to the
                                             traffic manager.";
                                    }

                                    leaf high-priority-offered-octets {
                                        type yang:counter64;
                                        description
                                            "The number of high priority octets,
                                             as determined by the SAP ingress QoS
                                             policy, offered by the packet processor to the
                                             traffic manager.";
                                    }

                                    leaf low-priority-offered-packets {
                                        type yang:counter64;
                                        description
                                            "The number of low priority packets,
                                             as determined by the SAP ingress QoS
                                             policy, offered by the packet processor to the
                                             traffic manager.";
                                    }

                                    leaf low-priority-offered-octets {
                                        type yang:counter64;
                                        description
                                            "The number of low priority octets,
                                             as determined by the SAP ingress QoS
                                             policy, offered by the packet processor to the
                                             traffic manager.";
                                    }

                                    leaf uncolor-offered-packets {
                                        type yang:counter64;
                                        description
                                            "The number of uncolored packets,
                                             as determined by the SAP ingress QoS
                                             policy, offered by the packet processor to the
                                             traffic manager.";
                                    }

                                    leaf uncolor-offered-octets {
                                        type yang:counter64;
                                        description
                                            "The number of uncolored octets,
                                             as determined by the SAP ingress QoS
                                             policy, offered by the packet processor to the
                                             traffic manager.";
                                    }

                                    leaf managed-offered-packets {
                                        type yang:counter64;
                                        description
                                            "The value of managed-offered indicates
                                             number of managed multicast packets, as determined by the SAP
                                             ingress QoS policy, offered by the packet processor to the traffic manager.";
                                    }

                                    leaf managed-offered-octets {
                                        type yang:counter64;
                                        description
                                            "The value of managed-offered indicates
                                             number of managed multicast octets, as determined by the SAP
                                             ingress QoS policy, offered by the packet processor to the traffic manager.";
                                    }

                                    leaf aggregate-offered-packets {
                                        type yang:counter64;
                                        description
                                            "The value of aggregate-offered indicates aggregate
                                             number of hi, lo priority and uncolour packets,
                                             as determined by the SAP ingress QoS policy,
                                             offered by the packet processor to the traffic manager.";
                                    }

                                    leaf aggregate-offered-octets {
                                        type yang:counter64;
                                        description
                                            "The value of managed-offered indicates aggregate
                                             number of hi, lo priority and uncolour octets,
                                             as determined by the SAP ingress QoS policy,
                                             offered by the packet processor to the traffic manager.";
                                    }

                                    leaf last-cleared-time {
                                        type yang:date-and-time;
                                        description "Time when the counters in this table were last cleared.";
                                    }

                                } // container statistics

                            } // container forwarding-engine

                            container traffic-manager {
                                description "Enter the traffic-manager context";

                                container statistics {
                                    description "Enter the statistics context";

                                    leaf cpm-packets {
                                        type yang:counter64;
                                        description
                                            "The value of cpm-packets indicates
                                             ingress traffic in terms of packets destined to CPM
                                             associated with this SAP.";
                                    }

                                    leaf cpm-octets {
                                        type yang:counter64;
                                        description
                                            "The value of cpm indicates
                                             ingress traffic in terms of bytes destined to CPM
                                             associated with this SAP.";
                                    }

                                    leaf high-priority-dropped-packets {
                                        type yang:counter64;
                                        description
                                            "The number of high priority packets,
                                             as determined by the SAP ingress QoS
                                             policy, dropped by the traffic manager due to:
                                             MBS exceeded, buffer pool limit
                                             exceeded, etc.";
                                    }

                                    leaf high-priority-dropped-octets {
                                        type yang:counter64;
                                        description
                                            "The number of high priority octets,
                                             as determined by the SAP ingress QoS
                                             policy, dropped by the traffic manager due to:
                                             MBS exceeded, buffer pool limit
                                             exceeded, etc.";
                                    }

                                    leaf low-priority-dropped-packets {
                                        type yang:counter64;
                                        description
                                            "The number of low priority packets,
                                             as determined by the SAP ingress QoS
                                             policy, dropped by the traffic manager due to:
                                             MBS exceeded, buffer pool limit
                                             exceeded, etc.";
                                    }

                                    leaf low-priority-dropped-octets {
                                        type yang:counter64;
                                        description
                                            "The number of low priority octets,
                                             as determined by the SAP ingress QoS
                                             policy, dropped by the traffic manager due to:
                                             MBS exceeded, buffer pool limit
                                             exceeded, etc.";
                                    }

                                    leaf in-profile-forwarded-packets {
                                        type yang:counter64;
                                        description
                                            "The number of in-profile packets
                                             (rate below CIR) forwarded by the
                                             ingress traffic manager.";
                                    }

                                    leaf in-profile-forwarded-octets {
                                        type yang:counter64;
                                        description
                                            "The number of in-profile octets
                                             (rate below CIR) forwarded by the
                                             ingress traffic manager.";
                                    }

                                    leaf out-profile-forwarded-packets {
                                        type yang:counter64;
                                        description
                                            "The number of out-of-profile packets
                                             (rate above CIR) forwarded by the
                                             ingress traffic manager.";
                                    }

                                    leaf out-profile-forwarded-octets {
                                        type yang:counter64;
                                        description
                                            "The number of out-of-profile octets
                                             (rate above CIR) forwarded by the
                                             ingress traffic manager.";
                                    }

                                    leaf aggregate-forwarded-packets {
                                        type yang:counter64;
                                        description
                                            "The aggregate number of in and out-of profile
                                              packets forwarded by the ingress traffic manager.";
                                    }

                                    leaf aggregate-forwarded-octets {
                                        type yang:counter64;
                                        description
                                            "The aggregate number of in and out-of-profile
                                             octets forwarded by the ingress traffic manager.";
                                    }

                                    leaf aggregate-dropped-packets {
                                        type yang:counter64;
                                        description
                                            "The aggregate number of in and out-of profile
                                             packets, dropped by the traffic manager due to:
                                             MBS exceeded, buffer pool limit
                                             exceeded, etc.";
                                    }

                                    leaf aggregate-dropped-octets {
                                        type yang:counter64;
                                        description
                                            "The aggregate number of in and out-of profile
                                             octets, dropped by the traffic manager due to:
                                             MBS exceeded, buffer pool limit
                                             exceeded, etc.";
                                    }

                                    leaf last-cleared-time {
                                        type yang:date-and-time;
                                        description "Time when the counters in this table were last cleared.";
                                    }

                                } // container statistics

                            } // container traffic-manager

                            container qos-traffic {
                                description "Enter the qos-traffic context";

                                container statistics {
                                    description "Enter the statistics context";

                                    leaf ingress-packets {
                                        type yang:counter64;
                                        description "The number of ingress packets on this SAP.";
                                    }

                                    leaf ingress-octets {
                                        type yang:counter64;
                                        description "The number of ingress octets on this SAP.";
                                    }

                                } // container statistics

                            } // container qos-traffic

                            list queue {
                                key "queue-id";
                                description "Enter the queue list instance";

                                leaf queue-id {
                                    type types-qos:ingress-queue-id;
                                    description "The unique identifier for the queue.";
                                }

                                container statistics {
                                    description "Enter the statistics context";

                                    choice stat-mode {
                                        case unicast-priority {

                                            container unicast-priority {
                                                description "Enter the unicast-priority context";

                                                leaf high-priority-offered-packets {
                                                    type yang:counter64;
                                                    description "The number of high-priority packets offered by packet processor to traffic manager.";
                                                }

                                                leaf high-priority-offered-octets {
                                                    type yang:counter64;
                                                    description "The number of high-priority octets offered by packet processor to traffic manager.";
                                                }

                                                leaf low-priority-offered-packets {
                                                    type yang:counter64;
                                                    description "The number of low-priority packets offered by packet processor to traffic manager.";
                                                }

                                                leaf low-priority-offered-octets {
                                                    type yang:counter64;
                                                    description "The number of low-priority octets offered by packet processor to traffic manager.";
                                                }

                                                leaf high-priority-dropped-packets {
                                                    type yang:counter64;
                                                    description "The number of high-priority packets dropped by packet processor to traffic manager.";
                                                }

                                                leaf high-priority-dropped-octets {
                                                    type yang:counter64;
                                                    description "The number of high-priority octets dropped by packet processor to traffic manager.";
                                                }

                                                leaf low-priority-dropped-packets {
                                                    type yang:counter64;
                                                    description "The number of low-priority packets dropped by packet processor to traffic manager.";
                                                }

                                                leaf low-priority-dropped-octets {
                                                    type yang:counter64;
                                                    description "The number of low-priority octets dropped by packet processor to traffic manager.";
                                                }

                                                leaf in-profile-forwarded-packets {
                                                    type yang:counter64;
                                                    description "The number of in-profile packets (rate below CIR) forwarded.";
                                                }

                                                leaf in-profile-forwarded-octets {
                                                    type yang:counter64;
                                                    description "The number of in-profile octets (rate below CIR) forwarded.";
                                                }

                                                leaf out-profile-forwarded-packets {
                                                    type yang:counter64;
                                                    description "The number of out-of-profile packets (rate below CIR) forwarded.";
                                                }

                                                leaf out-profile-forwarded-octets {
                                                    type yang:counter64;
                                                    description "The number of out-of-profile octets (rate below CIR) forwarded.";
                                                }

                                            } // container unicast-priority

                                        }
                                        case unicast-profile {

                                            container unicast-profile {
                                                description "Enter the unicast-profile context";

                                                leaf color-in-offered-packets {
                                                    type yang:counter64;
                                                    description "The number of color-in packets offered to traffic manager.";
                                                }

                                                leaf color-in-offered-octets {
                                                    type yang:counter64;
                                                    description "The number of color-in octets offered to traffic manager.";
                                                }

                                                leaf color-out-offered-packets {
                                                    type yang:counter64;
                                                    description "The number of color-out packets offered to traffic manager.";
                                                }

                                                leaf color-out-offered-octets {
                                                    type yang:counter64;
                                                    description "The number of color-out octets offered to traffic manager.";
                                                }

                                                leaf color-offered-packets {
                                                    type yang:counter64;
                                                    description "The number of color packets offered to traffic manager.";
                                                }

                                                leaf color-offered-octets {
                                                    type yang:counter64;
                                                    description "The number of color octets offered to traffic manager.";
                                                }

                                                leaf uncolor-offered-packets {
                                                    type yang:counter64;
                                                    description "The number of uncolor packets offered to traffic manager.";
                                                }

                                                leaf uncolor-offered-octets {
                                                    type yang:counter64;
                                                    description "The number of uncolor octets offered to traffic manager.";
                                                }

                                                leaf color-out-dropped-packets {
                                                    type yang:counter64;
                                                    description "The number of color-out packets dropped.";
                                                }

                                                leaf color-out-dropped-octets {
                                                    type yang:counter64;
                                                    description "The number of color-out octets dropped.";
                                                }

                                                leaf color-in-uncolor-dropped-packets {
                                                    type yang:counter64;
                                                    description "The number of color-in/uncolor packets dropped.";
                                                }

                                                leaf color-in-uncolor-dropped-octets {
                                                    type yang:counter64;
                                                    description "The number of color-in/uncolor octets dropped.";
                                                }

                                                leaf in-profile-forwarded-packets {
                                                    type yang:counter64;
                                                    description "The number of in-profile packets (rate below CIR) forwarded.";
                                                }

                                                leaf in-profile-forwarded-octets {
                                                    type yang:counter64;
                                                    description "The number of in-profile octets (rate below CIR) forwarded.";
                                                }

                                                leaf out-profile-forwarded-packets {
                                                    type yang:counter64;
                                                    description "The number of out-of-profile packets (rate below CIR) forwarded.";
                                                }

                                                leaf out-profile-forwarded-octets {
                                                    type yang:counter64;
                                                    description "The number of out-of-profile octets (rate below CIR) forwarded.";
                                                }

                                            } // container unicast-profile

                                        }
                                        case multipoint-priority {

                                            container multipoint-priority {
                                                description "Enter the multipoint-priority context";

                                                leaf high-priority-offered-packets {
                                                    type yang:counter64;
                                                    description "The number of high-priority packets offered by packet processor to traffic manager.";
                                                }

                                                leaf high-priority-offered-octets {
                                                    type yang:counter64;
                                                    description "The number of high-priority octets offered by packet processor to traffic manager.";
                                                }

                                                leaf low-priority-offered-packets {
                                                    type yang:counter64;
                                                    description "The number of low-priority packets offered by packet processor to traffic manager.";
                                                }

                                                leaf low-priority-offered-octets {
                                                    type yang:counter64;
                                                    description "The number of low-priority octets offered by packet processor to traffic manager.";
                                                }

                                                leaf combined-offered-packets {
                                                    type yang:counter64;
                                                    description "The number of combined high and low priority packets offered by packet processor to traffic manager.";
                                                }

                                                leaf combined-offered-octets {
                                                    type yang:counter64;
                                                    description "The number of combined high and low priority octets offered by packet processor to traffic manager.";
                                                }

                                                leaf managed-offered-packets {
                                                    type yang:counter64;
                                                    description "The number of managed packets offered by packet processor to traffic manager.";
                                                }

                                                leaf managed-offered-octets {
                                                    type yang:counter64;
                                                    description "The number of managed octets offered by packet processor to traffic manager.";
                                                }

                                                leaf high-priority-dropped-packets {
                                                    type yang:counter64;
                                                    description "The number of high-priority packets dropped by packet processor to traffic manager.";
                                                }

                                                leaf high-priority-dropped-octets {
                                                    type yang:counter64;
                                                    description "The number of high-priority octets dropped by packet processor to traffic manager.";
                                                }

                                                leaf low-priority-dropped-packets {
                                                    type yang:counter64;
                                                    description "The number of low-priority packets dropped by packet processor to traffic manager.";
                                                }

                                                leaf low-priority-dropped-octets {
                                                    type yang:counter64;
                                                    description "The number of low-priority octets dropped by packet processor to traffic manager.";
                                                }

                                                leaf in-profile-forwarded-packets {
                                                    type yang:counter64;
                                                    description "The number of in-profile packets (rate below CIR) forwarded.";
                                                }

                                                leaf in-profile-forwarded-octets {
                                                    type yang:counter64;
                                                    description "The number of in-profile octets (rate below CIR) forwarded.";
                                                }

                                                leaf out-profile-forwarded-packets {
                                                    type yang:counter64;
                                                    description "The number of out-of-profile packets (rate below CIR) forwarded.";
                                                }

                                                leaf out-profile-forwarded-octets {
                                                    type yang:counter64;
                                                    description "The number of out-of-profile octets (rate below CIR) forwarded.";
                                                }

                                            } // container multipoint-priority

                                        }
                                        case multipoint-profile {

                                            container multipoint-profile {
                                                description "Enter the multipoint-profile context";

                                                leaf color-in-offered-packets {
                                                    type yang:counter64;
                                                    description "The number of color-in packets offered to traffic manager.";
                                                }

                                                leaf color-in-offered-octets {
                                                    type yang:counter64;
                                                    description "The number of color-in octets offered to traffic manager.";
                                                }

                                                leaf color-out-offered-packets {
                                                    type yang:counter64;
                                                    description "The number of color-out packets offered to traffic manager.";
                                                }

                                                leaf color-out-offered-octets {
                                                    type yang:counter64;
                                                    description "The number of color-out octets offered to traffic manager.";
                                                }

                                                leaf uncolor-offered-packets {
                                                    type yang:counter64;
                                                    description "The number of uncolor packets offered to traffic manager.";
                                                }

                                                leaf uncolor-offered-octets {
                                                    type yang:counter64;
                                                    description "The number of uncolor octets offered to traffic manager.";
                                                }

                                                leaf combined-offered-packets {
                                                    type yang:counter64;
                                                    description "The number of combined colored in, out and uncolored packets offered to traffic manager.";
                                                }

                                                leaf combined-offered-octets {
                                                    type yang:counter64;
                                                    description "The number of combined colored in, out and uncolored octets offered to traffic manager.";
                                                }

                                                leaf managed-offered-packets {
                                                    type yang:counter64;
                                                    description "The number of managed packets offered by packet processor to traffic manager.";
                                                }

                                                leaf managed-offered-octets {
                                                    type yang:counter64;
                                                    description "The number of managed octets offered by packet processor to traffic manager.";
                                                }

                                                leaf color-out-dropped-packets {
                                                    type yang:counter64;
                                                    description "The number of color-out packets dropped.";
                                                }

                                                leaf color-out-dropped-octets {
                                                    type yang:counter64;
                                                    description "The number of color-out octets dropped.";
                                                }

                                                leaf color-in-uncolor-dropped-packets {
                                                    type yang:counter64;
                                                    description "The number of color-in/uncolor packets dropped.";
                                                }

                                                leaf color-in-uncolor-dropped-octets {
                                                    type yang:counter64;
                                                    description "The number of color-in/uncolor octets dropped.";
                                                }

                                                leaf in-profile-forwarded-packets {
                                                    type yang:counter64;
                                                    description "The number of in-profile packets (rate below CIR) forwarded.";
                                                }

                                                leaf in-profile-forwarded-octets {
                                                    type yang:counter64;
                                                    description "The number of in-profile octets (rate below CIR) forwarded.";
                                                }

                                                leaf out-profile-forwarded-packets {
                                                    type yang:counter64;
                                                    description "The number of out-of-profile packets (rate below CIR) forwarded.";
                                                }

                                                leaf out-profile-forwarded-octets {
                                                    type yang:counter64;
                                                    description "The number of out-of-profile octets (rate below CIR) forwarded.";
                                                }

                                            } // container multipoint-profile

                                        }
                                        case v4-v6 {

                                            container v4-v6 {
                                                description "Enter the v4-v6 context";

                                                leaf ipv4-offered-packets {
                                                    type yang:counter64;
                                                    description "The number of ipv4 packets offered by packet processor to traffic manager.";
                                                }

                                                leaf ipv4-offered-octets {
                                                    type yang:counter64;
                                                    description "The number of ipv4 octets offered by packet processor to traffic manager.";
                                                }

                                                leaf ipv6-offered-packets {
                                                    type yang:counter64;
                                                    description "The number of ipv6 packets offered by packet processor to traffic manager.";
                                                }

                                                leaf ipv6-offered-octets {
                                                    type yang:counter64;
                                                    description "The number of ipv6 octets offered by packet processor to traffic manager.";
                                                }

                                                leaf ipv4-dropped-packets {
                                                    type yang:counter64;
                                                    description "The number of ipv4 packets dropped by packet processor to traffic manager.";
                                                }

                                                leaf ipv4-dropped-octets {
                                                    type yang:counter64;
                                                    description "The number of ipv4 octets dropped by packet processor to traffic manager.";
                                                }

                                                leaf ipv6-dropped-packets {
                                                    type yang:counter64;
                                                    description "The number of ipv6 packets dropped by packet processor to traffic manager.";
                                                }

                                                leaf ipv6-dropped-octets {
                                                    type yang:counter64;
                                                    description "The number of ipv6 octets dropped by packet processor to traffic manager.";
                                                }

                                                leaf ipv4-forwarded-packets {
                                                    type yang:counter64;
                                                    description "The number of ipv4 packets forwarded.";
                                                }

                                                leaf ipv4-forwarded-octets {
                                                    type yang:counter64;
                                                    description "The number of ipv4 octets forwarded.";
                                                }

                                                leaf ipv6-forwarded-packets {
                                                    type yang:counter64;
                                                    description "The number of ipv6 packets forwarded.";
                                                }

                                                leaf ipv6-forwarded-octets {
                                                    type yang:counter64;
                                                    description "The number of ipv6 octets forwarded.";
                                                }

                                            } // container v4-v6

                                        }
                                    }
                                } // container statistics

                                container queue-depth {
                                    description "Enter the queue-depth context";

                                    leaf elapsed-time {
                                        type types-sros:time-interval;
                                        description "Indicated the elapsed time.";
                                    }

                                    leaf depth-0-to-10-percent {
                                        type decimal64 {
                                            fraction-digits 2;
                                        }
                                        description "Indicated the depth 0 to 10 percent.";
                                    }

                                    leaf depth-11-to-20-percent {
                                        type decimal64 {
                                            fraction-digits 2;
                                        }
                                        description "Indicated the depth 0 to 20 percent.";
                                    }

                                    leaf depth-21-to-30-percent {
                                        type decimal64 {
                                            fraction-digits 2;
                                        }
                                        description "Indicated the depth 0 to 30 percent.";
                                    }

                                    leaf depth-31-to-40-percent {
                                        type decimal64 {
                                            fraction-digits 2;
                                        }
                                        description "Indicated the depth 0 to 40 percent.";
                                    }

                                    leaf depth-41-to-50-percent {
                                        type decimal64 {
                                            fraction-digits 2;
                                        }
                                        description "Indicated the depth 0 to 50 percent.";
                                    }

                                    leaf depth-51-to-60-percent {
                                        type decimal64 {
                                            fraction-digits 2;
                                        }
                                        description "Indicated the depth 0 to 60 percent.";
                                    }

                                    leaf depth-61-to-70-percent {
                                        type decimal64 {
                                            fraction-digits 2;
                                        }
                                        description "Indicated the depth 0 to 70 percent.";
                                    }

                                    leaf depth-71-to-80-percent {
                                        type decimal64 {
                                            fraction-digits 2;
                                        }
                                        description "Indicated the depth 0 to 80 percent.";
                                    }

                                    leaf depth-81-to-90-percent {
                                        type decimal64 {
                                            fraction-digits 2;
                                        }
                                        description "Indicated the depth 0 to 90 percent.";
                                    }

                                    leaf depth-91-to-100-percent {
                                        type decimal64 {
                                            fraction-digits 2;
                                        }
                                        description "Indicated the depth 0 to 100 percent.";
                                    }

                                    leaf queue-polling-interval {
                                        type types-sros:time-interval;
                                        description "Indicates the queue polling interval.";
                                    }

                                } // container queue-depth

                                list hardware-queue {
                                    key "source-card source-fp source-tap-offset source-port dest-card dest-fp dest-tap-offset";
                                    description "Enter the hardware-queue list instance";

                                    leaf source-card {
                                        type int32;
                                        description "Card number";
                                    }

                                    leaf source-fp {
                                        type int32;
                                        description "FP number";
                                    }

                                    leaf source-tap-offset {
                                        type int32;
                                        description "Source TAP.";
                                    }

                                    leaf source-port {
                                        type types-sros:port;
                                        description "Port identifier";
                                    }

                                    leaf dest-card {
                                        type int32;
                                        description "Card number";
                                    }

                                    leaf dest-fp {
                                        type int32;
                                        description "FP number";
                                    }

                                    leaf dest-tap-offset {
                                        type int32;
                                        description "Destination TAP.";
                                    }

                                    leaf adapted-admin-mbs {
                                        type int64;
                                        units "bytes";
                                        description "Admin MBS.";
                                    }

                                    leaf adapted-admin-cbs {
                                        type types-qos:bytes;
                                        units "bytes";
                                        description "Admin CBS.";
                                    }

                                    leaf operational-mbs {
                                        type int64;
                                        units "bytes";
                                        description "Oper MBS.";
                                    }

                                    leaf depth {
                                        type union {
                                            type enumeration {
                                                enum max                            { value -1; }
                                            }
                                            type int64;
                                        }
                                        description "Depth CIR.";
                                    }

                                    leaf operational-cir {
                                        type union {
                                            type enumeration {
                                                enum max                            { value -1; }
                                            }
                                            type int64;
                                        }
                                        description "Oper CIR.";
                                    }

                                    leaf operational-fir {
                                        type union {
                                            type enumeration {
                                                enum max                            { value -1; }
                                            }
                                            type int64;
                                        }
                                        description "Oper FIR.";
                                    }

                                    leaf operational-pir {
                                        type union {
                                            type enumeration {
                                                enum max                            { value -1; }
                                            }
                                            type int64;
                                        }
                                        description "Oper PIR.";
                                    }

                                    leaf exceed-droptail {
                                        type union {
                                            type int64 {
                                                range "0..max";
                                            }
                                            type enumeration {
                                                enum auto                           { value -1; }
                                            }
                                        }
                                        description "Exceed droptail.";
                                    }

                                    leaf high-droptail {
                                        type union {
                                            type int64 {
                                                range "0..max";
                                            }
                                            type enumeration {
                                                enum auto                           { value -1; }
                                            }
                                        }
                                        description "High droptail.";
                                    }

                                    leaf high-plus-droptail {
                                        type union {
                                            type int64 {
                                                range "0..max";
                                            }
                                            type enumeration {
                                                enum auto                           { value -1; }
                                            }
                                        }
                                        description "Highplus droptail.";
                                    }

                                    leaf low-droptail {
                                        type union {
                                            type int64 {
                                                range "0..max";
                                            }
                                            type enumeration {
                                                enum auto                           { value -1; }
                                            }
                                        }
                                        description "Low droptail.";
                                    }

                                    leaf operational-exceed-burst {
                                        type types-qos:int64-max;
                                        description "Oper burst exceed.";
                                    }

                                    leaf operational-max-transmit-data-size {
                                        type types-qos:int64-max;
                                        description "Oper max transmit data size.";
                                    }

                                    leaf operational-burst-fir {
                                        type types-qos:int64-max;
                                        description "Oper burst FIR.";
                                    }

                                    leaf local-parent-rate {
                                        type types-qos:kbps;
                                        description "The local limit rate for the delay budget";
                                    }

                                } // list hardware-queue

                            } // list queue

                            list policer {
                                key "policer-id";
                                description "Enter the policer list instance";

                                leaf policer-id {
                                    type types-qos:ingress-policer-id;
                                    description "The unique identifier for the policer.";
                                }

                                container statistics {
                                    description "Enter the statistics context";

                                    choice stat-mode {
                                        case minimal {

                                            container minimal {
                                                description "Enter the minimal context";

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf all-dropped-packets {
                                                    type yang:counter64;
                                                    description "The number of all the priority packets dropped by the packet processor to traffic manager";
                                                }

                                                leaf all-dropped-octets {
                                                    type yang:counter64;
                                                    description "The number of all the priority octets dropped by the packet processor to traffic manager";
                                                }

                                                leaf all-forwarded-packets {
                                                    type yang:counter64;
                                                    description "The number of all the priority packets forwarded by the packet processor to traffic manager";
                                                }

                                                leaf all-forwarded-octets {
                                                    type yang:counter64;
                                                    description "The number of all the priority octets forwarded by the packet processor to traffic manager";
                                                }

                                            } // container minimal

                                        }
                                        case offered-profile-no-cir {

                                            container offered-profile-no-cir {
                                                description "Enter the offered-profile-no-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-no-cir

                                        }
                                        case offered-priority-no-cir {

                                            container offered-priority-no-cir {
                                                description "Enter the offered-priority-no-cir context";

                                                leaf high-priority-offered-packets {
                                                    type yang:counter64;
                                                    description "The number of high-priority packets offered by the packet processor to traffic manager";
                                                }

                                                leaf high-priority-offered-octets {
                                                    type yang:counter64;
                                                    description "The number of high-priority octets offered by the packet processor to traffic manager";
                                                }

                                                leaf low-priority-offered-packets {
                                                    type yang:counter64;
                                                    description "The number of low-priority packets offered by the packet processor to traffic manager";
                                                }

                                                leaf low-priority-offered-octets {
                                                    type yang:counter64;
                                                    description "The number of low-priority octets offered by the packet processor to traffic manager";
                                                }

                                                leaf high-priority-dropped-packets {
                                                    type yang:counter64;
                                                    description "The number of high-priority packets dropped by the packet processor to traffic manager";
                                                }

                                                leaf high-priority-dropped-octets {
                                                    type yang:counter64;
                                                    description "The number of high-priority octets dropped by the packet processor to traffic manager";
                                                }

                                                leaf low-priority-dropped-packets {
                                                    type yang:counter64;
                                                    description "The number of low-priority packets dropped by the packet processor to traffic manager";
                                                }

                                                leaf low-priority-dropped-octets {
                                                    type yang:counter64;
                                                    description "The number of low-priority octets dropped by the packet processor to traffic manager";
                                                }

                                                leaf high-priority-forwarded-packets {
                                                    type yang:counter64;
                                                    description "The number of high-priority packets forwarded by the packet processor to traffic manager";
                                                }

                                                leaf high-priority-forwarded-octets {
                                                    type yang:counter64;
                                                    description "The number of high-priority octets forwarded by the packet processor to traffic manager";
                                                }

                                                leaf low-priority-forwarded-packets {
                                                    type yang:counter64;
                                                    description "The number of low-priority packets forwarded by the packet processor to traffic manager";
                                                }

                                                leaf low-priority-forwarded-octets {
                                                    type yang:counter64;
                                                    description "The number of low-priority octets forwarded by the packet processor to traffic manager";
                                                }

                                            } // container offered-priority-no-cir

                                        }
                                        case offered-profile-cir {

                                            container offered-profile-cir {
                                                description "Enter the offered-profile-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf uncolor-offered-packets {
                                                    type yang:counter64;
                                                    description "The number of uncolor packets offered by the packet processor to traffic manager";
                                                }

                                                leaf uncolor-offered-octets {
                                                    type yang:counter64;
                                                    description "The number of uncolor octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-cir

                                        }
                                        case offered-priority-cir {

                                            container offered-priority-cir {
                                                description "Enter the offered-priority-cir context";

                                                leaf high-priority-offered-packets {
                                                    type yang:counter64;
                                                    description "The number of high-priority packets offered by the packet processor to traffic manager";
                                                }

                                                leaf high-priority-offered-octets {
                                                    type yang:counter64;
                                                    description "The number of high-priority octets offered by the packet processor to traffic manager";
                                                }

                                                leaf low-priority-offered-packets {
                                                    type yang:counter64;
                                                    description "The number of low-priority packets offered by the packet processor to traffic manager";
                                                }

                                                leaf low-priority-offered-octets {
                                                    type yang:counter64;
                                                    description "The number of low-priority octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-priority-cir

                                        }
                                        case offered-total-cir {

                                            container offered-total-cir {
                                                description "Enter the offered-total-cir context";

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-total-cir

                                        }
                                        case offered-limited-profile-cir {

                                            container offered-limited-profile-cir {
                                                description "Enter the offered-limited-profile-cir context";

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf uncolor-offered-packets {
                                                    type yang:counter64;
                                                    description "The number of uncolor packets offered by the packet processor to traffic manager";
                                                }

                                                leaf uncolor-offered-octets {
                                                    type yang:counter64;
                                                    description "The number of uncolor octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-limited-profile-cir

                                        }
                                        case offered-profile-capped-cir {

                                            container offered-profile-capped-cir {
                                                description "Enter the offered-profile-capped-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf uncolor-offered-packets {
                                                    type yang:counter64;
                                                    description "The number of uncolor packets offered by the packet processor to traffic manager";
                                                }

                                                leaf uncolor-offered-octets {
                                                    type yang:counter64;
                                                    description "The number of uncolor octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-capped-cir

                                        }
                                        case offered-profile-with-discards {

                                            container offered-profile-with-discards {
                                                description "Enter the offered-profile-with-discards context";

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-profile packets forwarded by the packet processor to traffic manager";
                                                }

                                                leaf out-profile-forwarded-octets {
                                                    type yang:counter64;
                                                    description "The number of out-profile octets forwarded by the packet processor to traffic manager";
                                                }

                                                leaf dropped-exceed-profile-packets {
                                                    type yang:counter64;
                                                    description "The number of dropped-exceed-profile packets by the packet processor to traffic manager";
                                                }

                                                leaf dropped-exceed-profile-octets {
                                                    type yang:counter64;
                                                    description "The number of dropped-exceed-profile octets by the packet processor to traffic manager";
                                                }

                                            } // container offered-profile-with-discards

                                        }
                                        case offered-limited-capped-cir {

                                            container offered-limited-capped-cir {
                                                description "Enter the offered-limited-capped-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                                leaf uncolor-offered-packets {
                                                    type yang:counter64;
                                                    description "The number of out-of-rofile packets offered by the packet processor to traffic manager";
                                                }

                                                leaf uncolor-offered-octets {
                                                    type yang:counter64;
                                                    description "The number of out-of-profile octets offered by the packet processor to traffic manager";
                                                }

                                            } // container offered-limited-capped-cir

                                        }
                                        case v4-v6 {

                                            container v4-v6 {
                                                description "Enter the v4-v6 context";

                                                leaf ipv4-offered-packets {
                                                    type yang:counter64;
                                                    description "The number of ipv4 packets offered by the packet processor to traffic manager";
                                                }

                                                leaf ipv4-offered-octets {
                                                    type yang:counter64;
                                                    description "The number of ipv4 octets offered by the packet processor to traffic manager";
                                                }

                                                leaf ipv6-offered-packets {
                                                    type yang:counter64;
                                                    description "The number of ipv6 packets offered by the packet processor to traffic manager";
                                                }

                                                leaf ipv6-offered-octets {
                                                    type yang:counter64;
                                                    description "The number of ipv6 octets offered by the packet processor to traffic manager";
                                                }

                                                leaf ipv4-dropped-packets {
                                                    type yang:counter64;
                                                    description "The number of ipv4 packets dropped by the packet processor to traffic manager";
                                                }

                                                leaf ipv4-dropped-octets {
                                                    type yang:counter64;
                                                    description "The number of ipv4 octets dropped by the packet processor to traffic manager";
                                                }

                                                leaf ipv6-dropped-packets {
                                                    type yang:counter64;
                                                    description "The number of ipv6 packets dropped by the packet processor to traffic manager";
                                                }

                                                leaf ipv6-dropped-octets {
                                                    type yang:counter64;
                                                    description "The number of ipv6 octets dropped by the packet processor to traffic manager";
                                                }

                                                leaf ipv4-forwarded-packets {
                                                    type yang:counter64;
                                                    description "The number of ipv4 packets forwarded by the packet processor to traffic manager";
                                                }

                                                leaf ipv4-forwarded-octets {
                                                    type yang:counter64;
                                                    description "The number of ipv4 octets forwarded by the packet processor to traffic manager";
                                                }

                                                leaf ipv6-forwarded-packets {
                                                    type yang:counter64;
                                                    description "The number of ipv6 packets forwarded by the packet processor to traffic manager";
                                                }

                                                leaf ipv6-forwarded-octets {
                                                    type yang:counter64;
                                                    description "The number of ipv6 octets forwarded by the packet processor to traffic manager";
                                                }

                                            } // container v4-v6

                                        }
                                    }
                                } // container statistics

                                list hardware-policer {
                                    key "source-card source-fp source-port";
                                    description "Enter the hardware-policer list instance";

                                    leaf source-card {
                                        type int32;
                                        description "Card number";
                                    }

                                    leaf source-fp {
                                        type int32;
                                        description "FP number";
                                    }

                                    leaf source-port {
                                        type types-sros:port;
                                        description "Port identifier";
                                    }

                                    leaf adapted-admin-cbs {
                                        type int64;
                                        units "bytes";
                                        description "Admin CBS.";
                                    }

                                    leaf adapted-admin-mbs {
                                        type int64;
                                        units "bytes";
                                        description "Admin MBS.";
                                    }

                                    leaf adapted-hp-only {
                                        type int64;
                                        units "bytes";
                                        description "Hi Prio Only.";
                                    }

                                    leaf depth {
                                        type int64;
                                        units "bytes";
                                        description "Depth.";
                                    }

                                    leaf operational-cir {
                                        type types-qos:int64-max;
                                        description "Oper CIR.";
                                    }

                                    leaf operational-fir {
                                        type types-qos:int64-max;
                                        description "Oper FIR.";
                                    }

                                    leaf operational-pir {
                                        type types-qos:int64-max;
                                        description "Oper PIR.";
                                    }

                                } // list hardware-policer

                                list hw-policer {
                                    key "card fp core";
                                    description "Enter the hw-policer list instance";

                                    leaf card {
                                        type int32;
                                        description "Card number";
                                    }

                                    leaf fp {
                                        type int32;
                                        description "FP number";
                                    }

                                    leaf core {
                                        type int32;
                                        description "core number";
                                    }

                                    leaf operational-mbs {
                                        type int64;
                                        units "bytes";
                                        description "Oper MBS.";
                                    }

                                    leaf operational-eir {
                                        type types-qos:int64-max;
                                        description "Oper EIR.";
                                    }

                                    leaf operational-cir {
                                        type types-qos:int64-max;
                                        description "Oper CIR.";
                                    }

                                    leaf operational-cbs {
                                        type int64;
                                        units "bytes";
                                        description "Oper CBS.";
                                    }

                                    leaf depth {
                                        type int64;
                                        units "bytes";
                                        description "Depth.";
                                    }

                                } // list hw-policer

                            } // list policer

                        } // container sap-ingress

                        container policer-control-policy {
                            description "Enter the policer-control-policy context";

                            list arbiter {
                                key "arbiter-name";
                                description "Enter the arbiter list instance";

                                leaf arbiter-name {
                                    type types-sros:named-item;
                                    description "Specifies the arbiter name.";
                                }

                                container statistics {
                                    description "Enter the statistics context";

                                    leaf forwarded-packets {
                                        type yang:counter64;
                                        description "The number of forwarded packets.";
                                    }

                                    leaf forwarded-octets {
                                        type yang:counter64;
                                        description "The number of forwarded octets.";
                                    }

                                    list lag-member-port {
                                        key "port";
                                        description "Enter the lag-member-port list instance";

                                        leaf port {
                                            type types-sros:port;
                                            description "Port identifier";
                                        }

                                        leaf forwarded-packets {
                                            type yang:counter64;
                                            description "The number of forwarded packets.";
                                        }

                                        leaf forwarded-octets {
                                            type yang:counter64;
                                            description "The number of forwarded octets.";
                                        }

                                    } // list lag-member-port

                                } // container statistics

                            } // list arbiter

                        } // container policer-control-policy

                        container scheduler-policy {
                            description "Enter the scheduler-policy context";

                            list scheduler {
                                key "scheduler-name";
                                description "Enter the scheduler list instance";

                                leaf scheduler-name {
                                    type types-sros:named-item;
                                    description "Specifies the scheduler name.";
                                }

                                container statistics {
                                    description "Enter the statistics context";

                                    leaf forwarded-packets {
                                        type yang:counter64;
                                        description "The number of forwarded packets.";
                                    }

                                    leaf forwarded-octets {
                                        type yang:counter64;
                                        description "The number of forwarded octets.";
                                    }

                                    list lag-member-port {
                                        key "port";
                                        description "Enter the lag-member-port list instance";

                                        leaf port {
                                            type types-sros:port;
                                            description "Port identifier";
                                        }

                                        leaf forwarded-packets {
                                            type yang:counter64;
                                            description "The number of forwarded packets.";
                                        }

                                        leaf forwarded-octets {
                                            type yang:counter64;
                                            description "The number of forwarded octets.";
                                        }

                                    } // list lag-member-port

                                } // container statistics

                            } // list scheduler

                        } // container scheduler-policy

                    } // container qos

                    container aggregate-policer {
                        description "Enter the aggregate-policer context";

                        container statistics {
                            description "Enter the statistics context";

                            container offered-profile-with-discards {
                                description "Enter the offered-profile-with-discards context";

                                leaf in-profile-forwarded-packets {
                                    type yang:counter64;
                                    description "The number of in-profile packets forwarded by the packet processor to traffic manager";
                                }

                                leaf in-profile-forwarded-octets {
                                    type yang:counter64;
                                    description "The number of in-profile octets forwarded by the packet processor to traffic manager";
                                }

                                leaf out-profile-forwarded-packets {
                                    type yang:counter64;
                                    description "The number of out-profile packets forwarded by the packet processor to traffic manager";
                                }

                                leaf out-profile-forwarded-octets {
                                    type yang:counter64;
                                    description "The number of out-profile octets forwarded by the packet processor to traffic manager";
                                }

                                leaf dropped-exceed-profile-packets {
                                    type yang:counter64;
                                    description "The number of dropped-exceed-profile packets by the packet processor to traffic manager";
                                }

                                leaf dropped-exceed-profile-octets {
                                    type yang:counter64;
                                    description "The number of dropped-exceed-profile octets by the packet processor to traffic manager";
                                }

                            } // container offered-profile-with-discards

                        } // container statistics

                        list hw-policer {
                            key "card fp core";
                            description "Enter the hw-policer list instance";

                            leaf card {
                                type int32;
                                description "Card number";
                            }

                            leaf fp {
                                type int32;
                                description "FP number";
                            }

                            leaf core {
                                type int32;
                                description "core number";
                            }

                            leaf operational-mbs {
                                type int64;
                                units "bytes";
                                description "Oper MBS.";
                            }

                            leaf operational-eir {
                                type types-qos:int64-max;
                                description "Oper EIR.";
                            }

                            leaf operational-cir {
                                type types-qos:int64-max;
                                description "Oper CIR.";
                            }

                            leaf operational-cbs {
                                type int64;
                                units "bytes";
                                description "Oper CBS.";
                            }

                            leaf depth {
                                type int64;
                                units "bytes";
                                description "Depth.";
                            }

                        } // list hw-policer

                    } // container aggregate-policer

                } // container ingress

                container egress {
                    description "Enter the egress context";

                    container vlan-qos {
                        description "Enter the vlan-qos context";

                        list queue {
                            key "queue-id";
                            description "Enter the queue list instance";

                            leaf queue-id {
                                type types-qos:egress-queue-id;
                                description "The unique identifier for the queue.";
                            }

                            container statistics {
                                description "Enter the statistics context";

                                choice stat-mode {
                                    case enqueued-with-discards {

                                        container enqueued-with-discards {
                                            description "Enter the enqueued-with-discards context";

                                            leaf forwarded-packets {
                                                type yang:counter64;
                                                description "The number of packets (rate below CIR) forwarded.";
                                            }

                                            leaf forwarded-octets {
                                                type yang:counter64;
                                                description "The number of octets (rate below CIR) forwarded.";
                                            }

                                            leaf dropped-packets {
                                                type yang:counter64;
                                                description "The number of packets discarded.";
                                            }

                                            leaf dropped-octets {
                                                type yang:counter64;
                                                description "The number of octets discarded.";
                                            }

                                        } // container enqueued-with-discards

                                    }
                                    case enqueued-4-profile-with-discards {

                                        container enqueued-4-profile-with-discards {
                                            description "Enter the enqueued-4-profile-with-discards context";

                                            leaf inplus-profile-forwarded-packets {
                                                type yang:counter64;
                                                description
                                                    "The number of in-plus-profile packets
                                                     (rate below CIR) forwarded.";
                                            }

                                            leaf inplus-profile-forwarded-octets {
                                                type yang:counter64;
                                                description
                                                    "The number of in-plus-profile octets
                                                     (rate below CIR) forwarded.";
                                            }

                                            leaf inplus-profile-dropped-packets {
                                                type yang:counter64;
                                                description
                                                    "The number of in-plus-profile packets
                                                     discarded.";
                                            }

                                            leaf inplus-profile-dropped-octets {
                                                type yang:counter64;
                                                description
                                                    "The number of in-plus-profile octets
                                                     discarded.";
                                            }

                                            leaf in-profile-forwarded-packets {
                                                type yang:counter64;
                                                description
                                                    "The number of in-profile packets
                                                     (rate below CIR) forwarded.";
                                            }

                                            leaf in-profile-forwarded-octets {
                                                type yang:counter64;
                                                description
                                                    "The number of in-profile octets
                                                     (rate below CIR) forwarded.";
                                            }

                                            leaf in-profile-dropped-packets {
                                                type yang:counter64;
                                                description
                                                    "The number of in-profile packets
                                                     discarded.";
                                            }

                                            leaf in-profile-dropped-octets {
                                                type yang:counter64;
                                                description
                                                    "The number of in-profile octets
                                                     discarded.";
                                            }

                                            leaf out-profile-forwarded-packets {
                                                type yang:counter64;
                                                description
                                                    "The number of out-profile packets
                                                     (rate below CIR) forwarded.";
                                            }

                                            leaf out-profile-forwarded-octets {
                                                type yang:counter64;
                                                description
                                                    "The number of out-profile octets
                                                     (rate below CIR) forwarded.";
                                            }

                                            leaf out-profile-dropped-packets {
                                                type yang:counter64;
                                                description
                                                    "The number of out-profile packets
                                                     discarded.";
                                            }

                                            leaf out-profile-dropped-octets {
                                                type yang:counter64;
                                                description
                                                    "The number of out-profile octets
                                                     discarded.";
                                            }

                                            leaf exceed-profile-forwarded-packets {
                                                type yang:counter64;
                                                description
                                                    "The number of exceed-profile packets
                                                     (rate above CIR) forwarded.";
                                            }

                                            leaf exceed-profile-forwarded-octets {
                                                type yang:counter64;
                                                description
                                                    "The number of exceed-profile octets
                                                     (rate above CIR) forwarded.";
                                            }

                                            leaf exceed-profile-dropped-packets {
                                                type yang:counter64;
                                                description
                                                    "The number of exceed-profile packets
                                                     discarded.";
                                            }

                                            leaf exceed-profile-dropped-octets {
                                                type yang:counter64;
                                                description
                                                    "The number of exceed-profile octets
                                                     discarded.";
                                            }

                                        } // container enqueued-4-profile-with-discards

                                    }
                                }
                            } // container statistics

                            container state {
                                description "Enter the state context";

                                leaf admin-pir {
                                    type uint32;
                                    units "kilobps";
                                    description "Specifies the administrative PIR.";
                                }

                                leaf oper-pir {
                                    type uint32;
                                    units "kilobps";
                                    description "Specifies the administrative PIR.";
                                }

                                leaf admin-cir {
                                    type uint32;
                                    units "kilobps";
                                    description "Specifies the administrative CIR.";
                                }

                                leaf oper-cir {
                                    type uint32;
                                    units "kilobps";
                                    description "Specifies the administrative CIR.";
                                }

                                leaf admin-pir-weight {
                                    type uint32;
                                    description "Specifies the administrative pir weight.";
                                }

                                leaf oper-pir-weight {
                                    type uint32;
                                    description "Specifies the operational pir weight.";
                                }

                                leaf admin-mbs {
                                    type uint32;
                                    description "Specifies the administrative mbs.";
                                }

                                leaf oper-mbs {
                                    type uint32;
                                    description "Specifies the operational mbs.";
                                }

                                list slot {
                                    key "slot-num";
                                    description "Enter the slot list instance";

                                    leaf slot-num {
                                        type uint32;
                                        description "Slot number.";
                                    }

                                    list unit {
                                        key "unit-num";
                                        description "Enter the unit list instance";

                                        leaf unit-num {
                                            type uint32;
                                            description "Unit number.";
                                        }

                                        list core {
                                            key "core-num";
                                            description "Enter the core list instance";

                                            leaf core-num {
                                                type uint32;
                                                description "Core number.";
                                            }

                                            leaf depth-bytes {
                                                type uint32;
                                                description "Specifies the depth bytes.";
                                            }

                                            leaf depth-buffers {
                                                type uint32;
                                                description "Specifies the depth buffers.";
                                            }

                                        } // list core

                                    } // list unit

                                } // list slot

                            } // container state

                        } // list queue

                    } // container vlan-qos

                    container qos {
                        description "Enter the qos context";

                        container sap-egress {
                            description "Enter the sap-egress context";

                            container traffic-manager {
                                description "Enter the traffic-manager context";

                                container statistics {
                                    description "Enter the statistics context";

                                    leaf in-inplus-profile-dropped-packets {
                                        type yang:counter64;
                                        description
                                            "The number of in-profile packets
                                             discarded by the egress traffic manager due
                                             to: MBS exceeded, buffer pool limit
                                             exceeded, etc.";
                                    }

                                    leaf in-inplus-profile-dropped-octets {
                                        type yang:counter64;
                                        description
                                            "The number of in-profile octets
                                             discarded by the egress traffic manager due
                                             to: MBS exceeded, buffer pool limit
                                             exceeded, etc.";
                                    }

                                    leaf out-exceed-profile-dropped-packets {
                                        type yang:counter64;
                                        description
                                            "The number of out-of-profile packets
                                             discarded by the egress traffic manager due
                                             to: MBS exceeded, buffer pool limit
                                             exceeded, etc.";
                                    }

                                    leaf out-exceed-profile-dropped-octets {
                                        type yang:counter64;
                                        description
                                            "The number of out-of-profile packets
                                             discarded by the egress traffic manager due
                                             to: MBS exceeded, buffer pool limit
                                             exceeded, etc.";
                                    }

                                    leaf in-inplus-profile-forwarded-packets {
                                        type yang:counter64;
                                        description
                                            "The number of in-profile packets
                                             (rate below CIR) forwarded by the
                                             egress traffic manager.";
                                    }

                                    leaf in-inplus-profile-forwarded-octets {
                                        type yang:counter64;
                                        description
                                            "The number of in-profile octets
                                             (rate below CIR) forwarded by the
                                             egress traffic manager.";
                                    }

                                    leaf out-exceed-profile-forwarded-packets {
                                        type yang:counter64;
                                        description
                                            "The number of out-of-profile packets
                                             (rate above CIR) forwarded by the
                                             egress traffic manager.";
                                    }

                                    leaf out-exceed-profile-forwarded-octets {
                                        type yang:counter64;
                                        description
                                            "The number of out-of-profile octets
                                             (rate above CIR) forwarded by the
                                             egress traffic manager.";
                                    }

                                    leaf aggregate-forwarded-packets {
                                        type yang:counter64;
                                        description
                                            "The aggregate number of in and out-of profile
                                             packets forwarded by the egress traffic manager.";
                                    }

                                    leaf aggregate-forwarded-octets {
                                        type yang:counter64;
                                        description
                                            "The aggregate number of in and out-of profile
                                             octets forwarded by the egress traffic manager.";
                                    }

                                    leaf aggregate-dropped-packets {
                                        type yang:counter64;
                                        description
                                            "The aggregate number of in and out-of profile
                                             packets discarded by the egress traffic manager due
                                             to: MBS exceeded, buffer pool limit
                                             exceeded, etc.";
                                    }

                                    leaf aggregate-dropped-octets {
                                        type yang:counter64;
                                        description
                                            "The aggregate number of in and out-of profile
                                             octets discarded by the egress traffic manager due
                                             to: MBS exceeded, buffer pool limit
                                             exceeded, etc.";
                                    }

                                    leaf last-cleared-time {
                                        type yang:date-and-time;
                                        description "Time when the counters in this table were last cleared.";
                                    }

                                } // container statistics

                            } // container traffic-manager

                            container qos-traffic {
                                description "Enter the qos-traffic context";

                                container statistics {
                                    description "Enter the statistics context";

                                    leaf egress-packets {
                                        type yang:counter64;
                                        description "The number of egress packets on this SAP.";
                                    }

                                    leaf egress-octets {
                                        type yang:counter64;
                                        description "The number of egress octets on this SAP.";
                                    }

                                } // container statistics

                            } // container qos-traffic

                            container aggregate-shapers {
                                description "Enter the aggregate-shapers context";

                                list aggregate-shaper-port {
                                    key "port-id";
                                    description "Enter the aggregate-shaper-port list instance";

                                    leaf port-id {
                                        type types-sros:port;
                                        description "The identifier which uniquely identifies the port.";
                                    }

                                    leaf burst-limit {
                                        type int32;
                                        units "bytes";
                                        description "Operational burst";
                                    }

                                    leaf depth {
                                        type uint32;
                                        units "bytes";
                                        description "Leaky-bucket depth of the aggregate shaper PIR";
                                    }

                                    leaf packet-mode {
                                        type types-qos:packet-mode;
                                        description "Packet-mode";
                                    }

                                    leaf out-of-date {
                                        type boolean;
                                        description
                                            "Info is out-of-date with respect to the latest config; the
                                             shaper-algorithm still needs to re-calculate the implemented
                                             rate.";
                                    }

                                    leaf queue-set-size {
                                        type int32;
                                        description "Queue set size";
                                    }

                                    leaf queue-set-size-overridden {
                                        type boolean;
                                        description
                                            "Info queue-set-size-overridden is set to true when the shaper is created by
                                             the override configured for sap egress qos policy. When it is set to false,
                                             it indicates that fp-resource-policy default-size setting is used to create 
                                             this shaper.";
                                    }

                                    container rate {
                                        description "Enter the rate context";

                                        leaf assigned {
                                            type uint32;
                                            units "kilobps";
                                            description "Rate assigned by a hw-agg-shaper-scheduler";
                                        }

                                        leaf implemented {
                                            type uint32;
                                            units "kilobps";
                                            description
                                                "Implemented rate (based on hardware restrictions and based
                                                 on avg-frame-overhead and ATM adjustments)";
                                        }

                                        leaf consumed {
                                            type uint32;
                                            units "kilobps";
                                            description
                                                "Sum of the rates of the queues feeding into the aggregate
                                                 shaper";
                                        }

                                    } // container rate

                                    container avg-frame-overhead {
                                        description "Enter the avg-frame-overhead context";

                                        leaf overhead {
                                            type decimal64 {
                                                fraction-digits 2;
                                            }
                                            units "percent";
                                            description "Percentage average frame overhead";
                                        }

                                        leaf real-time {
                                            type boolean;
                                            description "Is it real-time?";
                                        }

                                    } // container avg-frame-overhead

                                    container hw-agg-shaper-scheduler {
                                        description "Enter the hw-agg-shaper-scheduler context";

                                        leaf active {
                                            type boolean;
                                            description
                                                "The aggregate shaper is controlled by a
                                                 hw-agg-shaper-scheduler";
                                        }

                                        leaf running {
                                            type boolean;
                                            description
                                                "The hw-agg-shaper-scheduler is currently running and
                                                 updating the aggregate shaper rates";
                                        }

                                        leaf invalid-class-usage {
                                            type boolean;
                                            description
                                                "The aggregate shaper has queues in multiple classes in the
                                                 same group in the hw-agg-shaper-scheduler";
                                        }

                                    } // container hw-agg-shaper-scheduler

                                } // list aggregate-shaper-port

                            } // container aggregate-shapers

                            list queue {
                                key "queue-id";
                                description "Enter the queue list instance";

                                leaf queue-id {
                                    type types-qos:egress-queue-id;
                                    description "The unique identifier for the queue.";
                                }

                                container queue-depth {
                                    description "Enter the queue-depth context";

                                    leaf elapsed-time {
                                        type types-sros:time-interval;
                                        description "Indicated the elapsed time.";
                                    }

                                    leaf depth-0-to-10-percent {
                                        type decimal64 {
                                            fraction-digits 2;
                                        }
                                        description "Indicated the depth 0 to 10 percent.";
                                    }

                                    leaf depth-11-to-20-percent {
                                        type decimal64 {
                                            fraction-digits 2;
                                        }
                                        description "Indicated the depth 0 to 20 percent.";
                                    }

                                    leaf depth-21-to-30-percent {
                                        type decimal64 {
                                            fraction-digits 2;
                                        }
                                        description "Indicated the depth 0 to 30 percent.";
                                    }

                                    leaf depth-31-to-40-percent {
                                        type decimal64 {
                                            fraction-digits 2;
                                        }
                                        description "Indicated the depth 0 to 40 percent.";
                                    }

                                    leaf depth-41-to-50-percent {
                                        type decimal64 {
                                            fraction-digits 2;
                                        }
                                        description "Indicated the depth 0 to 50 percent.";
                                    }

                                    leaf depth-51-to-60-percent {
                                        type decimal64 {
                                            fraction-digits 2;
                                        }
                                        description "Indicated the depth 0 to 60 percent.";
                                    }

                                    leaf depth-61-to-70-percent {
                                        type decimal64 {
                                            fraction-digits 2;
                                        }
                                        description "Indicated the depth 0 to 70 percent.";
                                    }

                                    leaf depth-71-to-80-percent {
                                        type decimal64 {
                                            fraction-digits 2;
                                        }
                                        description "Indicated the depth 0 to 80 percent.";
                                    }

                                    leaf depth-81-to-90-percent {
                                        type decimal64 {
                                            fraction-digits 2;
                                        }
                                        description "Indicated the depth 0 to 90 percent.";
                                    }

                                    leaf depth-91-to-100-percent {
                                        type decimal64 {
                                            fraction-digits 2;
                                        }
                                        description "Indicated the depth 0 to 100 percent.";
                                    }

                                    leaf queue-polling-interval {
                                        type types-sros:time-interval;
                                        description "Indicates the queue polling interval.";
                                    }

                                    leaf last-violation {
                                        type yang:date-and-time;
                                        description "Indicates the last violation time.";
                                    }

                                    leaf total-threshold-violations {
                                        type yang:counter32;
                                        description "Indicates the total threshold violations.";
                                    }

                                    leaf high-water-mark-polling-interval {
                                        type types-sros:time-duration;
                                        units "microseconds";
                                        description "Indicates the high water mark polling interval.";
                                    }

                                } // container queue-depth

                                container statistics {
                                    description "Enter the statistics context";

                                    choice stat-mode {
                                        case profile {

                                            container profile {
                                                description "Enter the profile context";

                                                leaf in-inplus-profile-forwarded-packets {
                                                    type yang:counter64;
                                                    description
                                                        "The number of in-profile/in-plus-profile packets
                                                         (rate below CIR) forwarded.";
                                                }

                                                leaf in-inplus-profile-forwarded-octets {
                                                    type yang:counter64;
                                                    description
                                                        "The number of in-profile/in-plus-profile octets
                                                         (rate below CIR) forwarded.";
                                                }

                                                leaf out-exceed-profile-forwarded-packets {
                                                    type yang:counter64;
                                                    description
                                                        "The number of out-profile/exceed-profile packets
                                                         (rate above CIR) forwarded.";
                                                }

                                                leaf out-exceed-profile-forwarded-octets {
                                                    type yang:counter64;
                                                    description
                                                        "The number of out-profile/exceed-profile octets
                                                         (rate above CIR) forwarded.";
                                                }

                                                leaf in-inplus-profile-dropped-packets {
                                                    type yang:counter64;
                                                    description
                                                        "The number of in-profile/in-plus-profile packets
                                                         discarded.";
                                                }

                                                leaf in-inplus-profile-dropped-octets {
                                                    type yang:counter64;
                                                    description
                                                        "The number of in-profile/in-plus-profile octets
                                                         discarded.";
                                                }

                                                leaf out-exceed-profile-dropped-packets {
                                                    type yang:counter64;
                                                    description
                                                        "The number of out-profile/exceed-profile packets
                                                         discarded.";
                                                }

                                                leaf out-exceed-profile-dropped-octets {
                                                    type yang:counter64;
                                                    description
                                                        "The number of out-profile/exceed-profile octets
                                                         discarded.";
                                                }

                                            } // container profile

                                        }
                                        case v4-v6 {

                                            container v4-v6 {
                                                description "Enter the v4-v6 context";

                                                leaf ipv4-dropped-packets {
                                                    type yang:counter64;
                                                    description "The number of ipv4 packets discarded.";
                                                }

                                                leaf ipv4-dropped-octets {
                                                    type yang:counter64;
                                                    description "The number of ipv4 octets discarded.";
                                                }

                                                leaf ipv6-dropped-packets {
                                                    type yang:counter64;
                                                    description "The number of ipv6 packets discarded.";
                                                }

                                                leaf ipv6-dropped-octets {
                                                    type yang:counter64;
                                                    description "The number of ipv6 octets discarded.";
                                                }

                                                leaf ipv4-forwarded-packets {
                                                    type yang:counter64;
                                                    description "The number of ipv4 packets forwarded.";
                                                }

                                                leaf ipv4-forwarded-octets {
                                                    type yang:counter64;
                                                    description "The number of ipv4 octets forwarded.";
                                                }

                                                leaf ipv6-forwarded-packets {
                                                    type yang:counter64;
                                                    description "The number of ipv6 packets forwarded.";
                                                }

                                                leaf ipv6-forwarded-octets {
                                                    type yang:counter64;
                                                    description "The number of ipv6 octets forwarded.";
                                                }

                                            } // container v4-v6

                                        }
                                    }
                                } // container statistics

                                list hardware-queue {
                                    key "source-card source-fp source-port";
                                    description "Enter the hardware-queue list instance";

                                    leaf source-card {
                                        type int32;
                                        description "Card number";
                                    }

                                    leaf source-fp {
                                        type int32;
                                        description "FP number";
                                    }

                                    leaf source-port {
                                        type types-sros:port;
                                        description "Port identifier";
                                    }

                                    leaf adapted-admin-mbs {
                                        type types-qos:bytes;
                                        units "bytes";
                                        description "Admin MBS.";
                                    }

                                    leaf exceed-droptail {
                                        type union {
                                            type int64 {
                                                range "0..max";
                                            }
                                            type enumeration {
                                                enum auto                           { value -1; }
                                            }
                                        }
                                        description "Exceed droptail.";
                                    }

                                    leaf high-droptail {
                                        type union {
                                            type int64 {
                                                range "0..max";
                                            }
                                            type enumeration {
                                                enum auto                           { value -1; }
                                            }
                                        }
                                        description "High droptail.";
                                    }

                                    leaf high-plus-droptail {
                                        type union {
                                            type int64 {
                                                range "0..max";
                                            }
                                            type enumeration {
                                                enum auto                           { value -1; }
                                            }
                                        }
                                        description "Highplus droptail.";
                                    }

                                    leaf low-droptail {
                                        type union {
                                            type int64 {
                                                range "0..max";
                                            }
                                            type enumeration {
                                                enum auto                           { value -1; }
                                            }
                                        }
                                        description "Low droptail.";
                                    }

                                    leaf operational-cbs {
                                        type types-qos:bytes;
                                        units "bytes";
                                        description "Oper CBS.";
                                    }

                                    leaf operational-cir {
                                        type union {
                                            type enumeration {
                                                enum max                            { value -1; }
                                            }
                                            type int64;
                                        }
                                        description "Oper CIR.";
                                    }

                                    leaf operational-mbs {
                                        type types-qos:bytes;
                                        units "bytes";
                                        description "Oper MBS.";
                                    }

                                    leaf operational-pir {
                                        type union {
                                            type enumeration {
                                                enum max                            { value -1; }
                                            }
                                            type int64;
                                        }
                                        description "Oper PIR.";
                                    }

                                    leaf depth {
                                        type union {
                                            type enumeration {
                                                enum max                            { value -1; }
                                            }
                                            type int64;
                                        }
                                        description "Depth CIR.";
                                    }

                                    leaf operational-burst-limit {
                                        type uint32;
                                        description "Sepcifies the operational burst-limit value.";
                                    }

                                    leaf operational-exceed-burst {
                                        type types-qos:int64-max;
                                        description "Oper burst exceed.";
                                    }

                                    leaf operational-max-transmit-data-size {
                                        type types-qos:int64-max;
                                        description "Oper max transmit data size.";
                                    }

                                    leaf operational-burst-fir {
                                        type types-qos:int64-max;
                                        description "Oper burst FIR.";
                                    }

                                    leaf orphan {
                                        type boolean;
                                        description "Orphan queue";
                                    }

                                    leaf local-parent-rate {
                                        type types-qos:kbps;
                                        description "The local limit rate for the delay budget";
                                    }

                                    container exceed-slope {
                                        description "Enter the exceed-slope context";

                                        leaf current-probability {
                                            type types-sros:percent;
                                            description "Specifies the current probability in percentage";
                                        }

                                    } // container exceed-slope

                                    container high-slope {
                                        description "Enter the high-slope context";

                                        leaf current-probability {
                                            type types-sros:percent;
                                            description "Specifies the current probability in percentage";
                                        }

                                    } // container high-slope

                                    container high-plus-slope {
                                        description "Enter the high-plus-slope context";

                                        leaf current-probability {
                                            type types-sros:percent;
                                            description "Specifies the current probability in percentage";
                                        }

                                    } // container high-plus-slope

                                    container low-slope {
                                        description "Enter the low-slope context";

                                        leaf current-probability {
                                            type types-sros:percent;
                                            description "Specifies the current probability in percentage";
                                        }

                                    } // container low-slope

                                    container aggregate-rate {
                                        description "Enter the aggregate-rate context";

                                        leaf rate {
                                            type types-qos:kbps;
                                            units "kilobps";
                                            description "Rate";
                                        }

                                        leaf on-the-wire {
                                            type types-qos:on-the-wire;
                                            description "On the wire";
                                        }

                                        leaf type {
                                            type types-qos:qos-location;
                                            description "Aggregate rate type";
                                        }

                                        leaf vport-rate {
                                            type types-qos:kbps;
                                            units "kilobps";
                                            description "Vport rate";
                                        }

                                    } // container aggregate-rate

                                } // list hardware-queue

                            } // list queue

                            list policer {
                                key "policer-id";
                                description "Enter the policer list instance";

                                leaf policer-id {
                                    type types-qos:sap-egress-policer-id;
                                    description "The unique identifier for the policer.";
                                }

                                container statistics {
                                    description "Enter the statistics context";

                                    choice stat-mode {
                                        case minimal {

                                            container minimal {
                                                description "Enter the minimal context";

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf all-dropped-packets {
                                                    type yang:counter64;
                                                    description "The number of all the priority packets dropped by the packet processor to traffic manager";
                                                }

                                                leaf all-dropped-octets {
                                                    type yang:counter64;
                                                    description "The number of all the priority octets dropped by the packet processor to traffic manager";
                                                }

                                                leaf all-forwarded-packets {
                                                    type yang:counter64;
                                                    description "The number of all the priority packets forwarded by the packet processor to traffic manager";
                                                }

                                                leaf all-forwarded-octets {
                                                    type yang:counter64;
                                                    description "The number of all the priority octets forwarded by the packet processor to traffic manager";
                                                }

                                            } // container minimal

                                        }
                                        case offered-profile-no-cir {

                                            container offered-profile-no-cir {
                                                description "Enter the offered-profile-no-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-no-cir

                                        }
                                        case offered-profile-cir {

                                            container offered-profile-cir {
                                                description "Enter the offered-profile-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf uncolor-offered-packets {
                                                    type yang:counter64;
                                                    description "The number of uncolor packets offered by the packet processor to traffic manager";
                                                }

                                                leaf uncolor-offered-octets {
                                                    type yang:counter64;
                                                    description "The number of uncolor octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-cir

                                        }
                                        case offered-total-cir {

                                            container offered-total-cir {
                                                description "Enter the offered-total-cir context";

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-total-cir

                                        }
                                        case offered-limited-capped-cir {

                                            container offered-limited-capped-cir {
                                                description "Enter the offered-limited-capped-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                                leaf out-profile-offered-packets {
                                                    type yang:counter64;
                                                    description "The number of out-of-rofile packets offered by the packet processor to traffic manager";
                                                }

                                                leaf out-profile-offered-octets {
                                                    type yang:counter64;
                                                    description "The number of out-of-profile octets offered by the packet processor to traffic manager";
                                                }

                                            } // container offered-limited-capped-cir

                                        }
                                        case offered-profile-capped-cir {

                                            container offered-profile-capped-cir {
                                                description "Enter the offered-profile-capped-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf uncolor-offered-packets {
                                                    type yang:counter64;
                                                    description "The number of uncolor packets offered by the packet processor to traffic manager";
                                                }

                                                leaf uncolor-offered-octets {
                                                    type yang:counter64;
                                                    description "The number of uncolor octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-capped-cir

                                        }
                                        case offered-total-cir-exceed {

                                            container offered-total-cir-exceed {
                                                description "Enter the offered-total-cir-exceed context";

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf exceed-profile-dropped-packets {
                                                    type yang:counter64;
                                                    description "The number of exceed-profile packets dropped by the packet processor to traffic manager";
                                                }

                                                leaf exceed-profile-dropped-octets {
                                                    type yang:counter64;
                                                    description "The number of exceed-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                                leaf exceed-profile-forwarded-packets {
                                                    type yang:counter64;
                                                    description "The number of exceed-profile packets forwarded by the packet processor to traffic manager";
                                                }

                                                leaf exceed-profile-forwarded-octets {
                                                    type yang:counter64;
                                                    description "The number of exceed-profile octets forwarded by the packet processor to traffic manager";
                                                }

                                            } // container offered-total-cir-exceed

                                        }
                                        case offered-four-profile-no-cir {

                                            container offered-four-profile-no-cir {
                                                description "Enter the offered-four-profile-no-cir context";

                                                leaf inplus-profile-offered-packets {
                                                    type yang:counter64;
                                                    description "The number of inplus-profile packets offered by the packet processor to traffic manager";
                                                }

                                                leaf inplus-profile-offered-octets {
                                                    type yang:counter64;
                                                    description "The number of inplus-profile octets offered by the packet processor to traffic manager";
                                                }

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf exceed-profile-offered-packets {
                                                    type yang:counter64;
                                                    description "The number of exceed-profile packets offered by the packet processor to traffic manager";
                                                }

                                                leaf exceed-profile-offered-octets {
                                                    type yang:counter64;
                                                    description "The number of exceed-profile octets offered by the packet processor to traffic manager";
                                                }

                                                leaf inplus-profile-dropped-packets {
                                                    type yang:counter64;
                                                    description "The number of inplus-profile packets dropped by the packet processor to traffic manager";
                                                }

                                                leaf inplus-profile-dropped-octets {
                                                    type yang:counter64;
                                                    description "The number of inplus-profile octets dropped by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf exceed-profile-dropped-packets {
                                                    type yang:counter64;
                                                    description "The number of exceed-profile packets dropped by the packet processor to traffic manager";
                                                }

                                                leaf exceed-profile-dropped-octets {
                                                    type yang:counter64;
                                                    description "The number of exceed-profile octets dropped by the packet processor to traffic manager";
                                                }

                                                leaf inplus-profile-forwarded-packets {
                                                    type yang:counter64;
                                                    description "The number of inplus-profile packets forwarded by the packet processor to traffic manager";
                                                }

                                                leaf inplus-profile-forwarded-octets {
                                                    type yang:counter64;
                                                    description "The number of inplus-profile octets forwarded by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                                leaf exceed-profile-forwarded-packets {
                                                    type yang:counter64;
                                                    description "The number of exceed-profile packets forwarded by the packet processor to traffic manager";
                                                }

                                                leaf exceed-profile-forwarded-octets {
                                                    type yang:counter64;
                                                    description "The number of exceed-profile octets forwarded by the packet processor to traffic manager";
                                                }

                                            } // container offered-four-profile-no-cir

                                        }
                                        case offered-total-cir-four-profile {

                                            container offered-total-cir-four-profile {
                                                description "Enter the offered-total-cir-four-profile context";

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf inplus-profile-dropped-packets {
                                                    type yang:counter64;
                                                    description "The number of inplus-profile packets dropped by the packet processor to traffic manager";
                                                }

                                                leaf inplus-profile-dropped-octets {
                                                    type yang:counter64;
                                                    description "The number of inplus-profile octets dropped by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf exceed-profile-dropped-packets {
                                                    type yang:counter64;
                                                    description "The number of exceed-profile packets dropped by the packet processor to traffic manager";
                                                }

                                                leaf exceed-profile-dropped-octets {
                                                    type yang:counter64;
                                                    description "The number of exceed-profile octets dropped by the packet processor to traffic manager";
                                                }

                                                leaf inplus-profile-forwarded-packets {
                                                    type yang:counter64;
                                                    description "The number of inplus-profile packets forwarded by the packet processor to traffic manager";
                                                }

                                                leaf inplus-profile-forwarded-octets {
                                                    type yang:counter64;
                                                    description "The number of inplus-profile octets forwarded by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                                leaf exceed-profile-forwarded-packets {
                                                    type yang:counter64;
                                                    description "The number of exceed-profile packets forwarded by the packet processor to traffic manager";
                                                }

                                                leaf exceed-profile-forwarded-octets {
                                                    type yang:counter64;
                                                    description "The number of exceed-profile octets forwarded by the packet processor to traffic manager";
                                                }

                                            } // container offered-total-cir-four-profile

                                        }
                                        case v4-v6 {

                                            container v4-v6 {
                                                description "Enter the v4-v6 context";

                                                leaf ipv4-offered-packets {
                                                    type yang:counter64;
                                                    description "The number of ipv4 packets offered by the packet processor to traffic manager";
                                                }

                                                leaf ipv4-offered-octets {
                                                    type yang:counter64;
                                                    description "The number of ipv4 octets offered by the packet processor to traffic manager";
                                                }

                                                leaf ipv6-offered-packets {
                                                    type yang:counter64;
                                                    description "The number of ipv6 packets offered by the packet processor to traffic manager";
                                                }

                                                leaf ipv6-offered-octets {
                                                    type yang:counter64;
                                                    description "The number of ipv6 octets offered by the packet processor to traffic manager";
                                                }

                                                leaf ipv4-dropped-packets {
                                                    type yang:counter64;
                                                    description "The number of ipv4 packets dropped by the packet processor to traffic manager";
                                                }

                                                leaf ipv4-dropped-octets {
                                                    type yang:counter64;
                                                    description "The number of ipv4 octets dropped by the packet processor to traffic manager";
                                                }

                                                leaf ipv6-dropped-packets {
                                                    type yang:counter64;
                                                    description "The number of ipv6 packets dropped by the packet processor to traffic manager";
                                                }

                                                leaf ipv6-dropped-octets {
                                                    type yang:counter64;
                                                    description "The number of ipv6 octets dropped by the packet processor to traffic manager";
                                                }

                                                leaf ipv4-forwarded-packets {
                                                    type yang:counter64;
                                                    description "The number of ipv4 packets forwarded by the packet processor to traffic manager";
                                                }

                                                leaf ipv4-forwarded-octets {
                                                    type yang:counter64;
                                                    description "The number of ipv4 octets forwarded by the packet processor to traffic manager";
                                                }

                                                leaf ipv6-forwarded-packets {
                                                    type yang:counter64;
                                                    description "The number of ipv6 packets forwarded by the packet processor to traffic manager";
                                                }

                                                leaf ipv6-forwarded-octets {
                                                    type yang:counter64;
                                                    description "The number of ipv6 octets forwarded by the packet processor to traffic manager";
                                                }

                                            } // container v4-v6

                                        }
                                        case bonding {

                                            container bonding {
                                                description "Enter the bonding context";

                                                leaf connection-1-offered-packets {
                                                    type yang:counter64;
                                                    description "The number of connection-1 packets offered by the packet processor to traffic manager";
                                                }

                                                leaf connection-1-offered-octets {
                                                    type yang:counter64;
                                                    description "The number of connection-1 octets offered by the packet processor to traffic manager";
                                                }

                                                leaf connection-2-offered-packets {
                                                    type yang:counter64;
                                                    description "The number of connection-2 packets offered by the packet processor to traffic manager";
                                                }

                                                leaf connection-2-offered-octets {
                                                    type yang:counter64;
                                                    description "The number of connection-2 octets offered by the packet processor to traffic manager";
                                                }

                                                leaf connection-1-dropped-packets {
                                                    type yang:counter64;
                                                    description "The number of connection-1 packets dropped by the packet processor to traffic manager";
                                                }

                                                leaf connection-1-dropped-octets {
                                                    type yang:counter64;
                                                    description "The number of connection-1 octets dropped by the packet processor to traffic manager";
                                                }

                                                leaf connection-2-dropped-packets {
                                                    type yang:counter64;
                                                    description "The number of connection-2 packets dropped by the packet processor to traffic manager";
                                                }

                                                leaf connection-2-dropped-octets {
                                                    type yang:counter64;
                                                    description "The number of connection-2 octets dropped by the packet processor to traffic manager";
                                                }

                                                leaf connection-1-forwarded-packets {
                                                    type yang:counter64;
                                                    description "The number of connection-1 packets forwarded by the packet processor to traffic manager";
                                                }

                                                leaf connection-1-forwarded-octets {
                                                    type yang:counter64;
                                                    description "The number of connection-1 octets forwarded by the packet processor to traffic manager";
                                                }

                                                leaf connection-2-forwarded-packets {
                                                    type yang:counter64;
                                                    description "The number of connection-2 packets forwarded by the packet processor to traffic manager";
                                                }

                                                leaf connection-2-forwarded-octets {
                                                    type yang:counter64;
                                                    description "The number of connection-2 octets forwarded by the packet processor to traffic manager";
                                                }

                                            } // container bonding

                                        }
                                    }
                                } // container statistics

                                list hardware-policer {
                                    key "dest-card dest-fp dest-port";
                                    description "Enter the hardware-policer list instance";

                                    leaf dest-card {
                                        type int32;
                                        description "Card number";
                                    }

                                    leaf dest-fp {
                                        type int32;
                                        description "FP number";
                                    }

                                    leaf dest-port {
                                        type types-sros:port;
                                        description "Port identifier";
                                    }

                                    leaf adapted-admin-cbs {
                                        type int64;
                                        units "bytes";
                                        description "Admin CBS.";
                                    }

                                    leaf adapted-admin-mbs {
                                        type int64;
                                        units "bytes";
                                        description "Admin MBS.";
                                    }

                                    leaf adapted-hp-only {
                                        type int64;
                                        units "bytes";
                                        description "Hi Prio Only.";
                                    }

                                    leaf depth {
                                        type int64;
                                        units "bytes";
                                        description "Depth.";
                                    }

                                    leaf operational-cir {
                                        type types-qos:int64-max;
                                        description "Oper CIR.";
                                    }

                                    leaf operational-fir {
                                        type types-qos:int64-max;
                                        description "Oper FIR.";
                                    }

                                    leaf operational-pir {
                                        type types-qos:int64-max;
                                        description "Oper PIR.";
                                    }

                                } // list hardware-policer

                            } // list policer

                        } // container sap-egress

                        container policer-control-policy {
                            description "Enter the policer-control-policy context";

                            list arbiter {
                                key "arbiter-name";
                                description "Enter the arbiter list instance";

                                leaf arbiter-name {
                                    type types-sros:named-item;
                                    description "Specifies the arbiter name.";
                                }

                                container statistics {
                                    description "Enter the statistics context";

                                    leaf forwarded-packets {
                                        type yang:counter64;
                                        description "The number of forwarded packets.";
                                    }

                                    leaf forwarded-octets {
                                        type yang:counter64;
                                        description "The number of forwarded octets.";
                                    }

                                    list lag-member-port {
                                        key "port";
                                        description "Enter the lag-member-port list instance";

                                        leaf port {
                                            type types-sros:port;
                                            description "Port identifier";
                                        }

                                        leaf forwarded-packets {
                                            type yang:counter64;
                                            description "The number of forwarded packets.";
                                        }

                                        leaf forwarded-octets {
                                            type yang:counter64;
                                            description "The number of forwarded octets.";
                                        }

                                    } // list lag-member-port

                                } // container statistics

                            } // list arbiter

                        } // container policer-control-policy

                        container scheduler-policy {
                            description "Enter the scheduler-policy context";

                            list scheduler {
                                key "scheduler-name";
                                description "Enter the scheduler list instance";

                                leaf scheduler-name {
                                    type types-sros:named-item;
                                    description "Specifies the scheduler name.";
                                }

                                container statistics {
                                    description "Enter the statistics context";

                                    leaf forwarded-packets {
                                        type yang:counter64;
                                        description "The number of forwarded packets.";
                                    }

                                    leaf forwarded-octets {
                                        type yang:counter64;
                                        description "The number of forwarded octets.";
                                    }

                                    list lag-member-port {
                                        key "port";
                                        description "Enter the lag-member-port list instance";

                                        leaf port {
                                            type types-sros:port;
                                            description "Port identifier";
                                        }

                                        leaf forwarded-packets {
                                            type yang:counter64;
                                            description "The number of forwarded packets.";
                                        }

                                        leaf forwarded-octets {
                                            type yang:counter64;
                                            description "The number of forwarded octets.";
                                        }

                                    } // list lag-member-port

                                } // container statistics

                                list sap-scheduler {
                                    key "card fp port physical-port";
                                    description "Enter the sap-scheduler list instance";

                                    leaf card {
                                        type int32;
                                        description "Card number";
                                    }

                                    leaf fp {
                                        type types-services:fp-any;
                                        description "FP number";
                                    }

                                    leaf port {
                                        type types-services:port-any;
                                        description "Port information";
                                    }

                                    leaf physical-port {
                                        type types-services:port-any;
                                        description "Physical port";
                                    }

                                    leaf members {
                                        type uint32;
                                        description "Members";
                                    }

                                    leaf max-pir {
                                        type types-qos:sched-pir;
                                        description "Max PIR rate";
                                    }

                                    leaf oper-pir {
                                        type types-qos:sched-pir;
                                        description "Operational PIR rate";
                                    }

                                    leaf parent-limit-unused-bandwidth {
                                        type boolean;
                                        description "Parent limit unused bandwidth";
                                    }

                                    leaf orphan {
                                        type boolean;
                                        description "Orphan";
                                    }

                                    container within-cir {
                                        description "Enter the within-cir context";

                                        leaf consumed {
                                            type types-qos:kbps;
                                            units "kilobps";
                                            description "Consumed";
                                        }

                                        leaf offered {
                                            type types-qos:kbps;
                                            units "kilobps";
                                            description "Offered";
                                        }

                                        leaf parent-level {
                                            type int32;
                                            description "Parent level";
                                        }

                                    } // container within-cir

                                    container above-cir {
                                        description "Enter the above-cir context";

                                        leaf consumed {
                                            type types-qos:kbps;
                                            units "kilobps";
                                            description "Consumed";
                                        }

                                        leaf offered {
                                            type types-qos:kbps;
                                            units "kilobps";
                                            description "Offered";
                                        }

                                        leaf parent-level {
                                            type int32;
                                            description "Parent level";
                                        }

                                    } // container above-cir

                                    list level {
                                        key "level-index";
                                        description "Enter the level list instance";

                                        leaf level-index {
                                            type int32 {
                                                range "0..8";
                                            }
                                        }

                                        container within-cir {
                                            description "Enter the within-cir context";

                                            leaf members {
                                                type uint32;
                                                description "Members";
                                            }

                                            leaf consumed {
                                                type types-qos:kbps;
                                                units "kilobps";
                                                description "Consumed";
                                            }

                                            leaf offered {
                                                type types-qos:kbps;
                                                units "kilobps";
                                                description "Offered";
                                            }

                                            container sched-hierarchy {
                                                description "Enter the sched-hierarchy context";

                                                container queue {
                                                    description "Enter the queue context";

                                                    container sap {
                                                        description "Enter the sap context";

                                                        list queue {
                                                            key "member";
                                                            description "Enter the queue list instance";

                                                            leaf member {
                                                                type uint32;
                                                                description "Member information";
                                                            }

                                                            leaf queue-id {
                                                                type int32;
                                                                description "Queue identifier";
                                                            }

                                                            leaf sap-id {
                                                                type types-sros:sap;
                                                                description "SAP identifier";
                                                            }

                                                            leaf port {
                                                                type types-sros:port;
                                                                description "Port identifier";
                                                            }

                                                        } // list queue

                                                    } // container sap

                                                } // container queue

                                                container scheduler {
                                                    description "Enter the scheduler context";

                                                    container sap {
                                                        description "Enter the sap context";

                                                        list scheduler {
                                                            key "member";
                                                            description "Enter the scheduler list instance";

                                                            leaf member {
                                                                type uint32;
                                                                description "Member information";
                                                            }

                                                            leaf scheduler-name {
                                                                type string;
                                                                description "Name";
                                                            }

                                                            leaf sap-id {
                                                                type types-sros:sap;
                                                                description "SAP identifier";
                                                            }

                                                        } // list scheduler

                                                        list t0-scheduler {
                                                            key "member";
                                                            description "Enter the t0-scheduler list instance";

                                                            leaf member {
                                                                type uint32;
                                                                description "Member information";
                                                            }

                                                            leaf scheduler-name {
                                                                type string;
                                                                description "Name";
                                                            }

                                                            leaf sap-id {
                                                                type types-sros:sap;
                                                                description "SAP identifier";
                                                            }

                                                        } // list t0-scheduler

                                                    } // container sap

                                                } // container scheduler

                                            } // container sched-hierarchy

                                        } // container within-cir

                                        container above-cir {
                                            description "Enter the above-cir context";

                                            leaf members {
                                                type uint32;
                                                description "Members";
                                            }

                                            leaf consumed {
                                                type types-qos:kbps;
                                                units "kilobps";
                                                description "Consumed";
                                            }

                                            leaf offered {
                                                type types-qos:kbps;
                                                units "kilobps";
                                                description "Offered";
                                            }

                                            container sched-hierarchy {
                                                description "Enter the sched-hierarchy context";

                                                container queue {
                                                    description "Enter the queue context";

                                                    container sap {
                                                        description "Enter the sap context";

                                                        list queue {
                                                            key "member";
                                                            description "Enter the queue list instance";

                                                            leaf member {
                                                                type uint32;
                                                                description "Member information";
                                                            }

                                                            leaf queue-id {
                                                                type int32;
                                                                description "Queue identifier";
                                                            }

                                                            leaf sap-id {
                                                                type types-sros:sap;
                                                                description "SAP identifier";
                                                            }

                                                            leaf port {
                                                                type types-sros:port;
                                                                description "Port identifier";
                                                            }

                                                        } // list queue

                                                    } // container sap

                                                } // container queue

                                                container scheduler {
                                                    description "Enter the scheduler context";

                                                    container sap {
                                                        description "Enter the sap context";

                                                        list scheduler {
                                                            key "member";
                                                            description "Enter the scheduler list instance";

                                                            leaf member {
                                                                type uint32;
                                                                description "Member information";
                                                            }

                                                            leaf scheduler-name {
                                                                type string;
                                                                description "Name";
                                                            }

                                                            leaf sap-id {
                                                                type types-sros:sap;
                                                                description "SAP identifier";
                                                            }

                                                        } // list scheduler

                                                        list t0-scheduler {
                                                            key "member";
                                                            description "Enter the t0-scheduler list instance";

                                                            leaf member {
                                                                type uint32;
                                                                description "Member information";
                                                            }

                                                            leaf scheduler-name {
                                                                type string;
                                                                description "Name";
                                                            }

                                                            leaf sap-id {
                                                                type types-sros:sap;
                                                                description "SAP identifier";
                                                            }

                                                        } // list t0-scheduler

                                                    } // container sap

                                                } // container scheduler

                                            } // container sched-hierarchy

                                        } // container above-cir

                                    } // list level

                                } // list sap-scheduler

                            } // list scheduler

                            list t0-scheduler {
                                key "card scheduler-name";
                                description "Enter the t0-scheduler list instance";

                                leaf card {
                                    type int32;
                                    description "Card number";
                                }

                                leaf scheduler-name {
                                    type string;
                                    description "Name";
                                }

                                leaf orphan {
                                    type boolean;
                                    description "Orphan";
                                }

                                leaf members {
                                    type uint32;
                                    description "Members";
                                }

                                container sched-hierarchy {
                                    description "Enter the sched-hierarchy context";

                                    container queue {
                                        description "Enter the queue context";

                                        container sap {
                                            description "Enter the sap context";

                                            list queue {
                                                key "member";
                                                description "Enter the queue list instance";

                                                leaf member {
                                                    type uint32;
                                                    description "Member information";
                                                }

                                                leaf queue-id {
                                                    type int32;
                                                    description "Queue identifier";
                                                }

                                                leaf sap-id {
                                                    type types-sros:sap;
                                                    description "SAP identifier";
                                                }

                                                leaf port {
                                                    type types-sros:port;
                                                    description "Port identifier";
                                                }

                                            } // list queue

                                        } // container sap

                                    } // container queue

                                } // container sched-hierarchy

                            } // list t0-scheduler

                        } // container scheduler-policy

                    } // container qos

                    list agg-rate-state {
                        key "card fp port physical-port";
                        description "Enter the agg-rate-state list instance";

                        leaf card {
                            type int32;
                            description "Card number";
                        }

                        leaf fp {
                            type types-services:fp-any;
                            description "FP number";
                        }

                        leaf port {
                            type types-services:port-any;
                            description "Port information";
                        }

                        leaf physical-port {
                            type types-services:port-any;
                            description "Physical port";
                        }

                        leaf rate {
                            type types-qos:kbps;
                            units "kilobps";
                            description "Rate";
                        }

                        leaf limit-unused-bandwidth {
                            type boolean;
                            description "Aggregate rate limit-unused-bandwidth";
                        }

                        leaf on-the-wire {
                            type types-qos:on-the-wire;
                            description "On the wire";
                        }

                    } // list agg-rate-state

                } // container egress

                container lag {
                    description "Enter the lag context";

                    leaf active-port {
                        type types-sros:port;
                        description
                            "Port on the lag associated with this SAP, that is used when
                             lag-per-link-hash is enabled on the lag or when lag-link-map-profile
                             is configured on this SAP.";
                    }

                    container per-link-hash-oper {
                        description "Enter the per-link-hash-oper context";

                        leaf class {
                            type int32;
                            description "Operational value for class associated with this SAP.";
                        }

                        leaf weight {
                            type int32;
                            description "Operational value used for weight associated with this SAP.";
                        }

                        leaf is-overriden {
                            type boolean;
                            description
                                "Whether administrative values, subscriber management determined
                                 operational weight and class are used for this SAP.";
                        }

                    } // container per-link-hash-oper

                } // container lag

                container igmp-host-tracking {
                    description "Enter the igmp-host-tracking context";

                    leaf group-count {
                        type int32;
                        description "The number of multicast groups which have been learned on this interface.";
                    }

                    list host-statistics {
                        key "host-address";
                        description "Enter the host-statistics list instance";

                        leaf host-address {
                            type types-sros:ipv4-address;
                            description "The IP address of this host.";
                        }

                        leaf v2-reports {
                            type yang:counter32;
                            description "V2 Reports.";
                        }

                        leaf leaves {
                            type yang:counter32;
                            description "V2 Leaves.";
                        }

                        leaf v3-reports {
                            type yang:counter32;
                            description "V3 Reports.";
                        }

                        leaf drops {
                            type yang:counter32;
                            description "Total number of dropped packets.";
                        }

                        leaf group-joins {
                            type yang:counter32;
                            description "Total number of joins.";
                        }

                        leaf group-leaves {
                            type yang:counter32;
                            description "Total number of leaves.";
                        }

                        leaf group-expiries {
                            type yang:counter32;
                            description "Total number of group expiries.";
                        }

                        leaf import-policy-drops {
                            type yang:counter32;
                            description
                                "Number of times we matched the host IP address or
                                 group or source addresses specified in the import
                                 policy.";
                        }

                        leaf maximum-number-groups-drops {
                            type yang:counter32;
                            description
                                "Number of times a join is dropped because we reached
                                 the maximum number of groups.";
                        }

                        leaf maximum-number-sources-drops {
                            type yang:counter32;
                            description
                                "Number of times a join is dropped because we reached
                                 the maximum number of sources per group.";
                        }

                        leaf maximum-number-group-sources-drops {
                            type yang:counter32;
                            description
                                "Number of times a join is dropped because we reached
                                 the maximum number group-source combinations.";
                        }

                    } // list host-statistics

                    list host-group-sources {
                        key "host-address group-address source-address";
                        description "Enter the host-group-sources list instance";

                        leaf host-address {
                            type types-sros:ipv4-address;
                            description "The IP address of this host.";
                        }

                        leaf group-address {
                            type types-sros:ipv4-multicast-address;
                            description "Group address of multicast channel.";
                        }

                        leaf source-address {
                            type types-sros:ipv4-address;
                            description "Source address of multicast channel.";
                        }

                        leaf bandwidth {
                            type uint32;
                            units "kilobps";
                            description
                                "The bandwidth allocated to this host for this multicast
                                 stream.";
                        }

                        leaf up-time {
                            type uint32;
                            units "seconds";
                            description "The time elapsed since this entry was created.";
                        }

                        leaf expiry-time {
                            type uint32;
                            units "seconds";
                            description "The time remaining before this entry is aged out.";
                        }

                        leaf subscriber-id {
                            type types-submgt:subscriber-id;
                            description "The subscriber identification of this subscriber host.";
                        }

                    } // list host-group-sources

                } // container igmp-host-tracking

                container igmp-snooping {
                    description "Enter the igmp-snooping context";

                    container mcac {
                        description "Enter the mcac context";

                        leaf in-use-mandatory-bandwidth {
                            type uint32;
                            units "kilobps";
                            description
                                "The in-use bandwidth for the mandatory channels for this
                                 protocol interface instance.";
                        }

                        leaf in-use-optional-bandwidth {
                            type uint32;
                            units "kilobps";
                            description
                                "The in-use bandwidth for the optional channels for this
                                 protocol interface instance.";
                        }

                        leaf available-mandatory-bandwidth {
                            type uint32;
                            units "kilobps";
                            description
                                "The pre-reserved bandwidth for the mandatory channels for
                                 this interface instance.";
                        }

                        leaf available-optional-bandwidth {
                            type uint32;
                            units "kilobps";
                            description "The available bandwidth for this interface instance.";
                        }

                        leaf values-in-transit {
                            type boolean;
                            description
                                "The operational (available and in-use mandatory/optional) value for the
                                 following objects is in transition due to configuration change:
                                 - available-mandatory-bandwidth
                                 - available-bandwidth
                                 - in-use-mandatory-bandwidth
                                 - in-use-optional-bandwidth.";
                        }

                    } // container mcac

                    container statistics {
                        description "Enter the statistics context";

                        container received {
                            description "Enter the received context";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                        } // container received

                        container transmitted {
                            description "Enter the transmitted context";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                            leaf errors {
                                type yang:counter32;
                                description "Transmission Errors.";
                            }

                        } // container transmitted

                        container forwarded {
                            description "Enter the forwarded context";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                            leaf unknown-types {
                                type yang:counter32;
                                description "Unknown types.";
                            }

                            leaf errors {
                                type yang:counter32;
                                description "Forwarding Errors.";
                            }

                        } // container forwarded

                        container error {
                            description "Enter the error context";

                            leaf bad-length {
                                type yang:counter32;
                                description "Bad length.";
                            }

                            leaf bad-ip-checksum {
                                type yang:counter32;
                                description "Bad Ip checksum.";
                            }

                            leaf unknown-type {
                                type yang:counter32;
                                description "Unknown type.";
                            }

                            leaf wrong-version {
                                type yang:counter32;
                                description "Wrong version.";
                            }

                            leaf import-policy-drops {
                                type yang:counter32;
                                description
                                    "Number of times we matched the host IP address or group or
                                     source addresses specified in the import policy.";
                            }

                            leaf missing-router-alert {
                                type yang:counter32;
                                description "Router alert flag is not set.";
                            }

                            leaf bad-encoding {
                                type yang:counter32;
                                description "Badly encoded.";
                            }

                            leaf local-scope {
                                type yang:counter32;
                                description "Link-local scope multicast group address.";
                            }

                            leaf mcac-policy-drops {
                                type yang:counter32;
                                description
                                    "Number of times a join is dropped because of applying a
                                     multicast CAC policy.";
                            }

                            leaf reached-maximum-number-groups {
                                type yang:counter32;
                                description
                                    "Number of times a join is dropped because we reached the maximum
                                     number of groups.";
                            }

                            leaf reached-maximum-number-group-sources {
                                type yang:counter32;
                                description
                                    "Number of times a join is dropped because we reached the maximum
                                     number group-source combinations.";
                            }

                            leaf reached-maximum-number-sources {
                                type yang:counter32;
                                description
                                    "Number of times a join is dropped because we reached the maximum
                                     number of sources per group.";
                            }

                            leaf out-of-memory-drops {
                                type yang:counter32;
                                description "Number of times a join is dropped because we ran out of memory.";
                            }

                            leaf mcs-failures {
                                type yang:counter32;
                                description "Number of times a group could not be synced through multi chassis synchronisation (MCS).";
                            }

                            leaf bad-igmp-checksum {
                                type yang:counter32;
                                description
                                    "Number of times a packet is dropped because of a bad IGMP
                                     header checksum.";
                            }

                            leaf zero-source-ip-addr {
                                type yang:counter32;
                                description "Number of times a packet is dropped because it has a zero source ip address.";
                            }

                            leaf send-query-cfg-drops {
                                type yang:counter32;
                                description "Number of times a query is dropped because send-queries is configured.";
                            }

                            leaf mvr-from-vpls-cfg-drops {
                                type yang:counter32;
                                description "Number of times a packet is dropped because mvr from-vpls could not be applied.";
                            }

                            leaf mvr-to-sap-cfg-drops {
                                type yang:counter32;
                                description "Number of times a packet is dropped because it has mvr to-sap configuration.";
                            }

                        } // container error

                    } // container statistics

                    list group {
                        key "group-address";
                        description "Enter the group list instance";

                        leaf group-address {
                            type types-sros:ipv4-multicast-address;
                            description "Group address of multicast channel.";
                        }

                        leaf group-type {
                            type types-igmp:learn-type;
                        }

                        leaf filter-mode {
                            type types-igmp:filter-mode;
                        }

                        leaf expiry-time {
                            type uint32;
                            units "seconds";
                            description "The time left before multicast group timeout.";
                        }

                        leaf up-time {
                            type uint32;
                            units "seconds";
                            description "The time elapsed since this entry was created.";
                        }

                        leaf v1-host-timer {
                            type uint32;
                            units "seconds";
                            description
                                "The time remaining until the local router will assume that
                                 there are no longer any version 1 members.";
                        }

                        leaf v2-host-timer {
                            type uint32;
                            units "seconds";
                            description
                                "The time remaining until the local router will assume that
                                 there are no longer any version 2 members.";
                        }

                        leaf igmp-compatibility-mode {
                            type types-igmp:igmp-version;
                            description "Compatibility with older version routers.";
                        }

                        leaf mvr-from-vpls-name {
                            type types-services:service-name;
                            description
                                "The name of the vpls service from which the multicast streams
                                 corresponding to this group are copied.";
                        }

                        leaf mvr-to-sap-id {
                            type types-sros:sap;
                            description
                                "The sap to which the multicast streams corresponding to this
                                 group are copied.";
                        }

                        list source {
                            key "source-address";
                            description "Enter the source list instance";

                            leaf source-address {
                                type types-sros:ipv4-address;
                                description "Source address of multicast channel.";
                            }

                            leaf source-type {
                                type types-igmp:learn-type;
                            }

                            leaf forwarding-state {
                                type types-igmp:forwarding-state;
                                description "Traffic forwardeding state on this port.";
                            }

                            leaf expiry-time {
                                type uint32;
                                units "seconds";
                                description "The time left before multicast group timeout.";
                            }

                            leaf up-time {
                                type uint32;
                                units "seconds";
                                description "The time elapsed since this entry was created.";
                            }

                        } // list source

                    } // list group

                } // container igmp-snooping

                container mld-snooping {
                    description "Enter the mld-snooping context";

                    container statistics {
                        description "Enter the statistics context";

                        container received {
                            description "Enter the received context";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf leaves {
                                type yang:counter32;
                                description "Leaves.";
                            }

                            leaf drops {
                                type yang:counter32;
                                description "Total number of dropped packets.";
                            }

                        } // container received

                        container transmitted {
                            description "Enter the transmitted context";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf leaves {
                                type yang:counter32;
                                description "Leaves.";
                            }

                            leaf drops {
                                type yang:counter32;
                                description "Total number of dropped packets.";
                            }

                            leaf errors {
                                type yang:counter32;
                                description "Transmission Errors.";
                            }

                        } // container transmitted

                        container forwarded {
                            description "Enter the forwarded context";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf leaves {
                                type yang:counter32;
                                description "Leaves.";
                            }

                            leaf drops {
                                type yang:counter32;
                                description "Total number of dropped packets.";
                            }

                            leaf unknown-types {
                                type yang:counter32;
                                description "Unknown types.";
                            }

                            leaf errors {
                                type yang:counter32;
                                description "Forwarding Errors.";
                            }

                        } // container forwarded

                        container error {
                            description "Enter the error context";

                            leaf bad-length {
                                type yang:counter32;
                                description "Bad length.";
                            }

                            leaf unknown-type {
                                type yang:counter32;
                                description "Unknown type.";
                            }

                            leaf wrong-version {
                                type yang:counter32;
                                description "Wrong version.";
                            }

                            leaf import-policy-drops {
                                type yang:counter32;
                                description
                                    "Number of times we matched the host IP address or group or
                                     source addresses specified in the import policy.";
                            }

                            leaf missing-router-alert {
                                type yang:counter32;
                                description "Router alert flag is not set.";
                            }

                            leaf bad-encoding {
                                type yang:counter32;
                                description "Badly encoded.";
                            }

                            leaf local-scope {
                                type yang:counter32;
                                description "Link-local scope multicast group address.";
                            }

                            leaf reserved-scope {
                                type yang:counter32;
                                description "Reserved scope multicast group address.";
                            }

                            leaf reached-maximum-number-groups {
                                type yang:counter32;
                                description
                                    "Number of times a join is dropped because we reached the maximum
                                     number of groups.";
                            }

                            leaf reached-maximum-number-group-sources {
                                type yang:counter32;
                                description
                                    "Number of times a join is dropped because we reached the maximum
                                     number group-source combinations.";
                            }

                            leaf reached-maximum-number-sources {
                                type yang:counter32;
                                description
                                    "Number of times a join is dropped because we reached the maximum
                                     number of sources per group.";
                            }

                            leaf out-of-memory-drops {
                                type yang:counter32;
                                description "Number of times a join is dropped because we ran out of memory.";
                            }

                            leaf mcs-failures {
                                type yang:counter32;
                                description "Number of times a group could not be synced through multi chassis synchronisation (MCS).";
                            }

                            leaf bad-mld-checksum {
                                type yang:counter32;
                                description
                                    "Number of times a packet is dropped because of a bad MLD
                                     header checksum.";
                            }

                            leaf zero-source-ip-addr {
                                type yang:counter32;
                                description "Number of times a packet is dropped because it has a zero source ip address.";
                            }

                            leaf send-query-cfg-drops {
                                type yang:counter32;
                                description "Number of times a query is dropped because send-queries is configured.";
                            }

                            leaf mvr-from-vpls-cfg-drops {
                                type yang:counter32;
                                description "Number of times a packet is dropped because mvr from-vpls could not be applied.";
                            }

                            leaf mvr-to-sap-cfg-drops {
                                type yang:counter32;
                                description "Number of times a packet is dropped because it has mvr to-sap configuration.";
                            }

                        } // container error

                    } // container statistics

                    list group {
                        key "group-address";
                        description "Enter the group list instance";

                        leaf group-address {
                            type types-sros:ipv6-multicast-address;
                            description "Group address of multicast channel.";
                        }

                        leaf group-type {
                            type types-igmp:learn-type;
                        }

                        leaf filter-mode {
                            type types-igmp:filter-mode;
                        }

                        leaf expiry-time {
                            type uint32;
                            units "seconds";
                            description "The time left before multicast group timeout.";
                        }

                        leaf up-time {
                            type uint32;
                            units "seconds";
                            description "The time elapsed since this entry was created.";
                        }

                        leaf v1-host-timer {
                            type uint32;
                            units "seconds";
                            description
                                "The time remaining until the local router will assume that
                                 there are no longer any version 1 members.";
                        }

                        leaf mld-compatibility-mode {
                            type types-igmp:mld-version;
                            description "Compatibility with older version routers.";
                        }

                        leaf mvr-from-vpls-name {
                            type types-services:service-name;
                            description
                                "The name of the vpls service from which the multicast streams
                                 corresponding to this group are copied.";
                        }

                        leaf mvr-to-sap-id {
                            type types-sros:sap;
                            description
                                "The sap to which the multicast streams corresponding to this
                                 group are copied.";
                        }

                        list source {
                            key "source-address";
                            description "Enter the source list instance";

                            leaf source-address {
                                type types-sros:ipv6-address;
                                description "Source address of multicast channel.";
                            }

                            leaf source-type {
                                type types-igmp:learn-type;
                            }

                            leaf forwarding-state {
                                type types-igmp:forwarding-state;
                                description "Traffic forwardeding state on this port.";
                            }

                            leaf expiry-time {
                                type uint32;
                                units "seconds";
                                description "The time left before multicast group timeout.";
                            }

                            leaf up-time {
                                type uint32;
                                units "seconds";
                                description "The time elapsed since this entry was created.";
                            }

                        } // list source

                    } // list group

                } // container mld-snooping

                container pim-snooping {
                    description "Enter the pim-snooping context";

                    container ipv4 {
                        description "Enter the ipv4 context";

                        leaf oper-state {
                            type types-sros:oper-state;
                            description
                                "The value of the this object indicates the operational
                                 state of PIM for this interface.";
                        }

                        leaf up-time {
                            type uint32;
                            units "seconds";
                            description "The time since this interface became operational.";
                        }

                        leaf group-count {
                            type uint32;
                            description
                                "The number of multicast groups which currently have this
                                 interface as an outgoing interface.";
                        }

                        leaf maximum-groups-until-now {
                            type uint32;
                            description "The highest value that 'group-count' had till now.";
                        }

                        leaf pseudo-wire-forwarder {
                            type boolean;
                            description
                                "Whether this interface is the forwarding interface
                                 of a pair of redundant pseudo-wire ports.";
                        }

                        container statistics {
                            description "Enter the statistics context";

                            leaf rx-packets {
                                type yang:counter32;
                                description "The number of multicast data packets received on this interface.";
                            }

                            leaf rx-hellos {
                                type yang:counter32;
                                description "The number of PIM hello messages received on this interface.";
                            }

                            leaf rx-join-prunes {
                                type yang:counter32;
                                description
                                    "The number of PIM
                                     Join Prune messages received on this interface.";
                            }

                            leaf tx-packets {
                                type yang:counter32;
                                description "The number of multicast data packets transmitted on this interface.";
                            }

                            leaf tx-join-prunes {
                                type yang:counter32;
                                description
                                    "The number of PIM
                                     Join Prune messages transmitted on this interface.";
                            }

                            leaf rx-hellos-dropped {
                                type yang:counter32;
                                description
                                    "The number of PIM Hello messages which were received on this interface but were
                                     dropped.";
                            }

                            leaf rx-neighbor-unknown {
                                type yang:counter32;
                                description
                                    "The number of PIM messages (other than Hello messages) which were received on this
                                     interface and were rejected because the adjacency with the neighbor
                                     router was not already established.";
                            }

                            leaf rx-bad-checksum-discard {
                                type yang:counter32;
                                description
                                    "The number of PIM messages received on this interface which were discarded because
                                     of bad checksum.";
                            }

                            leaf rx-bad-version-discard {
                                type yang:counter32;
                                description "The number of PIM messages with bad versions received on this interface.";
                            }

                            leaf rx-bad-encodings {
                                type yang:counter32;
                                description "The number of PIM messages with bad encodings received on this interface.";
                            }

                            leaf join-policy-drops {
                                type yang:counter32;
                                description
                                    "The number of times the join policy match resulted in dropping PIM Join-Prune
                                     Message or one of the source group contained in the message.";
                            }

                            leaf rx-join-prune-errors {
                                type yang:counter32;
                                description
                                    "The number of errors while processing Join-Prune messages received on this
                                     interface.";
                            }

                        } // container statistics

                        list neighbor {
                            key "neighbor-address";
                            description "Enter the neighbor list instance";

                            leaf neighbor-address {
                                type types-sros:ipv4-address;
                                description "This value indicates the IPv4 address of the PIM neighbor.";
                            }

                            leaf dr-priority {
                                type uint32;
                                description
                                    "This value indicates neighbor's DR priority which is received
                                     in the hello message. If the Hello Message did not contain
                                     the DR priority field, the value of priority will be '1'.";
                            }

                            leaf dr-priority-present {
                                type boolean;
                                description
                                    "This value of indicates whether the DR priority field was present
                                     in the Hello message received from the PIM neighbor.";
                            }

                            leaf tracking-support {
                                type boolean;
                                description
                                    "This value indicates whether the T bit in the LAN Prune Delay
                                     option was present in the Hello message. This indicates the
                                     neighbor's capability to disable Join message suppression.";
                            }

                            leaf lan-delay {
                                type uint32;
                                units "milliseconds";
                                description
                                    "This value indicates the value of lan delay field present in
                                     the Hello message received from the neighbor. ";
                            }

                            leaf lan-delay-present {
                                type boolean;
                                description
                                    "This value indicates whether the Hello message received from
                                     the neighbor contained the Lan Delay field.";
                            }

                            leaf generated-id {
                                type uint32;
                                description
                                    "This value indicates a randomly generated 32-bit value that is
                                     regenerated each time PIM forwarding is started or restarted on
                                     the interface, including when the router itself restarts.";
                            }

                            leaf override-interval {
                                type uint32;
                                units "milliseconds";
                                description
                                    "This value indicates the value of the override interval present
                                     in the Hello message.";
                            }

                            leaf up-time {
                                type uint32;
                                units "seconds";
                                description
                                    "This value indicates the time since this PIM neighbor (last)
                                     became a neighbor of the local router.";
                            }

                            leaf expiry-time {
                                type uint32;
                                units "seconds";
                                description
                                    "This value indicates the minimum time remaining before this
                                     PIM neighbor will be aged out.";
                            }

                            leaf hold-time {
                                type uint32;
                                units "seconds";
                                description
                                    "This value indicates the value of the hold time present in the
                                     Hello message.";
                            }

                            leaf join-attribute-support {
                                type boolean;
                                description
                                    "This value indicates whether the Hello Message received from
                                     the neighbor contained the Join Attribute field.";
                            }

                            list secondary-neighbor {
                                key "secondary-neighbor-address";
                                description "Enter the secondary-neighbor list instance";

                                leaf secondary-neighbor-address {
                                    type types-sros:ipv4-address;
                                    description
                                        "This value indicates the IPv4 address of the secondary PIM
                                         neighbor.";
                                }

                            } // list secondary-neighbor

                        } // list neighbor

                        list sg {
                            key "group-address source-address";
                            description "Enter the sg list instance";

                            leaf group-address {
                                type types-sros:ipv4-address;
                                description "The multicast group address of the entry.";
                            }

                            leaf source-address {
                                type types-sros:ipv4-address;
                                description "The source address of the multicast sender.";
                            }

                            leaf up-time {
                                type uint32;
                                units "seconds";
                                description "The time since this source group entry got created.";
                            }

                            leaf join-prune-state {
                                type types-pim:join-prune-state;
                                description
                                    "The Join Prune state for this entry on the interface.

                                     PIM Join or Prune messages are sent by the downstream routers
                                     towards the RPF' neighbor.";
                            }

                            leaf join-prune-timer {
                                type uint32;
                                units "seconds";
                                description
                                    "The time remaining before the router transitions the value of
                                     join-prune-state to 'no-info'.

                                     The timer is started or restarted when a valid Join message is
                                     received. If the value of this object is zero and
                                     join-prune-state is 'join' state, it means that the
                                     downstream router sent a holdtime of '0xffff'. In this case,
                                     join-prune-state will not transition until an appropriate
                                     cancelling of Join or Prune message is received.";
                            }

                            leaf prune-pending-timer {
                                type uint32;
                                units "seconds";
                                description
                                    "The time remaining before the router transitions the value of
                                     join-prune-state to 'no-info'.

                                     The timer is set when the PIM Prune message is received.";
                            }

                            leaf join-prune-rpt-state {
                                type types-pim:join-prune-state;
                                description
                                    "The Join Prune Rpt state for this entry on the interface.

                                     PIM Join or Prune messages are sent by the downstream routers towards the
                                     RPF' neighbor. (S,G,rpt) state is a result of receiving (S,G, rpt) JP message
                                     from the downstream router on the RP tree.";
                            }

                            leaf join-prune-rpt-timer {
                                type uint32;
                                units "seconds";
                                description
                                    "The time remaining before the router transitions the value of
                                     join-prune-rpt-state to 'no-info'.

                                     The timer is started or restarted when a valid Join message is
                                     received. If the value of this object is zero and
                                     join-prune-rpt-state is in 'join' state, it means that the
                                     downstream router sent a holdtime of '0xffff'. In this case,
                                     join-prune-rpt-state will not transition until an appropriate
                                     cancelling of Join or Prune message is received from the
                                     downstream router.";
                            }

                            leaf join-prune-rpt-pending-timer {
                                type uint32;
                                units "seconds";
                                description
                                    "The time remaining before the router transitions the value of
                                     join-prune-rpt-state to 'no-info'.

                                     The timer is set when the (S,G,rpt) PIM Prune message is received.";
                            }

                        } // list sg

                    } // container ipv4

                    container ipv6 {
                        description "Enter the ipv6 context";

                        leaf oper-state {
                            type types-sros:oper-state;
                            description
                                "The value of the this object indicates the operational
                                 state of PIM for this interface.";
                        }

                        leaf up-time {
                            type uint32;
                            units "seconds";
                            description "The time since this interface became operational.";
                        }

                        leaf group-count {
                            type uint32;
                            description
                                "The number of multicast groups which currently have this
                                 interface as an outgoing interface.";
                        }

                        leaf maximum-groups-until-now {
                            type uint32;
                            description "The highest value that 'group-count' had till now.";
                        }

                        leaf pseudo-wire-forwarder {
                            type boolean;
                            description
                                "Whether this interface is the forwarding interface
                                 of a pair of redundant pseudo-wire ports.";
                        }

                        container statistics {
                            description "Enter the statistics context";

                            leaf rx-packets {
                                type yang:counter32;
                                description "The number of multicast data packets received on this interface.";
                            }

                            leaf rx-hellos {
                                type yang:counter32;
                                description "The number of PIM hello messages received on this interface.";
                            }

                            leaf rx-join-prunes {
                                type yang:counter32;
                                description
                                    "The number of PIM
                                     Join Prune messages received on this interface.";
                            }

                            leaf tx-packets {
                                type yang:counter32;
                                description "The number of multicast data packets transmitted on this interface.";
                            }

                            leaf tx-join-prunes {
                                type yang:counter32;
                                description
                                    "The number of PIM
                                     Join Prune messages transmitted on this interface.";
                            }

                            leaf rx-hellos-dropped {
                                type yang:counter32;
                                description
                                    "The number of PIM Hello messages which were received on this interface but were
                                     dropped.";
                            }

                            leaf rx-neighbor-unknown {
                                type yang:counter32;
                                description
                                    "The number of PIM messages (other than Hello messages) which were received on this
                                     interface and were rejected because the adjacency with the neighbor
                                     router was not already established.";
                            }

                            leaf rx-bad-checksum-discard {
                                type yang:counter32;
                                description
                                    "The number of PIM messages received on this interface which were discarded because
                                     of bad checksum.";
                            }

                            leaf rx-bad-version-discard {
                                type yang:counter32;
                                description "The number of PIM messages with bad versions received on this interface.";
                            }

                            leaf rx-bad-encodings {
                                type yang:counter32;
                                description "The number of PIM messages with bad encodings received on this interface.";
                            }

                            leaf join-policy-drops {
                                type yang:counter32;
                                description
                                    "The number of times the join policy match resulted in dropping PIM Join-Prune
                                     Message or one of the source group contained in the message.";
                            }

                            leaf rx-join-prune-errors {
                                type yang:counter32;
                                description
                                    "The number of errors while processing Join-Prune messages received on this
                                     interface.";
                            }

                        } // container statistics

                        list neighbor {
                            key "neighbor-address";
                            description "Enter the neighbor list instance";

                            leaf neighbor-address {
                                type types-sros:ipv6-address;
                                description "This value indicates the IPv6 address of the PIM neighbor.";
                            }

                            leaf dr-priority {
                                type uint32;
                                description
                                    "This value indicates neighbor's DR priority which is received
                                     in the hello message. If the Hello Message did not contain
                                     the DR priority field, the value of priority will be '1'.";
                            }

                            leaf dr-priority-present {
                                type boolean;
                                description
                                    "This value of indicates whether the DR priority field was present
                                     in the Hello message received from the PIM neighbor.";
                            }

                            leaf tracking-support {
                                type boolean;
                                description
                                    "This value indicates whether the T bit in the LAN Prune Delay
                                     option was present in the Hello message. This indicates the
                                     neighbor's capability to disable Join message suppression.";
                            }

                            leaf lan-delay {
                                type uint32;
                                units "milliseconds";
                                description
                                    "This value indicates the value of lan delay field present in
                                     the Hello message received from the neighbor. ";
                            }

                            leaf lan-delay-present {
                                type boolean;
                                description
                                    "This value indicates whether the Hello message received from
                                     the neighbor contained the Lan Delay field.";
                            }

                            leaf generated-id {
                                type uint32;
                                description
                                    "This value indicates a randomly generated 32-bit value that is
                                     regenerated each time PIM forwarding is started or restarted on
                                     the interface, including when the router itself restarts.";
                            }

                            leaf override-interval {
                                type uint32;
                                units "milliseconds";
                                description
                                    "This value indicates the value of the override interval present
                                     in the Hello message.";
                            }

                            leaf up-time {
                                type uint32;
                                units "seconds";
                                description
                                    "This value indicates the time since this PIM neighbor (last)
                                     became a neighbor of the local router.";
                            }

                            leaf expiry-time {
                                type uint32;
                                units "seconds";
                                description
                                    "This value indicates the minimum time remaining before this
                                     PIM neighbor will be aged out.";
                            }

                            leaf hold-time {
                                type uint32;
                                units "seconds";
                                description
                                    "This value indicates the value of the hold time present in the
                                     Hello message.";
                            }

                            leaf join-attribute-support {
                                type boolean;
                                description
                                    "This value indicates whether the Hello Message received from
                                     the neighbor contained the Join Attribute field.";
                            }

                            list secondary-neighbor {
                                key "secondary-neighbor-address";
                                description "Enter the secondary-neighbor list instance";

                                leaf secondary-neighbor-address {
                                    type types-sros:ipv6-address;
                                    description
                                        "This value indicates the IPv6 address of the secondary PIM
                                         neighbor.";
                                }

                            } // list secondary-neighbor

                        } // list neighbor

                        list sg {
                            key "group-address source-address";
                            description "Enter the sg list instance";

                            leaf group-address {
                                type types-sros:ipv6-address;
                                description "The multicast group address of the entry.";
                            }

                            leaf source-address {
                                type types-sros:ipv6-address;
                                description "The source address of the multicast sender.";
                            }

                            leaf up-time {
                                type uint32;
                                units "seconds";
                                description "The time since this source group entry got created.";
                            }

                            leaf join-prune-state {
                                type types-pim:join-prune-state;
                                description
                                    "The Join Prune state for this entry on the interface.

                                     PIM Join or Prune messages are sent by the downstream routers
                                     towards the RPF' neighbor.";
                            }

                            leaf join-prune-timer {
                                type uint32;
                                units "seconds";
                                description
                                    "The time remaining before the router transitions the value of
                                     join-prune-state to 'no-info'.

                                     The timer is started or restarted when a valid Join message is
                                     received. If the value of this object is zero and
                                     join-prune-state is 'join' state, it means that the
                                     downstream router sent a holdtime of '0xffff'. In this case,
                                     join-prune-state will not transition until an appropriate
                                     cancelling of Join or Prune message is received.";
                            }

                            leaf prune-pending-timer {
                                type uint32;
                                units "seconds";
                                description
                                    "The time remaining before the router transitions the value of
                                     join-prune-state to 'no-info'.

                                     The timer is set when the PIM Prune message is received.";
                            }

                            leaf join-prune-rpt-state {
                                type types-pim:join-prune-state;
                                description
                                    "The Join Prune Rpt state for this entry on the interface.

                                     PIM Join or Prune messages are sent by the downstream routers towards the
                                     RPF' neighbor. (S,G,rpt) state is a result of receiving (S,G, rpt) JP message
                                     from the downstream router on the RP tree.";
                            }

                            leaf join-prune-rpt-timer {
                                type uint32;
                                units "seconds";
                                description
                                    "The time remaining before the router transitions the value of
                                     join-prune-rpt-state to 'no-info'.

                                     The timer is started or restarted when a valid Join message is
                                     received. If the value of this object is zero and
                                     join-prune-rpt-state is in 'join' state, it means that the
                                     downstream router sent a holdtime of '0xffff'. In this case,
                                     join-prune-rpt-state will not transition until an appropriate
                                     cancelling of Join or Prune message is received from the
                                     downstream router.";
                            }

                            leaf join-prune-rpt-pending-timer {
                                type uint32;
                                units "seconds";
                                description
                                    "The time remaining before the router transitions the value of
                                     join-prune-rpt-state to 'no-info'.

                                     The timer is set when the (S,G,rpt) PIM Prune message is received.";
                            }

                        } // list sg

                    } // container ipv6

                } // container pim-snooping

                container stp {
                    description "Enter the stp context";

                    leaf port-state {
                        type enumeration {
                            enum disabled                       { value 1; }
                            enum blocking                       { value 2; }
                            enum listening                      { value 3; }
                            enum learning                       { value 4; }
                            enum forwarding                     { value 5; }
                            enum broken                         { value 6; }
                            enum discarding                     { value 7; }
                        }
                        description "The PIP uplink's current state";
                    }

                    leaf designated-bridge {
                        type types-sros:bridge-id;
                        description "The identifier of the designated bridge of the PIP uplink";
                    }

                    leaf designated-port {
                        type int32;
                        description "The identifier of the port on the designated bridge";
                    }

                    leaf forward-transitions {
                        type uint32;
                        description "The number of times the port has transitioned from learned state to forwarding state";
                    }

                    leaf config-bpdus-received {
                        type uint32;
                        description "The number of configuration BPDUs received on this PIP uplink";
                    }

                    leaf tcn-bpdus-received {
                        type uint32;
                        description "The number of topology change notification BPDUs received on this PIP uplink";
                    }

                    leaf bad-bpdus-received {
                        type uint32;
                        description "The number of bad BPDUs received on this PIP uplink";
                    }

                    leaf config-bpdus-transmitted {
                        type uint32;
                        description "The number of configuration BPDUs transmitted on this PIP uplink";
                    }

                    leaf tcn-bpdus-transmitted {
                        type uint32;
                        description "The number of topology change notification BPDUs transmitted on this PIP uplink";
                    }

                    leaf oper-bpdus-encap {
                        type enumeration {
                            enum dynamic                        { value 1; }
                            enum dot1d                          { value 2; }
                            enum pvst                           { value 3; }
                        }
                        description "The operatiing encsapsulation type used on BPDUs sent and received on this SAP";
                    }

                    leaf oper-edge {
                        type boolean;
                        description "Oper edge";
                    }

                    leaf port-role {
                        type enumeration {
                            enum master                         { value 0; }
                            enum root                           { value 1; }
                            enum designated                     { value 2; }
                            enum alternate                      { value 3; }
                            enum backup                         { value 4; }
                            enum disabled                       { value 5; }
                        }
                        description "The current role of the PIP uplink";
                    }

                    leaf oper-protocol {
                        type enumeration {
                            enum not-applicable                 { value 0; }
                            enum stp                            { value 1; }
                            enum rstp                           { value 2; }
                            enum mstp                           { value 3; }
                        }
                        description "The protocol running on this PIP uplink";
                    }

                    leaf rst-bpdus-received {
                        type uint32;
                        description "The number of RST BPDUs recieved on this PIP uplink";
                    }

                    leaf rst-bpdus-transmitted {
                        type uint32;
                        description "The number of RST BPDUs transmitted on this PIP uplink";
                    }

                    leaf exception {
                        type enumeration {
                            enum none                           { value 1; }
                            enum one-way-communication          { value 2; }
                            enum downstream-loop-detected       { value 3; }
                        }
                        description "Indicates if an stp exception is present on the pip";
                    }

                    leaf inside-region {
                        type boolean;
                        description "Indicates if the network connected to the PIP is in the same MST region";
                    }

                    leaf mst-bpdus-received {
                        type uint32;
                        description "The number of MST BPDUs received on this PIP uplink";
                    }

                    leaf mst-bpdus-transmitted {
                        type uint32;
                        description "The number of MST BPDUs transmitted on this PIP uplink";
                    }

                    leaf receive-designated-bridge {
                        type types-sros:bridge-id;
                        description "The identifier of the designated bridge of the PIP uplink";
                    }

                    leaf root-guard-violation {
                        type boolean;
                        description "Indicates if there is a root-guard violation.";
                    }

                    list mst-instance {
                        key "mst-inst-number";
                        description "Enter the mst-instance list instance";

                        leaf mst-inst-number {
                            type uint32 {
                                range "1..4094";
                            }
                            description "Multiple Spanning Tree Instance number";
                        }

                        leaf port-role {
                            type enumeration {
                                enum master                         { value 0; }
                                enum root                           { value 1; }
                                enum designated                     { value 2; }
                                enum alternate                      { value 3; }
                                enum backup                         { value 4; }
                                enum disabled                       { value 5; }
                            }
                            description "The current role of the sap in the MSTI as defined by the Spanning Tree Protocol.";
                        }

                        leaf port-state {
                            type enumeration {
                                enum disabled                       { value 1; }
                                enum blocking                       { value 2; }
                                enum listening                      { value 3; }
                                enum learning                       { value 4; }
                                enum forwarding                     { value 5; }
                                enum broken                         { value 6; }
                                enum discarding                     { value 7; }
                            }
                            description
                                "The port's current state as defined by application of the
                                 Spanning Tree Protocol.";
                        }

                        leaf designated-bridge {
                            type binary {
                                length "8";
                            }
                            description
                                "The bridge identifier of the bridge which this port considers
                                 to be the designated bridge for this port's segment for this MSTI.";
                        }

                        leaf designated-port {
                            type int32;
                            description
                                "The port identifier of the port on the Designated Bridge
                                 for this port's segment for this MSTI.";
                        }

                    } // list mst-instance

                } // container stp

                container l2pt {
                    description "Enter the l2pt context";

                    container stp {
                        description "Enter the stp context";

                        leaf config-bpdus-received {
                            type uint32;
                            description "The number of L2PT configuration BPDUs received on this SAP";
                        }

                        leaf config-bpdus-transmitted {
                            type uint32;
                            description "The number of L2PT configuration BPDUs transmitted on this SAP";
                        }

                        leaf rst-bpdus-received {
                            type uint32;
                            description "The number of L2PT RST BPDUs received on this SAP";
                        }

                        leaf rst-bpdus-transmitted {
                            type uint32;
                            description "The number of L2PT RST configuration BPDUs transmitted on this SAP";
                        }

                        leaf tcn-bpdus-received {
                            type uint32;
                            description "The number of L2PT topology change notification BPDUs received on this SAP";
                        }

                        leaf tcn-bpdus-transmitted {
                            type uint32;
                            description "The number of L2PT topology change notification BPDUs transmitted on this SAP";
                        }

                        container encap {
                            description "Enter the encap context";

                            leaf config-bpdus-received {
                                type uint32;
                                description "The number of L2PT encapsulated configuration BPDUs received on this SAP";
                            }

                            leaf config-bpdus-transmitted {
                                type uint32;
                                description "The number of L2PT encapsulated configuration BPDUs transmitted on this SAP";
                            }

                            leaf rst-bpdus-received {
                                type uint32;
                                description "The number of L2PT encapsulated RST BPDUs received on this SAP";
                            }

                            leaf rst-bpdus-transmitted {
                                type uint32;
                                description "The number of L2PT encapsulated RST configuration BPDUs transmitted on this SAP";
                            }

                            leaf tcn-bpdus-received {
                                type uint32;
                                description "The number of L2PT encapsulated topology change notification BPDUs received on this SAP";
                            }

                            leaf tcn-bpdus-transmitted {
                                type uint32;
                                description "The number of L2PT encapsulated topology change notification BPDUs transmitted on this SAP";
                            }

                        } // container encap

                    } // container stp

                } // container l2pt

                container fdb {
                    description "Enter the fdb context";

                    leaf oper-auto-learn-mac-protect {
                        type boolean;
                        description "Automatic marking of MACs as protected";
                    }

                    leaf oper-discard-unprotected-dest-mac {
                        type boolean;
                        description "Unprotected dest MAC restriction";
                    }

                    leaf oper-auto-learn-mac-protect-exclude-list {
                        type types-sros:named-item-or-empty;
                        description "Operational mac protect exclusion list";
                    }

                    leaf protected-mac-address-received {
                        type yang:mac-address;
                        description "The protected MAC address received";
                    }

                    leaf protected-mac-address-received-last-changed {
                        type yang:date-and-time;
                        description "Timestamp when the protected MAC address was receieved";
                    }

                    leaf pbb-protected-mac-address-received {
                        type yang:mac-address;
                        description "The PBB protected MAC address received";
                    }

                    leaf pbb-protected-mac-address-received-last-changed {
                        type yang:date-and-time;
                        description "Timestamp when the PBB protected MAC address was receieved";
                    }

                    leaf table-high-utilization {
                        type boolean;
                        description "Set to 'true' when the FDB table utilization reaches the high watermark and 'false' when it reaches the low watermark.";
                    }

                    leaf non-blockable-move-rate-exceeded-mac-address {
                        type yang:mac-address;
                        description "The non-blocking MAC address of the SAP that exceeds the maximum move rate";
                    }

                    leaf non-blockable-move-rate-exceeded-mac-address-last-changed {
                        type yang:date-and-time;
                        description "Timestamp when the non-blocking MAC addresses was detected";
                    }

                    leaf mac-move-rate-exceeded-mac-address {
                        type yang:mac-address;
                        description "The MAC address of the SAP that exceeds the maximum move rate";
                    }

                    leaf mac-move-rate-exceeded-mac-address-last-changed {
                        type yang:date-and-time;
                        description "Timestamp when the MAC addresses was detected";
                    }

                    container mac-move {
                        description "Enter the mac-move context";

                        leaf remaining-down-time {
                            type union {
                                type uint32 {
                                    range "1..65534";
                                }
                                type enumeration {
                                    enum never                          { value 0; }
                                    enum indefinite                     { value 65535; }
                                }
                            }
                            units "seconds";
                            description
                                "The time remaining until the relearn-limit-exceeded oper-flag is cleared.
                                 When the value is 'indefinite', this flag will not be cleared automatically.
                                 Relearn-limit-exceeded oper-flag is set when sap is brought down 
                                 when mac-move max-rate is exceeded.";
                        }

                        leaf remaining-retry-reset-time {
                            type union {
                                type uint32 {
                                    range "1..4294967295";
                                }
                                type enumeration {
                                    enum never                          { value 0; }
                                }
                            }
                            units "seconds";
                            description
                                "The time remaining to reset the mac-move retries-left
                                 when the oper-state of sap is up.";
                        }

                        leaf rate-exceed-times-left {
                            type union {
                                type uint32 {
                                    range "1..4294967294";
                                }
                                type enumeration {
                                    enum unlimited                      { value -1; }
                                    enum none                           { value 0; }
                                }
                            }
                            description
                                "Counts down the number of times this SAP can exceed the
                                 VPLS mac-move max-rate and still be automatically
                                 brought up.";
                        }

                    } // container mac-move

                    container protected-src-mac-violation {
                        description "Enter the protected-src-mac-violation context";

                        leaf oper-state {
                            type boolean;
                            description "Operational state of the protected-source MAC violation feature.";
                        }

                        leaf oper-action {
                            type enumeration {
                                enum oper-down                      { value 1; }
                                enum alarm-only                     { value 2; }
                                enum discard-frame                  { value 3; }
                            }
                            description "Operation state of the protected-source MAC violation action.";
                        }

                    } // container protected-src-mac-violation

                    container statistics {
                        description "Enter the statistics context";

                        leaf total {
                            type int32;
                            description "Number of entries allocated in the FDB ";
                        }

                        leaf static {
                            type int32;
                            description "Number of static entries in the FDB";
                        }

                        leaf learned {
                            type int32;
                            description "Number of learned entries in the FDB";
                        }

                        leaf oam {
                            type int32;
                            description "Number of OAM entries in the FDB";
                        }

                        leaf conditional-static {
                            type int32;
                            description "Number of conditional static entries in the FDB";
                        }

                        leaf dhcp {
                            type int32;
                            description "Number of dhcp-learned entries in the FDB";
                        }

                        leaf host {
                            type int32;
                            description "Number of host-learned entries in the FDB";
                        }

                        leaf interface {
                            type int32;
                            description "Number of interface entries in the FDB";
                        }

                        leaf bgp-evpn {
                            type int32;
                            description "Number of bgp-evpn entries in the FDB";
                        }

                        leaf evpn-static {
                            type int32;
                            description "Number of evpn static entries in the FDB";
                        }

                        leaf spb {
                            type int32;
                            description "Number of SPB entries in the FDB";
                        }

                        leaf eth-cfm {
                            type int32;
                            description "Number of eth-cfm entries in FDB";
                        }

                    } // container statistics

                } // container fdb

                container mrp {
                    description "Enter the mrp context";


                } // container mrp

                container l2tpv3-session {
                    description "Enter the l2tpv3-session context";

                    leaf oper-state {
                        type types-sros:oper-state;
                        description "Operational status of this entry.";
                    }

                    leaf tunnel-status {
                        type enumeration {
                            enum down                           { value 1; }
                            enum inprogress                     { value 2; }
                            enum connected                      { value 3; }
                        }
                        description "State of the L2tpv3 tunnel.";
                    }

                    leaf oper-flags {
                        type bits {
                            bit sap-down                       { position 0; }
                            bit router-unreachable             { position 1; }
                            bit admin-down                     { position 2; }
                            bit tunnel-not-unique              { position 3; }
                        }
                        description "Reason why the L2tpv3 tunnel is operationally down.";
                    }

                    leaf last-oper-changed {
                        type yang:date-and-time;
                        description "Uptime at the time of the last operational status change of this l2tpv3 tunnel.";
                    }

                } // container l2tpv3-session

                container pppoe {
                    description "Enter the pppoe context";

                    container intermediate-agent {
                        description "Enter the intermediate-agent context";

                        container statistics {
                            description "Enter the statistics context";

                            container rx {
                                description "Enter the rx context";

                                leaf padi {
                                    type uint32;
                                    description "Count of PADI (PPPoE Active Discovery Initiation) packets received on this SAP.";
                                }

                                leaf padr {
                                    type uint32;
                                    description "Count of PADR (PPPoE Active Discovery Request) packets received on this SAP.";
                                }

                                leaf padt {
                                    type uint32;
                                    description "Count of PADT (PPPoE Active Discovery Terminate) packets received on this SAP.";
                                }

                                leaf invalid-version {
                                    type uint32;
                                    description "Count of PPPoE packets received with an invalid version field.";
                                }

                                leaf invalid-type {
                                    type uint32;
                                    description "Count of PPPoE packets received with an invalid type field.";
                                }

                                leaf invalid-code {
                                    type uint32;
                                    description "Count of PPPoE packets received with an invalid code field.";
                                }

                                leaf invalid-session {
                                    type uint32;
                                    description "Count of PPPoE packets received with an invalid session-id field.";
                                }

                                leaf invalid-len {
                                    type uint32;
                                    description "Count of PPPoE packets received with an invalid length field.";
                                }

                                leaf invalid-tags {
                                    type uint32;
                                    description "Count of PPPoE Active Discovery packets received with invalid tags.";
                                }

                                leaf invalid-mac {
                                    type uint32;
                                    description "Count of PPPoE packets received with an invalid MAC address.";
                                }

                                leaf mtu-exceeded {
                                    type uint32;
                                    description "Count of packets dropped on this SAP because the generated packet length is too long.";
                                }

                                leaf tag-too-long {
                                    type uint32;
                                    description "Count of packets dropped on this SAP because a generated tag is too long.";
                                }

                            } // container rx

                            container tx {
                                description "Enter the tx context";

                                leaf pado-spoofed {
                                    type uint32;
                                    description "Count of spoofed PADO (PPPoE Active Discovery Offer) packets transmitted on this SAP.";
                                }

                                leaf pads-spoofed {
                                    type uint32;
                                    description "Count of spoofed PADS (PPPoE Active Discovery Session) packets transmitted on this SAP.";
                                }

                            } // container tx

                        } // container statistics

                    } // container intermediate-agent

                } // container pppoe

                container spb {
                    description "Enter the spb context";

                    leaf interface {
                        type types-sros:interface-name;
                        description "Interface assigned for SPB";
                    }

                    list level {
                        key "id";
                        description "Enter the level list instance";

                        leaf id {
                            type int32 {
                                range "1";
                            }
                            description "Level identifier";
                        }

                        leaf oper-metric {
                            type uint32;
                            description "Operational metric";
                        }

                    } // list level

                    list adjacency {
                        key "adjacency-index";
                        description "Enter the adjacency list instance";

                        leaf adjacency-index {
                            type int32 {
                                range "1..2000000000";
                            }
                            description
                                "A unique value identifying the IS adjacency from all
                                 other such adjacencies on this circuit. This value is
                                 assigned by the system when the adjacency is created
                                 automatically.";
                        }

                        leaf oper-state {
                            type enumeration {
                                enum initializing                   { value 1; }
                                enum up                             { value 2; }
                                enum failed                         { value 3; }
                                enum down                           { value 4; }
                            }
                            description "The state of the adjacency";
                        }

                        leaf usage {
                            type enumeration {
                                enum undefined                      { value 1; }
                                enum level1                         { value 2; }
                                enum level2                         { value 3; }
                                enum level1and2                     { value 4; }
                            }
                            description
                                "An adjacency of type level1 is used for level 1
                                 traffic only. An adjacency of type level2 is used
                                 for level 2 traffic only. An adjacency of type level1and2
                                 is used for both level 1 and level 2 traffic. There
                                 may be two adjacencies (of types level1 and level2)
                                 between the same pair of Intermediate Systems.";
                        }

                        leaf hold-timer {
                            type int32 {
                                range "1..65535";
                            }
                            units "seconds";
                            description
                                "The holding time for this adjacency updated from
                                 received IIH PDUs.";
                        }

                        leaf uptime {
                            type int32;
                            units "seconds";
                            description
                                "If the adjacency is up, the amount of time in seconds
                                 since this adjacency entered state 'up'.  If the adjacency
                                 is not up, the number of seconds since the adjacency was
                                 up, or since the system started, if the adjacency has
                                 never been up.

                                 Note: This can be implemented as start time less
                                 the current time.";
                        }

                        leaf expires-in {
                            type int32 {
                                range "0..65535";
                            }
                            units "seconds";
                            description "The value indicates the time in which the adjacency will expire if no hello packets are received.";
                        }

                        leaf level {
                            type enumeration {
                                enum level1                         { value 1; }
                                enum level2                         { value 2; }
                                enum level1-l2                      { value 3; }
                                enum unknown                        { value 4; }
                            }
                            description "The value indicates the circuit type of the adjacency as advertised.";
                        }

                        container restart {
                            description "Enter the restart context";

                            leaf support {
                                type boolean;
                                description
                                    "The value indicates whether adjacency supports ISIS graceful restart.

                                     If support has a value of 'true' the adjacency
                                     supports graceful restart.";
                            }

                            leaf status {
                                type enumeration {
                                    enum not-helping                    { value 1; }
                                    enum restarting                     { value 2; }
                                    enum restart-complete               { value 3; }
                                    enum helping                        { value 4; }
                                    enum aborted                        { value 5; }
                                }
                                description "The value indicates the graceful restart status of the adjacency.";
                            }

                            leaf suppressed {
                                type boolean;
                                description
                                    "The value indicates if the adjacency has requested this router to suppress advertisement of
                                     the adjacency in this router's LSPs.

                                     If suppressed has a value of 'true' the adjacency
                                     has requested to suppress advertisement of the LSPs.";
                            }

                            leaf num-restarts {
                                type uint32;
                                description "The value indicates the number of times the adjacency has attempted restart.";
                            }

                            leaf last-restart {
                                type yang:date-and-time;
                                description "The value indicates the last time the adjacency attempted restart.";
                            }

                        } // container restart

                        container neighbor {
                            description "Enter the neighbor context";

                            leaf snpa-address {
                                type types-isis:snpa-address;
                                description "The SNPA address of the neighboring system.";
                            }

                            leaf system-type {
                                type enumeration {
                                    enum l1-is                          { value 1; }
                                    enum l2-is                          { value 2; }
                                    enum l1-l2-is                       { value 3; }
                                    enum unknown                        { value 4; }
                                }
                                description "The type of the neighboring system.";
                            }

                            leaf system-id {
                                type string {
                                    length "0..24";
                                }
                                description
                                    "The system ID and 4 byte circuit ID of the
                                     neighboring Intermediate System set from
                                     the source ID field of the Three-Way-Handshake
                                     information from the neighbor's IIH PDUs.";
                            }

                            leaf priority {
                                type int32 {
                                    range "0..127";
                                }
                                description
                                    "Priority of the neighboring Intermediate System for
                                     becoming the LAN Level 1 Designated Intermediate System
                                     if the value of isisISAdjNeighSysType is
                                     L1IntermediateSystem or LAN Level 2 Designated
                                     Intermediate System if the value of
                                     isisISAdjNeighSysType is L2IntermediateSystem.";
                            }

                            leaf ipv4 {
                                type types-sros:ipv4-address;
                                description "The value indicates the ip-address of the neighbor with which adjacency is formed.";
                            }

                            leaf ipv6 {
                                type types-sros:ipv6-address;
                                description
                                    "The value indicates the IP address of the neighbor with which an IPv6-adjacency is formed
                                     this will always be an IPv6 address.";
                            }

                        } // container neighbor

                        container multi-topology {
                            description "Enter the multi-topology context";

                            leaf enabled {
                                type boolean;
                                description
                                    "The value indicates if the ISIS multi-topology protocol is supported on the neighbor.

                                     If the value is 'true', ISIS multi-topology
                                     protocol is enabled on the neighbor.";
                            }

                            container id0 {
                                description "Enter the id0 context";

                                leaf enabled {
                                    type boolean;
                                    description
                                        "The value indicates if the MT x IPvx topology is supported on the neighbor.

                                         If the value of enable is 'true', MT x IPvx topology is
                                         supported on the neighbor.";
                                }

                                leaf bfd-required {
                                    type boolean;
                                    description
                                        "The value indicates if BFD session is required for this Multi Topology before bringing the
                                         adjacency to FULL state, as described in RFC6213.";
                                }

                                leaf bfd-usable {
                                    type boolean;
                                    description
                                        "The value indicates if BFD session for this Multi Topology is usable, that is either not
                                         required or in state UP, as described in RFC6213.";
                                }

                            } // container id0

                            container id2 {
                                description "Enter the id2 context";

                                leaf enabled {
                                    type boolean;
                                    description
                                        "The value indicates if the MT x IPvx topology is supported on the neighbor.

                                         If the value of enable is 'true', MT x IPvx topology is
                                         supported on the neighbor.";
                                }

                                leaf bfd-required {
                                    type boolean;
                                    description
                                        "The value indicates if BFD session is required for this Multi Topology before bringing the
                                         adjacency to FULL state, as described in RFC6213.";
                                }

                                leaf bfd-usable {
                                    type boolean;
                                    description
                                        "The value indicates if BFD session for this Multi Topology is usable, that is either not
                                         required or in state UP, as described in RFC6213.";
                                }

                            } // container id2

                            container id3 {
                                description "Enter the id3 context";

                                leaf enabled {
                                    type boolean;
                                    description
                                        "The value indicates if the MT x IPvx topology is supported on the neighbor.

                                         If the value of enable is 'true', MT x IPvx topology is
                                         supported on the neighbor.";
                                }

                                leaf bfd-required {
                                    type boolean;
                                    description
                                        "The value indicates if BFD session is required for this Multi Topology before bringing the
                                         adjacency to FULL state, as described in RFC6213.";
                                }

                                leaf bfd-usable {
                                    type boolean;
                                    description
                                        "The value indicates if BFD session for this Multi Topology is usable, that is either not
                                         required or in state UP, as described in RFC6213.";
                                }

                            } // container id3

                            container id4 {
                                description "Enter the id4 context";

                                leaf enabled {
                                    type boolean;
                                    description
                                        "The value indicates if the MT x IPvx topology is supported on the neighbor.

                                         If the value of enable is 'true', MT x IPvx topology is
                                         supported on the neighbor.";
                                }

                                leaf bfd-required {
                                    type boolean;
                                    description
                                        "The value indicates if BFD session is required for this Multi Topology before bringing the
                                         adjacency to FULL state, as described in RFC6213.";
                                }

                                leaf bfd-usable {
                                    type boolean;
                                    description
                                        "The value indicates if BFD session for this Multi Topology is usable, that is either not
                                         required or in state UP, as described in RFC6213.";
                                }

                            } // container id4

                        } // container multi-topology

                    } // list adjacency

                } // container spb

                container ethernet-segment {
                    description "Enter the ethernet-segment context";

                    leaf name {
                        type types-sros:named-item-or-empty;
                        description "Ethernet segment name.";
                    }

                    leaf oper-state {
                        type types-services:evpn-mh-es-status;
                        description "Operational status of the ethernet-segment.";
                    }

                } // container ethernet-segment

                container mvpls {
                    description "Enter the mvpls context";

                    leaf prune-state {
                        type types-services:mvpls-prune-state;
                        description
                            "The mVPLS prune state of the SAP. The leaf will be set to
                             not-applicable if the SAP is not managed by a mVPLS. If
                             the SAP is managed the state reflects whether or not
                             the SAP is pruned by the STP instance running in the
                             MVPLS instance.";
                    }

                    leaf service {
                        type types-sros:named-item-or-empty;
                        description
                            "Service name of the service where the STP instance is
                             running that is managing this SAP. This leaf is
                             only valid if mvpls-prune-state is different from
                             not-applicable.";
                    }

                    leaf sap {
                        type types-sros:sap;
                        description
                            "SAP in the MVPLS instance specified in mgmt-service
                             that is controlling this SAP.
                             This leaf is only valid if mvpls-prune-state is
                             different from not-applicable.";
                    }

                    leaf msti {
                        type types-services:msti-instance-or-zero;
                        description
                            "MST-instance in the MVPLS instance specified in
                             mgmt-service that is controlling this SAP. A
                             value of 0 indicates the CIST.
                             This leaf is only valid if mvpls-prune-state is
                             different from not-applicable.";
                    }

                } // container mvpls

                container data-instantiating-sap {
                    description "Enter the data-instantiating-sap context";

                    leaf status {
                        type types-services:sap-instance-status;
                        description
                            "Status of the SAP which is instantiating other SAPs controlled
                             by this SAP.
                             This leaf is valid for m-vpls services.";
                    }

                    leaf last-error {
                        type string;
                        description
                            "Last error encountered while instantiating SAPs controlled
                             by this SAP.
                             This leaf is valid for m-vpls services.";
                    }

                } // container data-instantiating-sap

                container topology-change-bit {
                    description "Enter the topology-change-bit context";

                    leaf in-bpdus {
                        type uint32;
                        description
                            "Number of BPDUs received on this SAP
                             with the Topology Change bit set.";
                    }

                    leaf out-bpdus {
                        type uint32;
                        description
                            "Number of BPDUs sent out this SAP
                             with the Topology Change bit set.";
                    }

                } // container topology-change-bit

                container distributed-cpu-protection {
                    description "Enter the distributed-cpu-protection context";

                    list static-policer {
                        key "name card fp-number";
                        description "Enter the static-policer list instance";

                        leaf name {
                            type types-sros:named-item;
                            description "Name of static policer.";
                        }

                        leaf card {
                            type types-card:iom-card-slot;
                            description "IOM card within a chassis in the system.";
                        }

                        leaf fp-number {
                            type uint32 {
                                range "1..12";
                            }
                            description "Forwarding plane within a specific IOM card in the system.";
                        }

                        leaf state {
                            type types-services:dist-cpu-prot-policer-state;
                            description "State of the policer configured on Distributed CPU Protection Policy.";
                        }

                        leaf exceed-count {
                            type uint64;
                            description
                                "Number of packets exceeding the policing parameters since the given
                                 policer was previously declared as conformant or newly instantiated.";
                        }

                        leaf hold-down-remain {
                            type types-services:dist-cpu-prot-action-duration;
                            units "seconds";
                            description "Remaining hold-down period for a given policer.";
                        }

                        leaf detection-time-remain {
                            type uint32;
                            units "seconds";
                            description "Detection time remaining for a given policer.";
                        }

                        leaf total-exceed-count {
                            type uint64;
                            description "Total number of packets exceeding the policing parametersi.";
                        }

                        leaf exit-conform-state-count {
                            type uint32;
                            description "Total number of transition of the policer to the exceed state.";
                        }

                    } // list static-policer

                    list local-monitor-policer {
                        key "name card fp-number";
                        description "Enter the local-monitor-policer list instance";

                        leaf name {
                            type types-sros:named-item;
                            description "Name of local-monitor policer.";
                        }

                        leaf card {
                            type types-card:iom-card-slot;
                            description "IOM card within a chassis in the system.";
                        }

                        leaf fp-number {
                            type uint32 {
                                range "1..12";
                            }
                            description "Forwarding plane within a specific IOM card in the system.";
                        }

                        leaf state {
                            type types-services:dist-cpu-prot-policer-state;
                            description "State of the policer configured on Distributed CPU Protection Policy.";
                        }

                        leaf exceed-count {
                            type uint64;
                            description
                                "Number of packets exceeding the policing parameters since the given
                                 policer was previously declared as conformant or newly instantiated.";
                        }

                        leaf all-dynamic-policer-allocation {
                            type boolean;
                            description "All dynamic-policers allocation status";
                        }

                        leaf total-exceed-count {
                            type uint64;
                            description "Total number of packets exceeding the policing parametersi.";
                        }

                        leaf exit-conform-state-count {
                            type uint32;
                            description "Total number of transition of the policer to the exceed state.";
                        }

                    } // list local-monitor-policer

                    list dynamic-policer {
                        key "protocol card fp-number";
                        description "Enter the dynamic-policer list instance";

                        leaf protocol {
                            type types-sros:dist-cpu-protection-protocol;
                            description "Dynamic policer protocol.";
                        }

                        leaf card {
                            type types-card:iom-card-slot;
                            description "IOM card within a chassis in the system.";
                        }

                        leaf fp-number {
                            type uint32 {
                                range "1..12";
                            }
                            description "Forwarding plane within a specific IOM card in the system.";
                        }

                        leaf state {
                            type types-services:dist-cpu-prot-policer-state;
                            description "State of the policer configured on Distributed CPU Protection Policy.";
                        }

                        leaf exceed-count {
                            type uint64;
                            description
                                "Number of packets exceeding the policing parameters since the given
                                 policer was previously declared as conformant or newly instantiated.";
                        }

                        leaf hold-down-remain {
                            type types-services:dist-cpu-prot-action-duration;
                            units "seconds";
                            description "Remaining hold-down period for a given policer.";
                        }

                        leaf detection-time-remain {
                            type uint32;
                            units "seconds";
                            description "Detection time remaining for a given policer.";
                        }

                        leaf dynamic-policer-allocation {
                            type boolean;
                            description "Dynamic-policer allocation status";
                        }

                        leaf total-exceed-count {
                            type uint64;
                            description "Total number of packets exceeding the policing parametersi.";
                        }

                        leaf exit-conform-state-count {
                            type uint32;
                            description "Total number of transition of the policer to the exceed state.";
                        }

                    } // list dynamic-policer

                } // container distributed-cpu-protection

                container msap {
                    description "Enter the msap context";

                    leaf capture-sap-id {
                        type types-sros:sap;
                        description "SAP identifier of the capture sap that created this MSAP";
                    }

                    leaf capture-service {
                        type types-services:service-name;
                        description "Service identifier of the capture sap that created this MSAP";
                    }

                    leaf msap-policy {
                        type types-sros:named-item;
                        description "The msap-policy used to create this MSAP";
                    }

                    leaf idle {
                        type boolean;
                        description "A managed SAP is considered idle when no hosts are associated with it.";
                    }

                    leaf sticky {
                        type boolean;
                        description "A sticky managed SAP will not be removed automatically.";
                    }

                } // container msap

                container arp-host {
                    description "Enter the arp-host context";

                    container statistics {
                        description "Enter the statistics context";

                        leaf last-cleared-time {
                            type yang:date-and-time;
                            description "The last time that these stats were cleared";
                        }

                        leaf hosts {
                            type yang:gauge32;
                            description "The actual number of ARP hosts on this SAP";
                        }

                        leaf triggers-received {
                            type yang:counter32;
                            description "The number of ARP triggers received on this SAP";
                        }

                        leaf error-triggers-dropped {
                            type yang:counter32;
                            description "ARP triggers that are dropped due to various error conditions";
                        }

                        leaf overload-triggers-dropped {
                            type yang:counter32;
                            description
                                "ARP triggers that are dropped because of too many outstanding
                                 requests";
                        }

                        leaf forced-verifications {
                            type yang:counter32;
                            description "The number of times a host connectivity verification was forced";
                        }

                        leaf hosts-created {
                            type yang:counter32;
                            description "The number of times an ARP host was created on this SAP";
                        }

                        leaf hosts-deleted {
                            type yang:counter32;
                            description "The number of times an ARP host was deleted on this SAP";
                        }

                        leaf hosts-updated {
                            type yang:counter32;
                            description "The number of times an ARP host was updated on this SAP";
                        }

                        leaf authentication-requests {
                            type yang:counter32;
                            description
                                "The number of times an authentication request was initiated
                                 by the system for an ARP host on this SAP";
                        }

                    } // container statistics

                } // container arp-host

                container dhcp {
                    description "Enter the dhcp context";

                    container lease-populate {
                        description "Enter the lease-populate context";

                        leaf current-lease-states {
                            type uint32 {
                                range "0..131071";
                            }
                            description "The number of DHCP lease states currently allocated on this interface.";
                        }

                    } // container lease-populate

                    container statistics {
                        description "Enter the statistics context";

                        container client-packets {
                            description "Enter the client-packets context";

                            leaf snooped {
                                type yang:counter32;
                                description "The number of DHCP client packets that have been snooped on this SAP.";
                            }

                            leaf forwarded {
                                type yang:counter32;
                                description "The number  of  DHCP  client  packets  that have been forwarded on this SAP.";
                            }

                            leaf dropped {
                                type yang:counter32;
                                description "The number  of  DHCP  client  packets  that have been dropped on this SAP.";
                            }

                            container proxied {
                                description "Enter the proxied context";

                                leaf radius {
                                    type yang:counter32;
                                    description
                                        "The number of DHCP client packets that have been proxied on this SAP
                                         based on data received from a RADIUS server.";
                                }

                                leaf lease-split {
                                    type yang:counter32;
                                    description
                                        "The number of DHCP client packets that have been proxied on this SAP
                                         based on lease state.";
                                }

                            } // container proxied

                        } // container client-packets

                        container server-packets {
                            description "Enter the server-packets context";

                            leaf snooped {
                                type yang:counter32;
                                description "The number of DHCP server packets that have been snooped on this SAP.";
                            }

                            leaf forwarded {
                                type yang:counter32;
                                description "The number  of  DHCP  server  packets  that have been forwarded on this SAP.";
                            }

                            leaf dropped {
                                type yang:counter32;
                                description "The number  of  DHCP  server  packets  that have been dropped on this SAP.";
                            }

                        } // container server-packets

                        container spoofed {
                            description "Enter the spoofed context";

                            leaf force-renews {
                                type yang:counter32;
                                description "The number of DHCP FORCERENEW messages spoofed on this SAP to the DHCP clients.";
                            }

                            leaf releases {
                                type yang:counter32;
                                description "The number of DHCP RELEASE messages spoofed on this SAP to the DHCP server.";
                            }

                        } // container spoofed

                    } // container statistics

                } // container dhcp

                container dhcp6 {
                    description "Enter the dhcp6 context";

                    container statistics {
                        description "Enter the statistics context";

                        container client-packets {
                            description "Enter the client-packets context";

                            leaf snooped {
                                type yang:counter32;
                                description "The number of DHCP client packets that have been snooped on this SAP.";
                            }

                            leaf forwarded {
                                type yang:counter32;
                                description "The number  of  DHCP  client  packets  that have been forwarded on this SAP.";
                            }

                            leaf dropped {
                                type yang:counter32;
                                description "The number  of  DHCP  client  packets  that have been dropped on this SAP.";
                            }

                        } // container client-packets

                        container server-packets {
                            description "Enter the server-packets context";

                            leaf snooped {
                                type yang:counter32;
                                description "The number of DHCP server packets that have been snooped on this SAP.";
                            }

                            leaf forwarded {
                                type yang:counter32;
                                description "The number  of  DHCP  server  packets  that have been forwarded on this SAP.";
                            }

                            leaf dropped {
                                type yang:counter32;
                                description "The number  of  DHCP  server  packets  that have been dropped on this SAP.";
                            }

                        } // container server-packets

                    } // container statistics

                } // container dhcp6

                container static-host {
                    description "Enter the static-host context";

                    list ipv4 {
                        key "ip mac";
                        description "Enter the ipv4 list instance";

                        leaf ip {
                            type types-sros:ipv4-address;
                            description "IP address";
                        }

                        leaf mac {
                            type types-sros:mac-unicast-address;
                            description "MAC address";
                        }

                        leaf dynamic-mac {
                            type yang:mac-address;
                            description "The dynamically learned MAC address for this host.";
                        }

                        leaf retail-service {
                            type types-services:service-name;
                            description
                                "The service name of the retailer service
                                 to which this static host belongs.";
                        }

                        leaf retail-interface {
                            type types-sros:named-item;
                            description
                                "The interface name of the retailer service interface to which
                                 this static host belongs.";
                        }

                        leaf forwarding-state {
                            type types-sros:oper-state;
                            description "Forwarding state of this static host.";
                        }

                        container shcv {
                            description "Enter the shcv context";

                            leaf oper-state {
                                type enumeration {
                                    enum disabled                       { value 1; }
                                    enum down                           { value 2; }
                                    enum up                             { value 3; }
                                }
                                description
                                    "The state of the subscriber host connectivity
                                     check for this static host.";
                            }

                            leaf checks {
                                type yang:gauge32;
                                description "The number of connectivity checks for this static host.";
                            }

                            leaf replies {
                                type yang:gauge32;
                                description "The number of host replies for this static host.";
                            }

                            leaf reply-time {
                                type yang:timestamp;
                                description
                                    "The timestamp of the last successful connectivity
                                     check for this static host.";
                            }

                        } // container shcv

                    } // list ipv4

                } // container static-host

                container eth-cfm {
                    description "Enter the eth-cfm context";

                    list mep {
                        key "md-admin-name ma-admin-name mep-id";
                        description "Enter the mep list instance";

                        leaf md-admin-name {
                            type leafref {
                                path "../../../../../../eth-cfm/domain/md-admin-name";
                            }
                            description "A unique administratively assigned name used to identify a domain.";
                        }

                        leaf ma-admin-name {
                            type leafref {
                                path "../../../../../../eth-cfm/domain[md-admin-name=current()/../md-admin-name]/association/ma-admin-name";
                            }
                            description "A unique administratively assigned name used to identify an association.";
                        }

                        leaf mep-id {
                            type types-eth-cfm:mep-id-type;
                            description
                                "A CFM Virtual Maintenance Endpoint

                                 Specifies a local Maintenance association End Point identifier unique
                                 over a given maintanance association.";
                        }

                        leaf if-index {
                            type uint32;
                            description "Port ID of the MEP.";
                        }

                        leaf oper-mac-address {
                            type yang:mac-address;
                            description "Operational MAC address of the MEP.";
                        }

                        leaf oper-group-state {
                            type types-sros:up-down-status;
                            description "MEP state caused by operational group";
                        }

                        container ais {
                            description "Enter the ais context";

                            container received {
                                description "Enter the received context";

                                leaf ais-packet {
                                    type boolean;
                                    description "Indicates if the MEP is receiving AIS test frames from one or more of its sub-layer MEPs.";
                                }

                                leaf interval {
                                    type uint32 {
                                        range "1|60";
                                    }
                                    units "seconds";
                                    description "Indicates the AIS Interval received in the last AIS Frame.";
                                }

                            } // container received

                            container transmitted {
                                description "Enter the transmitted context";

                                leaf ais-packet {
                                    type enumeration {
                                        enum no-transmit                    { value 0; }
                                        enum transmit                       { value 1; }
                                        enum pending                        { value 2; }
                                    }
                                    description "Indicates if the MEP is transmitting AIS test frames from one or more of its sub-layer MEPs.";
                                }

                            } // container transmitted

                        } // container ais

                        container csf {
                            description "Enter the csf context";

                            container received {
                                description "Enter the received context";

                                leaf state {
                                    type enumeration {
                                        enum los                            { value 0; }
                                        enum ais                            { value 1; }
                                        enum rdi                            { value 2; }
                                        enum dci                            { value 3; }
                                    }
                                    description
                                        "Indicates the state of the received CSF frames for the MEP.
                                            los (0) - Client Loss of Signal
                                            ais (1) - Client Forward Defect Indication
                                            rdi (2) - Client Reverse Defect Indication
                                            dci (3) - Client Defect Clear Indication.";
                                }

                                leaf interval {
                                    type uint32 {
                                        range "1|60";
                                    }
                                    units "seconds";
                                    description "Indicates the CSF Interval received in the most recent CSF frame.";
                                }

                            } // container received

                        } // container csf

                        container grace {
                            description "Enter the grace context";

                            container transmitted {
                                description "Enter the transmitted context";

                                leaf grace-notification {
                                    type enumeration {
                                        enum no-transmit                    { value 0; }
                                        enum grace                          { value 1; }
                                        enum eth-ed                         { value 2; }
                                    }
                                    description "Indicates the state of the MEP grace period PDU transmission.";
                                }

                            } // container transmitted

                            container received {
                                description "Enter the received context";

                                leaf process-grace-notification {
                                    type boolean;
                                    description
                                        "Indicates whether the local MEP is receiving and processing grace notifications
                                         from one or more peer MEPs. A value of 'true ' indicates the local MEP is
                                         receiving and processing grace from at least one peer MEP. A value
                                         of 'false' indicates that no peer grace notifications are being
                                         received and processed.";
                                }

                            } // container received

                        } // container grace

                        container ccm-states {
                            description "Enter the ccm-states context";

                            leaf transmit-status {
                                type enumeration {
                                    enum no-transmit                    { value 0; }
                                    enum transmit                       { value 1; }
                                    enum suppressed                     { value 2; }
                                }
                                description
                                    "Indicates the state of the MEP CCM PDU transmission.

                                     Values:
                                        noTransmit (0) - no CCM PDUs are being transmitted by the MEP
                                        transmit   (1) - MEP is currently transmitting CCM PDUs
                                        suppressed (2) - MEP should be transmitting CCM PDUs but is suppressing
                                                        them due to an internal condition";
                            }

                            leaf sequence-error {
                                type yang:counter32;
                                description "The total number of out-of-sequence CCMs received from all remote MEPs.";
                            }

                            leaf fng-state {
                                type types-eth-cfm:fng-state-type;
                                description "Current state of the MEP Fault Notification Generator State Machine.";
                            }

                            container transmitted {
                                description "Enter the transmitted context";

                                leaf count {
                                    type yang:counter32;
                                    description "Total number of CCMs transmitted.";
                                }

                                leaf interface-status {
                                    type types-eth-cfm:interface-status;
                                    description
                                        "Indicates the interface status TLV information included in the most
                                         recent Connectivity Check Message (CCM) transmission from the local MEP.
                                         If the local MEP CCM transmissions are not enabled, or if no interface
                                         status TLV was included in the most recent transmission, then
                                         ccm-tx-if-status will return a value of is-no-interface-status-tlv (0).";
                                }

                                leaf port-status {
                                    type types-eth-cfm:port-status;
                                    description
                                        "Indicates the port status TLV information included in the most recent
                                         Connectivity Check Message (CCM) transmission from the local MEP.

                                         If the local MEP CCM transmissions are not enabled, or if no port
                                         status TLV was included in the most recent transmission, then
                                         ccm-tx-port-status will return a value of ps-no-port-state-tlv (0).";
                                }

                                leaf remote-defect-indicator {
                                    type boolean;
                                    description
                                        "Indicates whether or not the Remote Defect Indication (RDI) bit was set
                                         on the most recent Connectivity Check Message (CCM) transmission from the
                                         local MEP.

                                         If the local MEP CCM transmissions are not eanbled, or if the RDI bit
                                         was not set in the most recent transmission, then ccm-tx-rdi will return
                                         a value of 'false (2)'.";
                                }

                            } // container transmitted

                            container received {
                                description "Enter the received context";

                                leaf highest-priority-defect {
                                    type types-eth-cfm:highest-priority-defect-type;
                                    description
                                        "The highest priority defect that has been present since the
                                         MEPs Fault Notification Generator State Machine was last in
                                         the reset state.";
                                }

                                leaf defect-flags {
                                    type types-eth-cfm:mep-defect-flags;
                                    description "A vector of boolean error conditions, any of which may be true.";
                                }

                                list remote-mep-peer {
                                    key "remote-mep-id";
                                    description "Enter the remote-mep-peer list instance";

                                    leaf remote-mep-id {
                                        type types-eth-cfm:mep-id-type;
                                        description "The Remote MEP ID within the same Maintenance Association.";
                                    }

                                    leaf auto-discovered {
                                        type boolean;
                                        description
                                            "Specifies whether or not the remote peer was automatically discovered
                                             ('true') or not. Auto-discovered remote peers are created by the system
                                             only, and are of a 'volatile' storage type. Specifying the value of
                                             'false' will mark an auto-discovered remote peer as permanently configured.";
                                    }

                                    leaf receiving-ccm {
                                        type types-eth-cfm:remote-mep-state-type;
                                        description "The operational CCM receiving state of the remote MEP.";
                                    }

                                    leaf ccm-status-since {
                                        type yang:date-and-time;
                                        description
                                            "The time at which the Remote MEP
                                             last entered either the mep-failed or mep-ok state. ";
                                    }

                                    leaf peer-mac-address {
                                        type yang:mac-address;
                                        description "The MAC address of the remote MEP.";
                                    }

                                    leaf receiving-remote-defect-indicator {
                                        type boolean;
                                        description
                                            "State of the RDI bit in the last received CCM (true for rdi=1), or false
                                             if none has been received.";
                                    }

                                    leaf port-status-tlv {
                                        type types-eth-cfm:port-status;
                                        description
                                            "An enumerated value of the Port status TLV received in the
                                             last CCM from the remote MEP or the default value
                                             ps-no-port-state-tlv indicating either no CCM has been received,
                                             or that no port status TLV was received in the last CCM. ";
                                    }

                                    leaf interface-status-tlv {
                                        type types-eth-cfm:interface-status;
                                        description
                                            "An enumerated value of the Interface status TLV received
                                             in the last CCM from the remote MEP or the default value
                                             is-no-interface-status-tlv indicating either no CCM has been
                                             received, or that no interface status TLV was received in
                                             the last CCM.";
                                    }

                                } // list remote-mep-peer

                            } // container received

                        } // container ccm-states

                        container mc-lag {
                            description "Enter the mc-lag context";

                            leaf inactive-state {
                                type enumeration {
                                    enum not-applicable                 { value 0; }
                                    enum standby                        { value 1; }
                                    enum active                         { value 2; }
                                }
                                description
                                    "Indicates the MC-LAG inactive state of the mep.  The value of
                                     system/eth-cfm/redundancy/mc-lag/standby-mep must be 'true (1)' 
                                     on the node for this leaf to have meaning.";
                            }

                        } // container mc-lag

                        container statistics {
                            description "Enter the statistics context";

                            list opcode {
                                key "opcode-name";
                                description "Enter the opcode list instance";

                                leaf opcode-name {
                                    type types-eth-cfm:statistics-opcode-name;
                                    description "Integer that defines which CFM PDU Opcode the statictics refer to.";
                                }

                                leaf transmitted {
                                    type yang:counter32;
                                    description "The total number of PDUs transmitted from the node with the specified Opcode.";
                                }

                                leaf received {
                                    type yang:counter32;
                                    description "The total number of PDUs received on the node with the specified Opcode.";
                                }

                            } // list opcode

                        } // container statistics

                    } // list mep

                    list mip {
                        key "primary-vlan";
                        description "Enter the mip list instance";

                        leaf primary-vlan {
                            type types-eth-cfm:vlan-id-or-none;
                            description "The VLAN ID to which the MIP is attached or none.";
                        }

                        leaf instantiated {
                            type boolean;
                            description "Indicates if the MIP is instanstiated or not.";
                        }

                        leaf direction {
                            type enumeration {
                                enum both                           { value 0; }
                            }
                            description "Indicates the direction in which the MIP faces on the Bridge Port.";
                        }

                        leaf level {
                            type types-eth-cfm:mp-level;
                            description "Indicate the MD (Maintenance Domain) Level at which MHFs (MIP Half Function) are created.";
                        }

                        leaf level-authority {
                            type types-eth-cfm:mip-authority;
                            description "Indicates the authority context used for leaf level of the instatiated MIP.";
                        }

                        leaf mhf-creation {
                            type enumeration {
                                enum none                           { value 1; }
                                enum default                        { value 2; }
                                enum explicit                       { value 3; }
                                enum defer                          { value 4; }
                                enum static                         { value 32; }
                            }
                            description
                                "A value indicating if the Management entity can create MHFs
                                 (MIP Half Function).";
                        }

                        leaf mhf-creation-authority {
                            type types-eth-cfm:mip-authority;
                            description "Indicates the authority context used for leaf mhf-creation of the instatiated MIP.";
                        }

                        leaf id-permission {
                            type types-eth-cfm:permission-type;
                            description "Indicates the sender ID TLV permissions for the instantiated MIP.";
                        }

                        leaf id-permission-authority {
                            type types-eth-cfm:mip-authority;
                            description "Indicates the authority context used for leaf id-permission of the instatiated MIP.";
                        }

                        leaf mip-ltr-priority {
                            type types-eth-cfm:frame-priority;
                            description "Indicates the priority to use in linktrace response frames to be transmitted for this MIP.";
                        }

                        leaf mip-ltr-priority-authority {
                            type types-eth-cfm:mip-authority;
                            description "Indicates the authority context used for leaf mip-ltr-priority of the instatiated MIP.";
                        }

                    } // list mip

                } // container eth-cfm

                list locked-out-host {
                    key "id";
                    description "Enter the locked-out-host list instance";

                    leaf id {
                        type uint32;
                        description "Id of the locked out host";
                    }

                    leaf mac-address {
                        type yang:mac-address;
                        description "Mac-address of the locked out host";
                    }

                    leaf circuit-id {
                        type binary {
                            length "1..256";
                        }
                        description "Circuit-id of the locked out host";
                    }

                    leaf remote-id {
                        type binary {
                            length "1..256";
                        }
                        description "Remote-id of the locked out host";
                    }

                    leaf elapsed-reset-time {
                        type uint32;
                        units "seconds";
                        description "Elapsed reset time";
                    }

                    leaf elapsed-lock-time {
                        type uint32;
                        units "seconds";
                        description "Elapsed lock time";
                    }

                    leaf current-lock-timeout {
                        type uint32;
                        units "seconds";
                        description "The timeout for the current lock interval";
                    }

                    leaf next-lock-timeout {
                        type uint32;
                        units "seconds";
                        description "The timeout for the next lock interval";
                    }

                    leaf lockout-count {
                        type uint32;
                        description "Number of lockouts";
                    }

                    leaf lockout-state {
                        type enumeration {
                            enum graceful {
                                value 1;
                                description "The host is allowed to authenticate and the reset timer is running. Another authentication failure for this host while in this state while change the state to active. If the reset timer expires, the lock out for this host is removed.";
                            }
                            enum active {
                                value 2;
                                description "The host is not allowed to authenticate and the lock-out timer is running. When the timer expires, the state is changed to graceful.";
                            }
                        }
                        description "Lockout state for this host";
                    }

                } // list locked-out-host

            } // list sap

            list capture-sap {
                key "sap-id";
                description "Enter the capture-sap list instance";

                leaf sap-id {
                    type types-sros:sap;
                    description "SAP identifier";
                }

                container pfcp {
                    description "Enter the pfcp context";

                    container up-resiliency {
                        description "Enter the up-resiliency context";

                        list monitor-oper-group {
                            key "oper-group";
                            description "Enter the monitor-oper-group list instance";

                            leaf oper-group {
                                type leafref {
                                    path "../../../../../../oper-group/name";
                                }
                                description "The identifier of the operational group";
                            }

                            leaf actual-health-drop {
                                type uint32;
                                description "The actual health drop caused by this monitor port or operational group";
                            }

                        } // list monitor-oper-group

                    } // container up-resiliency

                } // container pfcp

                container trigger-packet {
                    description "Enter the trigger-packet context";

                    list statistics {
                        key "packet-type";
                        description "Enter the statistics list instance";

                        leaf packet-type {
                            type enumeration {
                                enum dhcp                           { value 1; }
                                enum pppoe                          { value 2; }
                                enum arp                            { value 3; }
                                enum dhcp6                          { value 4; }
                                enum ppp                            { value 5; }
                                enum rtrsol                         { value 6; }
                                enum data                           { value 7; }
                            }
                            description "The trigger-packet type for which statistics are returned";
                        }

                        leaf received {
                            type yang:counter32;
                            description "The number of packets received";
                        }

                        leaf redirected {
                            type yang:counter32;
                            description "The number of packets redirected";
                        }

                        leaf dropped {
                            type yang:counter32;
                            description "The number of packets dropped";
                        }

                    } // list statistics

                } // container trigger-packet

                list locked-out-host {
                    key "id";
                    description "Enter the locked-out-host list instance";

                    leaf id {
                        type uint32;
                        description "Id of the locked out host";
                    }

                    leaf mac-address {
                        type yang:mac-address;
                        description "Mac-address of the locked out host";
                    }

                    leaf circuit-id {
                        type binary {
                            length "1..256";
                        }
                        description "Circuit-id of the locked out host";
                    }

                    leaf remote-id {
                        type binary {
                            length "1..256";
                        }
                        description "Remote-id of the locked out host";
                    }

                    leaf elapsed-reset-time {
                        type uint32;
                        units "seconds";
                        description "Elapsed reset time";
                    }

                    leaf elapsed-lock-time {
                        type uint32;
                        units "seconds";
                        description "Elapsed lock time";
                    }

                    leaf current-lock-timeout {
                        type uint32;
                        units "seconds";
                        description "The timeout for the current lock interval";
                    }

                    leaf next-lock-timeout {
                        type uint32;
                        units "seconds";
                        description "The timeout for the next lock interval";
                    }

                    leaf lockout-count {
                        type uint32;
                        description "Number of lockouts";
                    }

                    leaf lockout-state {
                        type enumeration {
                            enum graceful {
                                value 1;
                                description "The host is allowed to authenticate and the reset timer is running. Another authentication failure for this host while in this state while change the state to active. If the reset timer expires, the lock out for this host is removed.";
                            }
                            enum active {
                                value 2;
                                description "The host is not allowed to authenticate and the lock-out timer is running. When the timer expires, the state is changed to graceful.";
                            }
                        }
                        description "Lockout state for this host";
                    }

                } // list locked-out-host

                container distributed-cpu-protection {
                    description "Enter the distributed-cpu-protection context";

                    list static-policer {
                        key "name card fp-number";
                        description "Enter the static-policer list instance";

                        leaf name {
                            type types-sros:named-item;
                            description "Name of static policer.";
                        }

                        leaf card {
                            type types-card:iom-card-slot;
                            description "IOM card within a chassis in the system.";
                        }

                        leaf fp-number {
                            type uint32 {
                                range "1..12";
                            }
                            description "Forwarding plane within a specific IOM card in the system.";
                        }

                        leaf state {
                            type types-services:dist-cpu-prot-policer-state;
                            description "State of the policer configured on Distributed CPU Protection Policy.";
                        }

                        leaf exceed-count {
                            type uint64;
                            description
                                "Number of packets exceeding the policing parameters since the given
                                 policer was previously declared as conformant or newly instantiated.";
                        }

                        leaf hold-down-remain {
                            type types-services:dist-cpu-prot-action-duration;
                            units "seconds";
                            description "Remaining hold-down period for a given policer.";
                        }

                        leaf detection-time-remain {
                            type uint32;
                            units "seconds";
                            description "Detection time remaining for a given policer.";
                        }

                        leaf total-exceed-count {
                            type uint64;
                            description "Total number of packets exceeding the policing parametersi.";
                        }

                        leaf exit-conform-state-count {
                            type uint32;
                            description "Total number of transition of the policer to the exceed state.";
                        }

                    } // list static-policer

                    list local-monitor-policer {
                        key "name card fp-number";
                        description "Enter the local-monitor-policer list instance";

                        leaf name {
                            type types-sros:named-item;
                            description "Name of local-monitor policer.";
                        }

                        leaf card {
                            type types-card:iom-card-slot;
                            description "IOM card within a chassis in the system.";
                        }

                        leaf fp-number {
                            type uint32 {
                                range "1..12";
                            }
                            description "Forwarding plane within a specific IOM card in the system.";
                        }

                        leaf state {
                            type types-services:dist-cpu-prot-policer-state;
                            description "State of the policer configured on Distributed CPU Protection Policy.";
                        }

                        leaf exceed-count {
                            type uint64;
                            description
                                "Number of packets exceeding the policing parameters since the given
                                 policer was previously declared as conformant or newly instantiated.";
                        }

                        leaf all-dynamic-policer-allocation {
                            type boolean;
                            description "All dynamic-policers allocation status";
                        }

                        leaf total-exceed-count {
                            type uint64;
                            description "Total number of packets exceeding the policing parametersi.";
                        }

                        leaf exit-conform-state-count {
                            type uint32;
                            description "Total number of transition of the policer to the exceed state.";
                        }

                    } // list local-monitor-policer

                    list dynamic-policer {
                        key "protocol card fp-number";
                        description "Enter the dynamic-policer list instance";

                        leaf protocol {
                            type types-sros:dist-cpu-protection-protocol;
                            description "Dynamic policer protocol.";
                        }

                        leaf card {
                            type types-card:iom-card-slot;
                            description "IOM card within a chassis in the system.";
                        }

                        leaf fp-number {
                            type uint32 {
                                range "1..12";
                            }
                            description "Forwarding plane within a specific IOM card in the system.";
                        }

                        leaf state {
                            type types-services:dist-cpu-prot-policer-state;
                            description "State of the policer configured on Distributed CPU Protection Policy.";
                        }

                        leaf exceed-count {
                            type uint64;
                            description
                                "Number of packets exceeding the policing parameters since the given
                                 policer was previously declared as conformant or newly instantiated.";
                        }

                        leaf hold-down-remain {
                            type types-services:dist-cpu-prot-action-duration;
                            units "seconds";
                            description "Remaining hold-down period for a given policer.";
                        }

                        leaf detection-time-remain {
                            type uint32;
                            units "seconds";
                            description "Detection time remaining for a given policer.";
                        }

                        leaf dynamic-policer-allocation {
                            type boolean;
                            description "Dynamic-policer allocation status";
                        }

                        leaf total-exceed-count {
                            type uint64;
                            description "Total number of packets exceeding the policing parametersi.";
                        }

                        leaf exit-conform-state-count {
                            type uint32;
                            description "Total number of transition of the policer to the exceed state.";
                        }

                    } // list dynamic-policer

                } // container distributed-cpu-protection

            } // list capture-sap

            list interface {
                key "interface-name";
                description "Enter the interface list instance";

                leaf interface-name {
                    type types-sros:interface-name;
                    description
                        "The administrative name assigned to this router interface. The interface
                         name must be unique among entries with the same vRtrID value.";
                }

                leaf if-index {
                    type int32;
                    description "The interface index.";
                }

                leaf system-if-index {
                    type int32;
                    description "The interface system index.";
                }

                leaf oper-state {
                    type enumeration {
                        enum up                             { value 1; }
                        enum down                           { value 2; }
                        enum testing                        { value 3; }
                        enum unknown                        { value 4; }
                        enum dormant                        { value 5; }
                        enum not-present                    { value 6; }
                        enum lower-layer-down               { value 7; }
                    }
                    description
                        "The current operational state of the interface.
                         This leaf has the same semantics as ifOperStatus. 
                         in RFC 2863: The Interfaces Group MIB";
                }

                leaf protocol {
                    type bits {
                        bit ospfv2                         { position 0; }
                        bit rip                            { position 1; }
                        bit isis                           { position 2; }
                        bit bgp                            { position 3; }
                        bit mpls                           { position 4; }
                        bit rsvp                           { position 5; }
                        bit ldp                            { position 6; }
                        bit igmp                           { position 7; }
                        bit pim                            { position 8; }
                        bit ospfv3                         { position 9; }
                        bit mld                            { position 10; }
                        bit ripng                          { position 11; }
                    }
                    description
                        "Indicates which protocols are configured on the interface.;
                                         
                         Values:
                             ospfv2 - Indicates if OSPFv2 is configured.
                             rip    - Indicates if RIP is configured.
                             isis   - Indicates if ISIS is configured.
                             bgp    - Indicates if BGP is configured.
                             mpls   - Indicates if MPLS is configured.
                             rsvp   - Indicates if RSVP is configured.
                             ldp    - Indicates if LDP is configured.
                             igmp   - Indicates if IGMP is configured.
                             pim    - Indicates if PIM is configured.
                             ospfv3 - Indicates if OSPFv3 is configured.
                             mld    - Indicates if MLD is configured.
                             ripng  - Indicates if RIPng is configured.";
                }

                leaf oper-ip-mtu {
                    type uint32;
                    units "bytes";
                    description "Indicates the interface operational IP MTU.";
                }

                leaf creation-origin {
                    type types-sros:creation-origin;
                    description "Indicates the mechanism used to create this entry.";
                }

                leaf last-oper-change {
                    type yang:date-and-time;
                    description "The sysUpTime when the operational state of this interface last changed.";
                }

                container hold-time {
                    description "Enter the hold-time context";

                    container ipv4 {
                        description "Enter the ipv4 context";

                        leaf hold-timer {
                            type uint32;
                            units "seconds";
                            description
                                "The hold-timer indicates the time left before
                                 the interface comes up or goes down, depending on the ongoing
                                 transition state of the interface.";
                        }

                    } // container ipv4

                } // container hold-time

                container ipv4 {
                    description "Enter the ipv4 context";

                    leaf oper-state {
                        type types-sros:oper-state;
                        description "The current IPv4 operational status of this router interface.";
                    }

                    leaf down-reason {
                        type bits {
                            bit admin-disabled                 { position 0; }
                            bit service-admin-disabled         { position 1; }
                            bit port-down                      { position 2; }
                            bit address-or-parent-not-ready    { position 3; }
                            bit associated-object-not-ready    { position 4; }
                            bit rvpls-down                     { position 5; }
                            bit operational-group-down         { position 6; }
                            bit admin-destroy                  { position 7; }
                            bit no-address                     { position 8; }
                            bit no-info                        { position 9; }
                            bit hold-down-timer-running        { position 10; }
                            bit protocol-down                  { position 11; }
                            bit invalid-port-configuration     { position 12; }
                            bit unknown                        { position 13; }
                            bit no-route-distinguisher         { position 14; }
                            bit wlan-gateway-redundancy-standby { position 15; }
                            bit wlan-gateway-group-degraded    { position 16; }
                            bit ip-control-tunnel-down         { position 17; }
                            bit pdn-address-mismatch           { position 18; }
                            bit ping-check-failure             { position 19; }
                            bit port-internal-loopback         { position 20; }
                            bit no-resources-for-srv6-loopback { position 21; }
                            bit ip-tunnel-not-ready            { position 22; }
                        }
                        description
                            "Indicates the reason for why the interface is operationally down.
                                             
                             Values:
                                 admin-disabled                  - Administratively disabled.
                                 service-admin-disabled          - Assiocated service is administratively disabled.
                                 port-down                       - Associated SAP/port is operationally down.
                                 address-or-parent-not-ready     - Associated address or parent interface is not ready.
                                 associated-object-not-ready     - Associated object is not ready.
                                 rvpls-down                      - Associated R-VPLS service is operationally down.
                                 operational-group-down          - Associated operational group is operationally down.
                                 admin-destroy                   - The interface is being destroyed.
                                 no-address                      - There is no address configured.
                                 no-info                         - The interface info is not present.
                                 hold-down-timer-running         - The hold down timer is running.
                                 protocol-down                   - The protocols are operationally down.
                                 invalid-port-configuration      - Invalid port configuration.
                                 unknown                         - The interface is operationally down due to some unknown reason.
                                 no-route-distinguisher          - No route-distinguisher configured in the VRF.
                                 wlan-gateway-redundancy-standby - The interface is in standby state for WLAN-GW redundancy.
                                 wlan-gateway-group-degraded     - The interface associated WLAN-GW group is in a degraded state.
                                 ip-control-tunnel-down          - The IP tunnel associated to a control-tunnel interface is operationally down.
                                 pdn-address-mismatch            - The IP address learned from the packet data network does not match the configured primary IP address.
                                 ping-check-failure              - The IP interface is or went down because of a ping-template failure.
                                 port-internal-loopback          - The IP interface is bound to a port that has an internal loopback configured.
                                 no-resources-for-srv6-loopback  - There are not enough resources for the SRv6 locator prefix loopback address.
                                 ip-tunnel-not-ready             - The IP tunnel associated to an ip-tunnel-interface is not ready.";
                    }

                    container icmp {
                        description "Enter the icmp context";

                        container statistics {
                            description "Enter the statistics context";

                            leaf icmp-in-msgs {
                                type yang:counter32;
                                description
                                    "Total Number of ICMPv4 messages received by this interface.
                                                     
                                     This includes all those counted by icmp-in-errors. Note that this
                                     interface is the interface to which the ICMPv4 messages were
                                     addressed which may not be necessarily the input interface
                                     for the messages.";
                            }

                            leaf icmp-in-errors {
                                type yang:counter32;
                                description
                                    "Number of ICMPv4 errored messages received by this interface.
                                                     
                                     This implies ICMPv4 messages determined as having specific
                                     ICMPv4 errors (bad ICMPv4 checksums, bad length, etc.).";
                            }

                            leaf icmp-in-dest-unreachables {
                                type yang:counter32;
                                description "Number of ICMPv4 destination unreachable messages received by this interface.";
                            }

                            leaf icmp-in-redirects {
                                type yang:counter32;
                                description "Number of ICMPv4 redirect messages received by this interface.";
                            }

                            leaf icmp-in-echos {
                                type yang:counter32;
                                description "Number of ICMPv4 echo (request) messages received by this interface.";
                            }

                            leaf icmp-in-echo-replies {
                                type yang:counter32;
                                description "Number of ICMPv4 echo reply messages received by this interface.";
                            }

                            leaf icmp-in-time-exceeds {
                                type yang:counter32;
                                description "Number of ICMPv4 time exceeded messages received by this interface.";
                            }

                            leaf icmp-in-src-quenches {
                                type yang:counter32;
                                description "Number of ICMPv4 source quench messages received by this interface.";
                            }

                            leaf icmp-in-timestamps {
                                type yang:counter32;
                                description "Number of ICMPv4 timestamp (request) messages received by this interface.";
                            }

                            leaf icmp-in-timestamp-replies {
                                type yang:counter32;
                                description "Number of ICMPv4 timestamp reply messages received by this interface.";
                            }

                            leaf icmp-in-address-masks {
                                type yang:counter32;
                                description "Number of ICMPv4 address mask request messages received by this interface.";
                            }

                            leaf icmp-in-address-mask-replies {
                                type yang:counter32;
                                description "Number of ICMPv4 address mask reply messages received by this interface.";
                            }

                            leaf icmp-in-parm-problems {
                                type yang:counter32;
                                description "Number of ICMPv4 parameter problem messages received by this interface.";
                            }

                            leaf icmp-out-msgs {
                                type yang:counter32;
                                description
                                    "Total number of ICMPv4 messages this interface attempted to send.
                                                     
                                     This includes all those counted by icmp-out-errors.";
                            }

                            leaf icmp-out-errors {
                                type yang:counter32;
                                description
                                    "Number of ICMPv4 messages this interface could not be send due to problems
                                     discovered within ICMPv4 such as lack of buffers.
                                                     
                                     This value should not include errors discovered outside the ICMPv4 layer such as
                                     the inability of VRtr IPv4 to route the resultant datagram. In some implementations
                                     there may be no types of error which contribute to this counter's value.";
                            }

                            leaf icmp-out-dest-unreachables {
                                type yang:counter32;
                                description "Number of ICMPv4 destination unreachable messages sent by this interface.";
                            }

                            leaf icmp-out-redirects {
                                type yang:counter32;
                                description "Number of ICMPv4 redirect messages sent by this interface.";
                            }

                            leaf icmp-out-echos {
                                type yang:counter32;
                                description "Number of ICMPv4 echo request messages sent by this interface.";
                            }

                            leaf icmp-out-echo-replies {
                                type yang:counter32;
                                description "Number of ICMPv4 echo reply messages sent by this interface.";
                            }

                            leaf icmp-out-time-exceeds {
                                type yang:counter32;
                                description "Number of ICMPv4 time exceeded messages sent by this interface.";
                            }

                            leaf icmp-out-src-quenches {
                                type yang:counter32;
                                description "Number of ICMPv4 source quench messages sent by this interface.";
                            }

                            leaf icmp-out-timestamps {
                                type yang:counter32;
                                description "Number of ICMPv4 timestamp (request) messages sent by this interface.";
                            }

                            leaf icmp-out-timestamp-replies {
                                type yang:counter32;
                                description "Number of ICMPv4 timestamp reply messages sent by this interface.";
                            }

                            leaf icmp-out-address-masks {
                                type yang:counter32;
                                description "Number of ICMPv4 address mask request messages sent by this interface.";
                            }

                            leaf icmp-out-address-mask-replies {
                                type yang:counter32;
                                description "Number of ICMPv4 address mask reply messages sent by this interface.";
                            }

                            leaf icmp-out-parm-problems {
                                type yang:counter32;
                                description "Number of ICMPv4 parameter problem messages sent by this interface.";
                            }

                            leaf icmp-out-discards {
                                type yang:counter32;
                                description "Number of discarded ICMPv4 messages on this interface.";
                            }

                        } // container statistics

                    } // container icmp

                    container primary {
                        description "Enter the primary context";

                        leaf oper-address {
                            type types-sros:ip-address;
                            description "Indicates the operational address of this entry.";
                        }

                        leaf creation-origin {
                            type types-sros:creation-origin;
                            description "Indicates the mechanism used to create this entry.";
                        }

                    } // container primary

                    container neighbor-discovery {
                        description "Enter the neighbor-discovery context";

                        list neighbor {
                            key "ipv4-address";
                            description "Enter the neighbor list instance";

                            leaf ipv4-address {
                                type types-sros:ipv4-address;
                                description "The IPv4 address corresponding to the media-dependent physical address.";
                            }

                            leaf oper-state {
                                type types-sros:oper-state;
                                description "Indicates if the ARP entry is being used actively in the ARP table.";
                            }

                            leaf mac-address {
                                type yang:mac-address;
                                description "The media-dependent physical address.";
                            }

                            leaf type {
                                type enumeration {
                                    enum other                          { value 0; }
                                    enum static                         { value 1; }
                                    enum dynamic                        { value 2; }
                                    enum managed                        { value 100; }
                                    enum evpn                           { value 101; }
                                    enum evpn-local-es                  { value 102; }
                                }
                                description "The type of mapping.";
                            }

                            leaf timer {
                                type uint32 {
                                    range "0..65535";
                                }
                                units "seconds";
                                description
                                    "Indicates how much longer an ARP entry remains in the ARP cache.

                                     When timer has a value of zero, the entry is cleared from the cache.";
                            }

                        } // list neighbor

                    } // container neighbor-discovery

                } // container ipv4

            } // list interface

            container provider-tunnel {
                description "Enter the provider-tunnel context";

                container inclusive {
                    description "Enter the inclusive context";

                    leaf remain-data-delay-interval {
                        status obsolete;
                        type uint32;
                        description "Remaining data delay interval for the inclusive provider.";
                    }

                    leaf lsp-name {
                        status obsolete;
                        type types-sros:named-item-or-empty;
                        description "The LSP name used for signalling inclusive provider tunnel.";
                    }

                    leaf oper-state {
                        status obsolete;
                        type types-sros:oper-state;
                        description "Operational status of the inclusive provider-tunnel.";
                    }

                    container originating {
                        description "Enter the originating context";

                        leaf remain-data-delay-interval {
                            type uint32;
                            description "Remaining data delay interval for the inclusive provider.";
                        }

                        container ldp {
                            description "Enter the ldp context";

                            leaf tunnel-name {
                                type string;
                                description "Originating tunnel name";
                            }

                            leaf root-address {
                                type types-sros:ip-address;
                                description "Originating root address";
                            }

                            leaf lsp-id {
                                type uint32;
                                description "Originating lsp id";
                            }

                            leaf oper-state {
                                type types-sros:oper-state;
                                description "Operational status of originating ldp provider-tunnel";
                            }

                        } // container ldp

                        container rsvp {
                            description "Enter the rsvp context";

                            leaf tunnel-name {
                                type string;
                                description "Originating tunnel name";
                            }

                            leaf p2mp-id {
                                type uint32;
                                description "Originating p2mp id";
                            }

                            leaf tunnel-id {
                                type uint32;
                                description "Originating tunnel id";
                            }

                            leaf external-tunnel-id {
                                type types-sros:ip-address;
                                description "Originating external-tunnel-id";
                            }

                            leaf oper-state {
                                type types-sros:oper-state;
                                description "Operational status of originating rsvp provider-tunnel";
                            }

                        } // container rsvp

                    } // container originating

                    container terminating {
                        description "Enter the terminating context";

                        list ldp {
                            key "index";
                            description "Enter the ldp list instance";

                            leaf index {
                                type uint32;
                                description "The interface index of the entry";
                            }

                            leaf root-address {
                                type types-sros:ip-address;
                                description "Terminating root address";
                            }

                            leaf lsp-id {
                                type uint32;
                                description "Terminating lsp id";
                            }

                            leaf oper-state {
                                type types-sros:oper-state;
                                description "Operational status of Terminating ldp provider-tunnel";
                            }

                        } // list ldp

                        list rsvp {
                            key "index";
                            description "Enter the rsvp list instance";

                            leaf index {
                                type uint32;
                                description "The interface index of the entry";
                            }

                            leaf p2mp-id {
                                type uint32;
                                description "Terminating p2mp id";
                            }

                            leaf tunnel-id {
                                type uint32;
                                description "Terminating tunnel id";
                            }

                            leaf external-tunnel-id {
                                type types-sros:ip-address;
                                description "Terminating external-tunnel-id";
                            }

                            leaf oper-state {
                                type types-sros:oper-state;
                                description "Operational status of Terminating rsvp provider-tunnel";
                            }

                        } // list rsvp

                    } // container terminating

                } // container inclusive

                container selective {
                    description "Enter the selective context";

                    container originating {
                        description "Enter the originating context";

                        list multicast-tunnel {
                            key "group-address source-address ip-origin-address root-address-index lsp-index";
                            description "Enter the multicast-tunnel list instance";

                            leaf group-address {
                                type types-sros:ip-address;
                                description "The multicast group address of the entry.";
                            }

                            leaf source-address {
                                type types-sros:ip-address;
                                description "The source address of the multicast sender.";
                            }

                            leaf ip-origin-address {
                                type types-sros:ip-address;
                                description "The ip origin address of the entry.";
                            }

                            leaf root-address-index {
                                type types-sros:ip-address;
                                description "The root address of the tunel used as a key.";
                            }

                            leaf lsp-index {
                                type uint32;
                                description "lsp-index identifying the pmsi information of the tunnel used as a key.";
                            }

                            leaf interface-index {
                                type uint32;
                                description "Interface index of the data MT.";
                            }

                            leaf up-time {
                                type uint32;
                                description "Time since the data MT entry was created.";
                            }

                            leaf lsp-id {
                                type uint32;
                                description "Unique identifier of the data Multicast Tunnel entry.";
                            }

                            leaf root-address {
                                type types-sros:ip-address;
                                description "Root IP Address used for the Multicast Tunnel.";
                            }

                            leaf counter {
                                type uint32;
                                description "Number of current receiver PE associated with the Multicast tunnel.";
                            }

                            leaf oper-state {
                                type enumeration {
                                    enum tx-join-pending                { value 0; }
                                    enum tx-joined                      { value 1; }
                                    enum rx-not-joined                  { value 2; }
                                    enum rx-joined                      { value 3; }
                                    enum rx-joined-tracking             { value 4; }
                                    enum tx-leaving                     { value 5; }
                                    enum max-p2mp-reached               { value 6; }
                                }
                                description "Operational status of the provider-tunnel.";
                            }

                            leaf remain-delay-interval {
                                type uint32;
                                description "Remain delay interval after which the selective provider Multicast tunnel is created.";
                            }

                        } // list multicast-tunnel

                    } // container originating

                    container terminating {
                        description "Enter the terminating context";

                        list multicast-tunnel {
                            key "group-address source-address ip-origin-address root-address-index lsp-index";
                            description "Enter the multicast-tunnel list instance";

                            leaf group-address {
                                type types-sros:ip-address;
                                description "The multicast group address of the entry.";
                            }

                            leaf source-address {
                                type types-sros:ip-address;
                                description "The source address of the multicast sender.";
                            }

                            leaf ip-origin-address {
                                type types-sros:ip-address;
                                description "The ip origin address of the entry.";
                            }

                            leaf root-address-index {
                                type types-sros:ip-address;
                                description "The root address of the tunel used as a key.";
                            }

                            leaf lsp-index {
                                type uint32;
                                description "lsp-index identifying the pmsi information of the tunnel used as a key.";
                            }

                            leaf interface-index {
                                type uint32;
                                description "Interface index of the data MT.";
                            }

                            leaf up-time {
                                type uint32;
                                description "Time since the data MT entry was created.";
                            }

                            leaf lsp-id {
                                type uint32;
                                description "Unique identifier of the data Multicast Tunnel entry.";
                            }

                            leaf root-address {
                                type types-sros:ip-address;
                                description "Root IP Address used for the Multicast Tunnel.";
                            }

                            leaf counter {
                                type uint32;
                                description "Number of current receiver PE associated with the Multicast tunnel.";
                            }

                            leaf oper-state {
                                type enumeration {
                                    enum tx-join-pending                { value 0; }
                                    enum tx-joined                      { value 1; }
                                    enum rx-not-joined                  { value 2; }
                                    enum rx-joined                      { value 3; }
                                    enum rx-joined-tracking             { value 4; }
                                    enum tx-leaving                     { value 5; }
                                    enum max-p2mp-reached               { value 6; }
                                }
                                description "Operational status of the provider-tunnel.";
                            }

                        } // list multicast-tunnel

                    } // container terminating

                    list multicast-tunnel {
                        status obsolete;
                        key "group-address source-address ip-origin-address root-address-index lsp-index";
                        description "Enter the multicast-tunnel list instance";

                        leaf group-address {
                            status obsolete;
                            type types-sros:ip-address;
                            description "The multicast group address of the entry.";
                        }

                        leaf source-address {
                            status obsolete;
                            type types-sros:ip-address;
                            description "The source address of the multicast sender.";
                        }

                        leaf ip-origin-address {
                            status obsolete;
                            type types-sros:ip-address;
                            description "The ip origin address of the entry.";
                        }

                        leaf root-address-index {
                            status obsolete;
                            type types-sros:ip-address;
                            description "The root address of the tunel used as a key.";
                        }

                        leaf lsp-index {
                            status obsolete;
                            type uint32;
                            description "lsp-index identifying the pmsi information of the tunnel used as a key.";
                        }

                        leaf interface-index {
                            status obsolete;
                            type uint32;
                            description "Interface index of the data MT.";
                        }

                        leaf up-time {
                            status obsolete;
                            type uint32;
                            description "Time since the data MT entry was created.";
                        }

                        leaf source-address-group-address-count {
                            status obsolete;
                            type uint32;
                            description "Number of C-(S,G)'s mapped to the MT interface.";
                        }

                        leaf multi-stream-id {
                            status obsolete;
                            type uint32;
                            description "Stream ID of the multi-stream SPMSI.";
                        }

                        leaf lsp-id {
                            status obsolete;
                            type uint32;
                            description "Unique identifier of the data Multicast Tunnel entry.";
                        }

                        leaf remain-delay-interval {
                            status obsolete;
                            type uint32;
                            description "Remain delay interval after which the selective provider Multicast tunnel is created.";
                        }

                        leaf root-address {
                            status obsolete;
                            type types-sros:ip-address;
                            description "Root IP Address used for the Multicast Tunnel.";
                        }

                        leaf counter {
                            status obsolete;
                            type uint32;
                            description "Number of current receiver PE associated with the Multicast tunnel.";
                        }

                        leaf oper-state {
                            status obsolete;
                            type enumeration {
                                enum tx-join-pending                { value 0; }
                                enum tx-joined                      { value 1; }
                                enum rx-not-joined                  { value 2; }
                                enum rx-joined                      { value 3; }
                                enum rx-joined-tracking             { value 4; }
                                enum tx-leaving                     { value 5; }
                                enum max-p2mp-reached               { value 6; }
                            }
                            description "Operational status of the provider-tunnel.";
                        }

                    } // list multicast-tunnel

                } // container selective

            } // container provider-tunnel

            container subscriber-management {
                description "Enter the subscriber-management context";

                container statistics {
                    description "Enter the statistics context";

                    leaf last-reset-peak-values {
                        type yang:date-and-time;
                        description "Timestamp of the last reset of the peak values";
                    }

                    list ipv4-hosts {
                        key "counter";
                        description "Enter the ipv4-hosts list instance";

                        leaf counter {
                            type types-submgt:submgt-statistics-ipv4-type;
                            description "Type of submgt ipv4 hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list ipv4-hosts

                    list ipv6-hosts {
                        key "counter";
                        description "Enter the ipv6-hosts list instance";

                        leaf counter {
                            type types-submgt:submgt-statistics-ipv6-type;
                            description "Type of submgt ipv6 hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list ipv6-hosts

                    list total-hosts {
                        key "counter";
                        description "Enter the total-hosts list instance";

                        leaf counter {
                            type types-submgt:submgt-statistics-total-type;
                            description "Type of submgt total hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list total-hosts

                    list sessions {
                        key "counter";
                        description "Enter the sessions list instance";

                        leaf counter {
                            type types-submgt:submgt-statistics-session-type;
                            description "Type of submgt sessions counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list sessions

                } // container statistics

            } // container subscriber-management

        } // list vpls

    } // grouping state-svc-vpls

}
