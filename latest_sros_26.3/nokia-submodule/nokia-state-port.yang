submodule nokia-state-port {

    yang-version "1.1";

    belongs-to nokia-state { prefix "state"; }

    import ietf-yang-types                { prefix "yang"; }
    import nokia-sros-yang-extensions     { prefix "sros-ext"; }
    import nokia-types-card               { prefix "types-card"; }
    import nokia-types-port               { prefix "types-port"; }
    import nokia-types-qos                { prefix "types-qos"; }
    import nokia-types-services           { prefix "types-services"; }
    import nokia-types-sros               { prefix "types-sros"; }
    import nokia-types-subscriber-mgmt    { prefix "types-submgt"; }

    include nokia-state-port-access;
    include nokia-state-port-dwdm;
    include nokia-state-port-ethernet;
    include nokia-state-port-gnss;
    include nokia-state-port-network;
    include nokia-state-port-otu;
    include nokia-state-port-serial;
    include nokia-state-port-sonet;
    include nokia-state-port-tdm;
    include nokia-state-qos;

    sros-ext:sros-major-release "rel26";
    organization "Nokia";
    contact
        "Nokia SR OS Support
         Web: <http://www.nokia.com>";
    description
        "Nokia YANG Data model with operational state for physical ports on SR OS based routers.

         Copyright 2016 Nokia. All rights reserved. Reproduction of this document
         is authorized on the condition that the foregoing copyright notice is included.

         This nokia-state-port YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-05-27";

    grouping state-port {
        list port {
            key "port-id";
            description "Enter the port list instance";

            leaf port-id {
                type types-sros:port;
                description "The identifier which uniquely identifies the port.";
            }

            leaf bundle-number {
                status obsolete;
                type uint32;
                description
                    "Indicates the bundle for which this port is a member.

                     If this port is not a member of any bundle, the value will be zero.";
            }

            leaf down-reason {
                type bits {
                    bit unknown                        { position 0; }
                    bit linkloss-fwd                   { position 1; }
                    bit lag-member-port-standby        { position 2; }
                    bit eth-cfm-fault                  { position 3; }
                    bit optical-tuning                 { position 4; }
                    bit frequency-out-of-range         { position 5; }
                    bit frequency-not-configured       { position 6; }
                    bit crc-error                      { position 7; }
                    bit internal-mac-tx-error          { position 8; }
                    bit efm-oam-down                   { position 9; }
                    bit sym-mon-error                  { position 10; }
                    bit oper-group-down                { position 11; }
                    bit sat-host-port-down             { position 12; }
                    bit sat-uplink-port-down           { position 13; }
                }
                description
                    "Indicates the reason for why the port is operationally down.

                     Values:
                         unknown                 - Unspecified (or unknown).
                         linkloss-fwd            - A sap using this port has an LLF
                                                   operational status set to 'fault'.
                         lag-member-port-standby - A lag using this port as a member
                                                   port has set the member port to
                                                   'standby' while configured to keep
                                                   standby member ports down.
                         eth-cfm-fault           - A facility MEP bound to this port
                                                   has its highest priority defect
                                                   set to a value other than 'none'.
                         optical-tuning          - The DWDM optical receive signal is
                                                   undergoing tuning and analysis by
                                                   control algorithms to find the
                                                   optimal settings.
                         frequency-out-of-range  - The configured DWDM optical frequency
                                                   is out of range for the equipped
                                                   tunable optical interface.
                         frequency-not-configured - The DWDM optical frequency is not
                                                   configured for the equipped
                                                   tunable optical interface.
                         crc-error               - CRC errors on the port exceeded the
                                                   configured threshold.
                         internal-mac-tx-error   - An internal MAC transmit error was
                                                   detected on the port.
                         efm-oam-down            - EFM OAM is not 'operational'.
                         sym-mon-error           - Symbol Monitor Errors on the port
                                                   exceeded the configured threshold.
                         oper-group-down         - The associated operational-group being
                                                   monitored has gone down.
                         sat-host-port-down      - The host port for this satellite
                                                   uplink port is down.
                         sat-uplink-port-down    - The active satellite uplink port for
                                                   this satellite client port is down.";
            }

            leaf far-end-port-id {
                type types-sros:port;
                description
                    "Indicates the port identifier of the far-end port that is connected
                     to this port.";
            }

            leaf fp-number {
                type uint32;
                description "Indicates the FP number of this port.";
            }

            leaf hardware-mac-address {
                type yang:mac-address;
                description
                    "Indicates the interface's hardware or system assigned MAC address at its
                     protocol sub-layer.  When user-assigned-mac has a value of
                     'true', the value of mac-address is used instead of
                     hardware-mac-address.";
            }

            leaf interface-group-handler-index {
                status obsolete;
                type uint32;
                description
                    "Indicates the index of the Interface Group Handler for the physical port.

                     If the port is not a member of an Interface Group Handler, the value will
                     be '0'.";
            }

            leaf mac-chip-number {
                type uint32;
                description "Indicates the MAC chip number of this port.";
            }

            leaf number-of-channels {
                type uint32;
                description "Indicates the number of the possible channels on the physical port.";
            }

            leaf oper-state {
                type types-port:port-oper-state;
                description "Indicates the current operational status of this port.";
            }

            leaf oper-state-last-changed {
                type yang:date-and-time;
                description
                    "Indicates the date and time when the operational status of
                     the port changed state.";
            }

            leaf otu-capable {
                type boolean;
                description
                    "Indicates whether or not the physical port supports Optical
                     Transport Unit (OTU) encapsulation.";
            }

            leaf physical-link {
                type boolean;
                description "Indicates whether or not the port has a physical link.";
            }

            leaf port-class {
                type types-port:port-class;
                description
                    "Indicates the class of port or optical pack installed. This can be derived
                     from /port/type.";
            }

            leaf port-state {
                type types-port:port-state;
                description
                    "Indicates the state level of this port. A value of 'none' indicates the
                     port is either in its initial creation state or is just about to
                     be deleted.  A value of 'ghost' represents a port that is not
                     physically present.  This state may represent a pre-provisioned
                     port.  A value of 'link-down' represents a port that is physically
                     present but does not have a link.  The 'link-up' state represents a
                     port that is physically present and has physical link present.
                     A port in 'up' state is ready to pass some kinds of traffic. The
                     'diagnose' state represents the port undergoing diagnostic test.";
            }

            leaf previous-state {
                type types-port:port-state;
                description
                    "Indicates the state that the port transitioned from, into  the current state
                     level of the port indicated by 'port-state'.";
            }

            leaf protocols-supported {
                type bits {
                    bit ipv4                           { position 0; }
                    bit mpls                           { position 1; }
                    bit bcp                            { position 2; }
                    bit iso                            { position 3; }
                    bit ipv6                           { position 8; }
                }
                description "Indicates a bitmap of what protocols can be used on this port.";
            }

            leaf type {
                type types-port:type;
                description "Indicates the type of port or optical pack installed.";
            }

            leaf user-assigned-mac {
                type boolean;
                description "Indicates whether or not mac-address has explicitly been set.";
            }

            leaf wavelength-tracker-capable {
                status obsolete;
                type boolean;
                description
                    "Indicates whether or not the physical port supports Wavelength
                     Tracker capabilities.

                     This leaf was obsoleted in release 22.2.";
            }

            leaf rs-fec-oper-mode {
                type enumeration {
                    enum none                           { value 0; }
                    enum cl91-514-528                   { value 1; }
                    enum cl91-514-544                   { value 2; }
                    enum cl74                           { value 3; }
                    enum cl108                          { value 4; }
                    enum cl119                          { value 5; }
                    enum cl134-514-544                  { value 6; }
                    enum cl172                          { value 7; }
                }
                description "Indicates the operational RS FEC mode of the port.";
            }

            leaf licensed {
                type boolean;
                description "Indicates whether or not the port is licensed.";
            }

            leaf if-index {
                type types-port:if-index;
                description
                    "Specifies the unique, non-zero, system assigned number for this port.
                     Corresponds to the ifIndex object in SNMP Interface MIB and can
                     be used for correlation of the port for access via YANG interfaces and
                     SNMP interfaces.";
            }

            container dist-cpu-protection {
                description "Enter the dist-cpu-protection context";

                container policer {
                    description "Enter the policer context";

                    list static-policer {
                        key "name card fp-number";
                        description "Enter the static-policer list instance";

                        leaf name {
                            type types-sros:named-item;
                            description "Name of static policer.";
                        }

                        leaf card {
                            type types-card:iom-card-slot;
                            description "IOM card within a chassis in the system.";
                        }

                        leaf fp-number {
                            type uint32 {
                                range "1..12";
                            }
                            description "Forwarding plane within a specific IOM card in the system.";
                        }

                        leaf state {
                            type types-services:dist-cpu-prot-policer-state;
                            description "State of the policer configured on Distributed CPU Protection Policy.";
                        }

                        leaf exceed-count {
                            type uint64;
                            description
                                "Number of packets exceeding the policing parameters since the given
                                 policer was previously declared as conformant or newly instantiated.";
                        }

                        leaf hold-down-remain {
                            type types-services:dist-cpu-prot-action-duration;
                            units "seconds";
                            description "Remaining hold-down period for a given policer.";
                        }

                        leaf detection-time-remain {
                            type uint32;
                            units "seconds";
                            description "Detection time remaining for a given policer.";
                        }

                        leaf total-exceed-count {
                            type uint64;
                            description "Total number of packets exceeding the policing parametersi.";
                        }

                        leaf exit-conform-state-count {
                            type uint32;
                            description "Total number of transition of the policer to the exceed state.";
                        }

                    } // list static-policer

                    list local-monitor-policer {
                        key "name card fp-number";
                        description "Enter the local-monitor-policer list instance";

                        leaf name {
                            type types-sros:named-item;
                            description "Name of local-monitor policer.";
                        }

                        leaf card {
                            type types-card:iom-card-slot;
                            description "IOM card within a chassis in the system.";
                        }

                        leaf fp-number {
                            type uint32 {
                                range "1..12";
                            }
                            description "Forwarding plane within a specific IOM card in the system.";
                        }

                        leaf state {
                            type types-services:dist-cpu-prot-policer-state;
                            description "State of the policer configured on Distributed CPU Protection Policy.";
                        }

                        leaf exceed-count {
                            type uint64;
                            description
                                "Number of packets exceeding the policing parameters since the given
                                 policer was previously declared as conformant or newly instantiated.";
                        }

                        leaf all-dynamic-policer-allocation {
                            type boolean;
                            description "All dynamic-policers allocation status";
                        }

                        leaf total-exceed-count {
                            type uint64;
                            description "Total number of packets exceeding the policing parametersi.";
                        }

                        leaf exit-conform-state-count {
                            type uint32;
                            description "Total number of transition of the policer to the exceed state.";
                        }

                    } // list local-monitor-policer

                    list dynamic-policer {
                        key "protocol card fp-number";
                        description "Enter the dynamic-policer list instance";

                        leaf protocol {
                            type types-sros:dist-cpu-protection-protocol;
                            description "Dynamic policer protocol.";
                        }

                        leaf card {
                            type types-card:iom-card-slot;
                            description "IOM card within a chassis in the system.";
                        }

                        leaf fp-number {
                            type uint32 {
                                range "1..12";
                            }
                            description "Forwarding plane within a specific IOM card in the system.";
                        }

                        leaf state {
                            type types-services:dist-cpu-prot-policer-state;
                            description "State of the policer configured on Distributed CPU Protection Policy.";
                        }

                        leaf exceed-count {
                            type uint64;
                            description
                                "Number of packets exceeding the policing parameters since the given
                                 policer was previously declared as conformant or newly instantiated.";
                        }

                        leaf hold-down-remain {
                            type types-services:dist-cpu-prot-action-duration;
                            units "seconds";
                            description "Remaining hold-down period for a given policer.";
                        }

                        leaf detection-time-remain {
                            type uint32;
                            units "seconds";
                            description "Detection time remaining for a given policer.";
                        }

                        leaf dynamic-policer-allocation {
                            type boolean;
                            description "Dynamic-policer allocation status";
                        }

                        leaf total-exceed-count {
                            type uint64;
                            description "Total number of packets exceeding the policing parametersi.";
                        }

                        leaf exit-conform-state-count {
                            type uint32;
                            description "Total number of transition of the policer to the exceed state.";
                        }

                    } // list dynamic-policer

                } // container policer

            } // container dist-cpu-protection

            container adapter {
                description "Enter the adapter context";

                leaf model-number {
                    type types-sros:named-item-255-or-empty;
                    description
                        "Indicates the model information for the adapter, as read from
                         the adapter EEPROM.

                         The string is expected to contain printable ASCII characters, but
                         unprintable ASCII characters read from the EEPROM are not
                         filtered out.";
                }

                leaf type {
                    type enumeration {
                        enum unknown                        { value 0; }
                        enum qsfp28-to-sfp+/sfp28           { value 1; }
                        enum cfp-to-qsfp28                  { value 2; }
                    }
                    description "Indicates the type of adapter for the port.";
                }

                leaf vendor-manufacture-date {
                    type yang:date-and-time;
                    description "Indicates the vendor's date code.";
                }

                leaf vendor-oui {
                    type string;
                    description
                        "Indicates the vendor's organizationally unique identifier field
                         (OUI) which contains the IEEE company identifier for the vendor.

                         A value of all zero indicates that the vendor OUI is unspecified.";
                }

                leaf vendor-part-number {
                    type types-sros:named-item-255-or-empty;
                    description
                        "Indicates the vendor's part number of the adapter (or product name)
                         in ASCII characters, as read from the adapter EEPROM.

                         An empty string indicates the vendor part number is unspecified.

                         The string is expected to contain printable ASCII characters, but
                         unprintable ASCII characters read from the EEPROM are not
                         filtered out.";
                }

                leaf vendor-serial-number {
                    type types-sros:named-item-255-or-empty;
                    description
                        "Indicates the vendor's serial number of the adapter in ASCII
                         characters, as read from the adapter EEPROM.

                         An empty string indicates the vendor serial number is unspecified.

                         The string is expected to contain printable ASCII characters,
                         but unprintable ASCII characters read from the EEPROM are not
                         filtered out.";
                }

            } // container adapter

            container transceiver {
                description "Enter the transceiver context";

                leaf connector-code {
                    type enumeration {
                        enum unknown                        { value 0; }
                        enum sc                             { value 1; }
                        enum fiber-channel-style1-copper-connector { value 2; }
                        enum fiber-channel-style2-copper-connector { value 3; }
                        enum bncortnc                       { value 4; }
                        enum fiber-channel-coaxial-headers  { value 5; }
                        enum fiber-jack                     { value 6; }
                        enum lc                             { value 7; }
                        enum mt-rj                          { value 8; }
                        enum mu                             { value 9; }
                        enum sg                             { value 10; }
                        enum optical-pigtail                { value 11; }
                        enum mpo1x12                        { value 12; }
                        enum mpo2x16                        { value 13; }
                        enum hssdcii                        { value 32; }
                        enum copper-pigtail                 { value 33; }
                        enum rj45                           { value 34; }
                        enum no-sep-conn                    { value 35; }
                        enum mxc2x16                        { value 36; }
                        enum cs                             { value 37; }
                        enum sn-opt-conn                    { value 38; }
                        enum mpo2x12                        { value 39; }
                        enum mpo1x16                        { value 40; }
                        enum optical-transceiver            { value 51; }
                        enum copper-gig-e                   { value 128; }
                        enum rjp5                           { value 129; }
                    }
                    description "Indicates the external connector provided on the interface.";
                }

                leaf connector-type {
                    type types-port:connector-type;
                    description "Indicates the type of connector installed in this port.";
                }

                leaf diagnostics-capable {
                    type enumeration {
                        enum not-applicable                 { value 0; }
                        enum true                           { value 1; }
                        enum false                          { value 2; }
                    }
                    description
                        "Indicates whether or not the transceiver is capable of doing
                         diagnostics.";
                }

                leaf equipped {
                    type boolean;
                    description "Indicates whether or not a transceiver is equipped in the port.";
                }

                leaf laser-wavelength {
                    type uint32;
                    description
                        "Indicates the light wavelength transmitted by the transceiver's laser.

                         A value of zero indicates that the port is not equipped with
                         the transceiver.

                         A value in the range of 1 to 2000 indicates that the units are in
                         nano-meters (nm). A value in the range of 850000 to 2000000
                         indicates that the units are in pico-meters (pm).";
                }

                leaf link-length-information {
                    type string {
                        length "17";
                    }
                    description
                        "Indicates the link length information stored in SFF (Small Form
                         Factor) EEPROMs.

                         This leaf is applicable only when the SFF is equipped.
                         Otherwise, all 6 bytes will have a value of '0'.";
                }

                leaf media {
                    type enumeration {
                        enum not-applicable                 { value 0; }
                        enum ethernet                       { value 1; }
                        enum sonet-sdh                      { value 2; }
                    }
                    description "Indicates the media supported for the SFF.";
                }

                leaf model-number {
                    type string {
                        length "0..255";
                    }
                    description
                        "Indicates the model information for the transceiver, as read from
                         the transceiver EEPROM.

                         For example, the string may contain the Nokia part number and CLEI
                         for the transceiver.

                         The string is expected to contain printable ASCII characters, but
                         unprintable ASCII characters read from the EEPROM are not
                         filtered out.";
                }

                leaf number-of-lanes {
                    type uint32;
                    description
                        "Indicates the total number of lanes supported by the SFF.

                         If the SFF is not equipped, this leaf will have a value of '0'.";
                }

                leaf oper-state {
                    type types-port:sff-status;
                    description "Indicates the operation status of the inserted SFF.";
                }

                leaf optical-compliance {
                    type string {
                        length "191";
                    }
                    description
                        "Indicates the 64 bytes of optical compliance bits stored in SFF
                         EEPROMs. This leaf is only applicable when the SFF is equipped.";
                }

                leaf optical-compliance-extension {
                    type types-port:optical-compliance-extention-type;
                    description
                        "Indicates the optical compliance extension stored in the SFF EEPROMs.

                         This leaf is only applicable when the SFF is equipped, and extends
                         /port/transceiver/optical-compliance.";
                }

                leaf sff-equipped {
                    type boolean;
                    description
                        "Indicates whether or not a Small Form Factor (SFF) is equipped
                         in the port.";
                }

                leaf type {
                    type enumeration {
                        enum unknown                        { value 0; }
                        enum gbic                           { value 1; }
                        enum module-connector-soldered-to-motherboard { value 2; }
                        enum sfp                            { value 3; }
                        enum xbi                            { value 4; }
                        enum xenpak                         { value 5; }
                        enum xfp                            { value 6; }
                        enum xff                            { value 7; }
                        enum xfpe                           { value 8; }
                        enum xpak                           { value 9; }
                        enum x2                             { value 10; }
                        enum dwdm-sfp                       { value 11; }
                        enum qsfp                           { value 12; }
                        enum qsfp-plus                      { value 13; }
                        enum cfp                            { value 14; }
                        enum cxp                            { value 15; }
                        enum oif-msa-100g-lh                { value 16; }
                        enum cfp2-or-qsfp28                 { value 17; }
                        enum cfp4                           { value 18; }
                        enum cdfp                           { value 19; }
                        enum cfp2-aco                       { value 20; }
                        enum cfp8                           { value 21; }
                        enum cdfp3                          { value 22; }
                        enum micro-qsfp                     { value 23; }
                        enum qsfp-dd                        { value 24; }
                        enum cfp2-dco                       { value 25; }
                        enum sfp-dd                         { value 26; }
                        enum dsfp                           { value 27; }
                        enum x4-minilink                    { value 28; }
                        enum x8-minilink                    { value 29; }
                        enum qsfp-plus-or-later-with-cmis   { value 30; }
                        enum sfp-dd-with-cmis               { value 31; }
                        enum sfp-plus-or-later-with-cmis    { value 32; }
                        enum osfp-xd-with-cmis              { value 33; }
                        enum oif-elsfp-with-cmis            { value 34; }
                        enum cdfp-x4-pcie-with-cmis         { value 35; }
                        enum cdfp-x8-pcie-with-cmis         { value 36; }
                        enum cdfp-x16-pcie-with-cmis        { value 37; }
                    }
                    description "Indicates the type of transceiver for the port.";
                }

                leaf vendor-manufacture-date {
                    type yang:date-and-time;
                    description "Indicates the vendor's date code.";
                }

                leaf vendor-oui {
                    type string;
                    description
                        "Indicates the vendor's organizationally unique identifier field
                         (OUI) which contains the IEEE company identifier for the vendor.

                         A value of all zero indicates that the vendor OUI is unspecified.";
                }

                leaf vendor-part-number {
                    type types-sros:named-item-255-or-empty;
                    description
                        "Indicates the vendor's part number of the transceiver (or product name)
                         in ASCII characters, as read from the transceiver EEPROM.

                         An empty string indicates the vendor part number is unspecified.

                         The string is expected to contain printable ASCII characters, but
                         unprintable ASCII characters read from the EEPROM are not
                         filtered out.";
                }

                leaf vendor-serial-number {
                    type types-sros:named-item-255-or-empty;
                    description
                        "Indicates the vendor's serial number of the transceiver in ASCII
                         characters, as read from the transceiver EEPROM.

                         An empty string indicates the vendor serial number is unspecified.

                         The string is expected to contain printable ASCII characters,
                         but unprintable ASCII characters read from the EEPROM are not
                         filtered out.";
                }

                leaf aui-resets {
                    type yang:counter64;
                    description "Indicates the number of AUI reset occurrences on the transceiver.";
                }

                leaf last-aui-reset {
                    type yang:date-and-time;
                    description "Indicates the last time an AUI reset occurred on the transceiver.";
                }

                container digital-diagnostic-monitoring {
                    description "Enter the digital-diagnostic-monitoring context";

                    leaf failed-thresholds {
                        type types-port:transceiver-ddm-failure-bits;
                        description
                            "Indicates which objects of the monitored transceiver is in a failed or
                             cleared threshold state. A set bit indicates that the specified threshold
                             has been exceeded.";
                    }

                    leaf calibrated {
                        type enumeration {
                            enum externally                     { value 1; }
                            enum internally                     { value 2; }
                        }
                        description "Indicates whether the transceiver was internally or externally calibrated.";
                    }

                    container temperature {
                        description "Enter the temperature context";

                        leaf current {
                            type decimal64 {
                                fraction-digits 1;
                            }
                            units "degrees celsius";
                            description "Indicates the current temperature of the transceiver.";
                        }

                        leaf high-alarm {
                            type decimal64 {
                                fraction-digits 1;
                            }
                            units "degrees celsius";
                            description
                                "Indicates the temperature that triggers a high alarm on the
                                 transceiver.";
                        }

                        leaf high-warning {
                            type decimal64 {
                                fraction-digits 1;
                            }
                            units "degrees celsius";
                            description
                                "Indicates the temperature that triggers a high warning on the
                                 transceiver.";
                        }

                        leaf low-alarm {
                            type decimal64 {
                                fraction-digits 1;
                            }
                            units "degrees celsius";
                            description
                                "Indicates the temperature that triggers a low alarm on the
                                 transceiver.";
                        }

                        leaf low-warning {
                            type decimal64 {
                                fraction-digits 1;
                            }
                            units "degrees celsius";
                            description
                                "Indicates the temperature that triggers a low warning on the
                                 transceiver.";
                        }

                    } // container temperature

                    container transmit-bias-current {
                        description "Enter the transmit-bias-current context";

                        leaf current {
                            type decimal64 {
                                fraction-digits 1;
                            }
                            units "microamperes";
                            description "Indicates the current transmit bias current of the transceiver.";
                        }

                        leaf high-alarm {
                            type decimal64 {
                                fraction-digits 1;
                            }
                            units "microamperes";
                            description
                                "Indicates the transmit bias current that triggers a high alarm on the
                                 transceiver.";
                        }

                        leaf high-warning {
                            type decimal64 {
                                fraction-digits 1;
                            }
                            units "microamperes";
                            description
                                "Indicates the transmit bias current that triggers a high warning on the
                                 transceiver.";
                        }

                        leaf low-alarm {
                            type decimal64 {
                                fraction-digits 1;
                            }
                            units "microamperes";
                            description
                                "Indicates the transmit bias current that triggers a low alarm on the
                                 transceiver.";
                        }

                        leaf low-warning {
                            type decimal64 {
                                fraction-digits 1;
                            }
                            units "microamperes";
                            description
                                "Indicates the transmit bias current that triggers a low warning on the
                                 transceiver.";
                        }

                    } // container transmit-bias-current

                    container transmit-output-power {
                        description "Enter the transmit-output-power context";

                        leaf current {
                            type decimal64 {
                                fraction-digits 2;
                            }
                            units "decibel-milliwatts";
                            description "Indicates the current transmit output power of the transceiver.";
                        }

                        leaf high-alarm {
                            type decimal64 {
                                fraction-digits 2;
                            }
                            units "decibel-milliwatts";
                            description
                                "Indicates the transmit output power that triggers a high alarm on the
                                 transceiver.";
                        }

                        leaf high-warning {
                            type decimal64 {
                                fraction-digits 2;
                            }
                            units "decibel-milliwatts";
                            description
                                "Indicates the transmit output power that triggers a high warning on the
                                 transceiver.";
                        }

                        leaf low-alarm {
                            type decimal64 {
                                fraction-digits 2;
                            }
                            units "decibel-milliwatts";
                            description
                                "Indicates the transmit output power that triggers a low alarm on the
                                 transceiver.";
                        }

                        leaf low-warning {
                            type decimal64 {
                                fraction-digits 2;
                            }
                            units "decibel-milliwatts";
                            description
                                "Indicates the transmit output power that triggers a low warning on the
                                 transceiver.";
                        }

                    } // container transmit-output-power

                    container received-optical-power {
                        description "Enter the received-optical-power context";

                        leaf current {
                            type decimal64 {
                                fraction-digits 2;
                            }
                            units "decibel-milliwatts";
                            description "Indicates the current received optical power of the transceiver.";
                        }

                        leaf high-alarm {
                            type decimal64 {
                                fraction-digits 2;
                            }
                            units "decibel-milliwatts";
                            description
                                "Indicates the received optical power that triggers a high alarm on the
                                 transceiver.";
                        }

                        leaf high-warning {
                            type decimal64 {
                                fraction-digits 2;
                            }
                            units "decibel-milliwatts";
                            description
                                "Indicates the received optical power that triggers a high warning on the
                                 transceiver.";
                        }

                        leaf low-alarm {
                            type decimal64 {
                                fraction-digits 2;
                            }
                            units "decibel-milliwatts";
                            description
                                "Indicates the received optical power that triggers a low alarm on the
                                 transceiver.";
                        }

                        leaf low-warning {
                            type decimal64 {
                                fraction-digits 2;
                            }
                            units "decibel-milliwatts";
                            description
                                "Indicates the received optical power that triggers a low warning on the
                                 transceiver.";
                        }

                        leaf type {
                            type enumeration {
                                enum oma                            { value 0; }
                                enum average                        { value 1; }
                            }
                            description
                                "Indicates whether the received-optical-power/current was taken
                                 as an average, or as an Optical Modulation Amplitude (OMA).";
                        }

                    } // container received-optical-power

                    container supply-voltage {
                        description "Enter the supply-voltage context";

                        leaf current {
                            type decimal64 {
                                fraction-digits 2;
                            }
                            units "volts";
                            description "Indicates the current supply voltage of the transceiver.";
                        }

                        leaf high-alarm {
                            type decimal64 {
                                fraction-digits 2;
                            }
                            units "volts";
                            description
                                "Indicates the supply voltage that triggers a high alarm on the
                                 transceiver.";
                        }

                        leaf high-warning {
                            type decimal64 {
                                fraction-digits 2;
                            }
                            units "volts";
                            description
                                "Indicates the supply voltage that triggers a high warning on the
                                 transceiver.";
                        }

                        leaf low-alarm {
                            type decimal64 {
                                fraction-digits 2;
                            }
                            units "volts";
                            description
                                "Indicates the supply voltage that triggers a low alarm on the
                                 transceiver.";
                        }

                        leaf low-warning {
                            type decimal64 {
                                fraction-digits 2;
                            }
                            units "volts";
                            description
                                "Indicates the supply voltage that triggers a low warning on the
                                 transceiver.";
                        }

                    } // container supply-voltage

                    container auxiliary-1 {
                        description "Enter the auxiliary-1 context";

                        leaf current {
                            type decimal64 {
                                fraction-digits 2;
                            }
                            description
                                "Indicates the current manufacturer specific auxiliary 1 of the
                                 transceiver.";
                        }

                        leaf high-alarm {
                            type decimal64 {
                                fraction-digits 2;
                            }
                            description
                                "Indicates the manufacturer specific auxiliary 1 that triggers a
                                 high alarm threshold on the transceiver.";
                        }

                        leaf high-warning {
                            type decimal64 {
                                fraction-digits 2;
                            }
                            description
                                "Indicates the manufacturer specific auxiliary 1 that triggers a
                                 high warning threshold on the transceiver.";
                        }

                        leaf low-alarm {
                            type decimal64 {
                                fraction-digits 2;
                            }
                            description
                                "Indicates the manufacturer specific auxiliary 1 that triggers a
                                 low alarm threshold on the transceiver.";
                        }

                        leaf low-warning {
                            type decimal64 {
                                fraction-digits 2;
                            }
                            description
                                "Indicates the manufacturer specific auxiliary 1 that triggers a
                                 low warning threshold on the transceiver.";
                        }

                        leaf type {
                            type types-port:transceiver-auxiliary-type;
                            description
                                "Indicates the measurement type of the manufacturer specific auxiliary
                                 1 information of the transceiver.";
                        }

                    } // container auxiliary-1

                    container auxiliary-2 {
                        description "Enter the auxiliary-2 context";

                        leaf current {
                            type decimal64 {
                                fraction-digits 2;
                            }
                            description
                                "Indicates the current manufacturer specific auxiliary 2 of the
                                 transceiver.";
                        }

                        leaf high-alarm {
                            type decimal64 {
                                fraction-digits 2;
                            }
                            description
                                "Indicates the manufacturer specific auxiliary 2 that triggers a
                                 high alarm threshold on the transceiver.";
                        }

                        leaf high-warning {
                            type decimal64 {
                                fraction-digits 2;
                            }
                            description
                                "Indicates the manufacturer specific auxiliary 2 that triggers a
                                 high warning threshold on the transceiver.";
                        }

                        leaf low-alarm {
                            type decimal64 {
                                fraction-digits 2;
                            }
                            description
                                "Indicates the manufacturer specific auxiliary 2 that triggers a
                                 low alarm threshold on the transceiver.";
                        }

                        leaf low-warning {
                            type decimal64 {
                                fraction-digits 2;
                            }
                            description
                                "Indicates the manufacturer specific auxiliary 2 that triggers a
                                 low warning threshold on the transceiver.";
                        }

                        leaf type {
                            type types-port:transceiver-auxiliary-type;
                            description
                                "Indicates the measurement type of the manufacturer specific auxiliary
                                 2 information of the transceiver.";
                        }

                    } // container auxiliary-2

                    container externally-calibrated {
                        description "Enter the externally-calibrated context";

                        leaf rx-power-4 {
                            type uint32;
                            description
                                "Indicates the Rx_PWR(4) value as specified in Table 3.16 in the SFF
                                 Committee Standard's document SFF-8472 Rev 10.2.";
                        }

                        leaf rx-power-3 {
                            type uint32;
                            description
                                "Indicates the Rx_PWR(3) value as specified in Table 3.16 in the SFF
                                 Committee Standard's document SFF-8472 Rev 10.2.";
                        }

                        leaf rx-power-2 {
                            type uint32;
                            description
                                "Indicates the Rx_PWR(2) value as specified in Table 3.16 in the SFF
                                 Committee Standard's document SFF-8472 Rev 10.2.";
                        }

                        leaf rx-power-1 {
                            type uint32;
                            description
                                "Indicates the Rx_PWR(1) value as specified in Table 3.16 in the SFF
                                 Committee Standard's document SFF-8472 Rev 10.2.";
                        }

                        leaf rx-power-0 {
                            type uint32;
                            description
                                "Indicates the Rx_PWR(0) value as specified in Table 3.16 in the SFF
                                 Committee Standard's document SFF-8472 Rev 10.2.";
                        }

                        container transmitted-laser-bias {
                            description "Enter the transmitted-laser-bias context";

                            leaf offset {
                                type int32 {
                                    range "-32767..32768";
                                }
                                description
                                    "Indicates the Tx_l(Offset) value as specified in Table 3.16 in the SFF
                                     Committee Standard's document SFF-8472 Rev 10.2.";
                            }

                            leaf slope {
                                type uint32 {
                                    range "0..65535";
                                }
                                description
                                    "Indicates the Tx_l(Slope) value as specified in Table 3.16 in the SFF
                                     Committee Standard's document SFF-8472 Rev 10.2.";
                            }

                        } // container transmitted-laser-bias

                        container transmitted-power {
                            description "Enter the transmitted-power context";

                            leaf offset {
                                type int32 {
                                    range "-32767..32768";
                                }
                                description
                                    "Indicates the Tx_PWR(Offset) value as specified in Table 3.16 in the SFF
                                     Committee Standard's document SFF-8472 Rev 10.2.";
                            }

                            leaf slope {
                                type uint32 {
                                    range "0..65535";
                                }
                                description
                                    "Indicates the Tx_PWR(Slope) value as specified in Table 3.16 in the SFF
                                     Committee Standard's document SFF-8472 Rev 10.2.";
                            }

                        } // container transmitted-power

                        container internal-temperature {
                            description "Enter the internal-temperature context";

                            leaf offset {
                                type int32 {
                                    range "-32767..32768";
                                }
                                description
                                    "Indicates the T(Offset) value as specified in Table 3.16 in the SFF
                                     Committee Standard's document SFF-8472 Rev 10.2.";
                            }

                            leaf slope {
                                type uint32 {
                                    range "0..65535";
                                }
                                description
                                    "Indicates the T(Slope) value as specified in Table 3.16 in the SFF
                                     Committee Standard's document SFF-8472 Rev 10.2.";
                            }

                        } // container internal-temperature

                        container internal-voltage {
                            description "Enter the internal-voltage context";

                            leaf offset {
                                type int32 {
                                    range "-32767..32768";
                                }
                                description
                                    "Indicates the V(Offset) value as specified in Table 3.16 in the SFF
                                     Committee Standard's document SFF-8472 Rev 10.2.";
                            }

                            leaf slope {
                                type uint32 {
                                    range "0..65535";
                                }
                                description
                                    "Indicates the V(Slope) value as specified in Table 3.16 in the SFF
                                     Committee Standard's document SFF-8472 Rev 10.2.";
                            }

                        } // container internal-voltage

                    } // container externally-calibrated

                    list lane {
                        key "lane-id";
                        description "Enter the lane list instance";

                        leaf lane-id {
                            type uint32 {
                                range "1..16";
                            }
                            description "Specifies the optical lane identifier.";
                        }

                        leaf failed-thresholds {
                            type types-port:transceiver-ddm-failure-bits;
                            description
                                "Indicates which objects of the monitored transceiver is in a failed or
                                 cleared threshold state. A set bit indicates that the specified threshold
                                 has been exceeded.";
                        }

                        leaf ish-errors {
                            type yang:counter64;
                            description
                                "Indicates the number of sync header errors (ISH) that occurred on this lane
                                 of the optic.";
                        }

                        container temperature {
                            description "Enter the temperature context";

                            leaf current {
                                type decimal64 {
                                    fraction-digits 1;
                                }
                                units "degrees celsius";
                                description "Indicates the current temperature of the transceiver.";
                            }

                            leaf high-alarm {
                                type decimal64 {
                                    fraction-digits 1;
                                }
                                units "degrees celsius";
                                description
                                    "Indicates the temperature that triggers a high alarm on the
                                     transceiver.";
                            }

                            leaf high-warning {
                                type decimal64 {
                                    fraction-digits 1;
                                }
                                units "degrees celsius";
                                description
                                    "Indicates the temperature that triggers a high warning on the
                                     transceiver.";
                            }

                            leaf low-alarm {
                                type decimal64 {
                                    fraction-digits 1;
                                }
                                units "degrees celsius";
                                description
                                    "Indicates the temperature that triggers a low alarm on the
                                     transceiver.";
                            }

                            leaf low-warning {
                                type decimal64 {
                                    fraction-digits 1;
                                }
                                units "degrees celsius";
                                description
                                    "Indicates the temperature that triggers a low warning on the
                                     transceiver.";
                            }

                        } // container temperature

                        container transmit-bias-current {
                            description "Enter the transmit-bias-current context";

                            leaf current {
                                type decimal64 {
                                    fraction-digits 1;
                                }
                                units "microamperes";
                                description "Indicates the current transmit bias current of the transceiver.";
                            }

                            leaf high-alarm {
                                type decimal64 {
                                    fraction-digits 1;
                                }
                                units "microamperes";
                                description
                                    "Indicates the transmit bias current that triggers a high alarm on the
                                     transceiver.";
                            }

                            leaf high-warning {
                                type decimal64 {
                                    fraction-digits 1;
                                }
                                units "microamperes";
                                description
                                    "Indicates the transmit bias current that triggers a high warning on the
                                     transceiver.";
                            }

                            leaf low-alarm {
                                type decimal64 {
                                    fraction-digits 1;
                                }
                                units "microamperes";
                                description
                                    "Indicates the transmit bias current that triggers a low alarm on the
                                     transceiver.";
                            }

                            leaf low-warning {
                                type decimal64 {
                                    fraction-digits 1;
                                }
                                units "microamperes";
                                description
                                    "Indicates the transmit bias current that triggers a low warning on the
                                     transceiver.";
                            }

                        } // container transmit-bias-current

                        container transmit-output-power {
                            description "Enter the transmit-output-power context";

                            leaf current {
                                type decimal64 {
                                    fraction-digits 2;
                                }
                                units "decibel-milliwatts";
                                description "Indicates the current transmit output power of the transceiver.";
                            }

                            leaf high-alarm {
                                type decimal64 {
                                    fraction-digits 2;
                                }
                                units "decibel-milliwatts";
                                description
                                    "Indicates the transmit output power that triggers a high alarm on the
                                     transceiver.";
                            }

                            leaf high-warning {
                                type decimal64 {
                                    fraction-digits 2;
                                }
                                units "decibel-milliwatts";
                                description
                                    "Indicates the transmit output power that triggers a high warning on the
                                     transceiver.";
                            }

                            leaf low-alarm {
                                type decimal64 {
                                    fraction-digits 2;
                                }
                                units "decibel-milliwatts";
                                description
                                    "Indicates the transmit output power that triggers a low alarm on the
                                     transceiver.";
                            }

                            leaf low-warning {
                                type decimal64 {
                                    fraction-digits 2;
                                }
                                units "decibel-milliwatts";
                                description
                                    "Indicates the transmit output power that triggers a low warning on the
                                     transceiver.";
                            }

                        } // container transmit-output-power

                        container received-optical-power {
                            description "Enter the received-optical-power context";

                            leaf current {
                                type decimal64 {
                                    fraction-digits 2;
                                }
                                units "decibel-milliwatts";
                                description "Indicates the current received optical power of the transceiver.";
                            }

                            leaf high-alarm {
                                type decimal64 {
                                    fraction-digits 2;
                                }
                                units "decibel-milliwatts";
                                description
                                    "Indicates the received optical power that triggers a high alarm on the
                                     transceiver.";
                            }

                            leaf high-warning {
                                type decimal64 {
                                    fraction-digits 2;
                                }
                                units "decibel-milliwatts";
                                description
                                    "Indicates the received optical power that triggers a high warning on the
                                     transceiver.";
                            }

                            leaf low-alarm {
                                type decimal64 {
                                    fraction-digits 2;
                                }
                                units "decibel-milliwatts";
                                description
                                    "Indicates the received optical power that triggers a low alarm on the
                                     transceiver.";
                            }

                            leaf low-warning {
                                type decimal64 {
                                    fraction-digits 2;
                                }
                                units "decibel-milliwatts";
                                description
                                    "Indicates the received optical power that triggers a low warning on the
                                     transceiver.";
                            }

                            leaf type {
                                type enumeration {
                                    enum oma                            { value 0; }
                                    enum average                        { value 1; }
                                }
                                description
                                    "Indicates whether the received-optical-power/current was taken
                                     as an average, or as an Optical Modulation Amplitude (OMA).";
                            }

                        } // container received-optical-power

                    } // list lane

                } // container digital-diagnostic-monitoring

            } // container transceiver

            container statistics {
                description "Enter the statistics context";

                leaf counter-discontinuity-time {
                    type yang:date-and-time;
                    description
                        "Indicates the sysUpTime on the most recent occasion at which
                         any one or more of this interface's counters suffered a
                         discontinuity.  The relevant counters are the specific
                         instances associated with port statistics. If no such
                         discontinuities have occurred since the last re-initialization
                         of the local management subsystem, then this object contains a
                         zero value.";
                }

                leaf last-cleared-time {
                    type yang:date-and-time;
                    description
                        "Indicates the time, since system startup, when the counters in
                         IF-MIB::ifTable were last cleared.";
                }

                leaf in-discards {
                    type yang:counter64;
                    description
                        "Indicates the number of inbound packets which were chosen to be
                         discarded even though no errors had been detected to prevent
                         their being deliverable to a higher-layer protocol.  One
                         possible reason for discarding such a packet could be to
                         free up buffer space.

                         Discontinuities in the value of this counter can occur at
                         re-initialization of the management system, and at other
                         times as indicated by the value of
                         counter-discontinuity-time.";
                }

                leaf in-errors {
                    type yang:counter64;
                    description
                        "Indicates for packet-oriented interfaces, the number of inbound
                         packets that contained errors preventing them from being
                         deliverable to a higher-layer protocol.  For character-
                         oriented or fixed-length interfaces, the number of inbound
                         transmission units that contained errors preventing them
                         from being deliverable to a higher-layer protocol.

                         Discontinuities in the value of this counter can occur at
                         re-initialization of the management system, and at other
                         times as indicated by the value of
                         counter-discontinuity-time.";
                }

                leaf in-octets {
                    type yang:counter64;
                    description
                        "Indicates the total number of octets received on the interface,
                         including framing characters.

                         Discontinuities in the value of this counter can occur at
                         re-initialization of the management system, and at other
                         times as indicated by the value of
                         counter-discontinuity-time.";
                }

                leaf in-packets {
                    type yang:counter64;
                    description
                        "Indicates the total number of packets received on the interface,
                         including framing characters.

                         Discontinuities in the value of this counter can occur at
                         re-initialization of the management system, and at other
                         times as indicated by the value of
                         counter-discontinuity-time.";
                }

                leaf in-unknown-protocol-discards {
                    type yang:counter64;
                    description
                        "Indicates for packet-oriented interfaces, the number of packets
                         received via the interface which were discarded because of
                         an unknown or unsupported protocol.  For character-oriented
                         or fixed-length interfaces that support protocol
                         multiplexing the number of transmission units received via
                         the interface which were discarded because of an unknown or
                         unsupported protocol.  For any interface that does not
                         support protocol multiplexing, this counter will always be
                         0.

                         Discontinuities in the value of this counter can occur at
                         re-initialization of the management system, and at other
                         times as indicated by the value of
                         counter-discontinuity-time.";
                }

                leaf in-broadcast-packets {
                    type yang:counter64;
                    description
                        "Indicates the number of packets, delivered by this sub-layer to a
                         higher (sub-)layer, which were addressed to a broadcast
                         address at this sub-layer.

                         Discontinuities in the value of this counter can occur at
                         re-initialization of the management system, and at other
                         times as indicated by the value of
                         counter-discontinuity-time.";
                }

                leaf in-multicast-packets {
                    type yang:counter64;
                    description
                        "Indicates the number of packets, delivered by this sub-layer to a
                         higher (sub-)layer, which were addressed to a multicast
                         address at this sub-layer.  For a MAC layer protocol, this
                         includes both Group and Functional addresses.

                         Discontinuities in the value of this counter can occur at
                         re-initialization of the management system, and at other
                         times as indicated by the value of
                         counter-discontinuity-time.";
                }

                leaf in-unicast-packets {
                    type yang:counter64;
                    description
                        "Indicates the number of packets, delivered by this sub-layer to a
                         higher (sub-)layer, which were not addressed to a multicast
                         or broadcast address at this sub-layer.

                         Discontinuities in the value of this counter can occur at
                         re-initialization of the management system, and at other
                         times as indicated by the value of
                         counter-discontinuity-time.";
                }

                leaf out-discards {
                    type yang:counter64;
                    description
                        "Indicates the number of outbound packets which were chosen to be
                         discarded even though no errors had been detected to prevent
                         their being transmitted.  One possible reason for discarding
                         such a packet could be to free up buffer space.

                         Discontinuities in the value of this counter can occur at
                         re-initialization of the management system, and at other
                         times as indicated by the value of
                         counter-discontinuity-time.";
                }

                leaf out-errors {
                    type yang:counter64;
                    description
                        "Indicates for packet-oriented interfaces, the number of outbound
                         packets that could not be transmitted because of errors.
                         For character-oriented or fixed-length interfaces, the
                         number of outbound transmission units that could not be
                         transmitted because of errors.

                         Discontinuities in the value of this counter can occur at
                         re-initialization of the management system, and at other
                         times as indicated by the value of
                         counter-discontinuity-time.";
                }

                leaf out-octets {
                    type yang:counter64;
                    description
                        "Indicates the total number of octets transmitted out of the
                         interface, including framing characters.

                         Discontinuities in the value of this counter can occur at
                         re-initialization of the management system, and at other
                         times as indicated by the value of
                         counter-discontinuity-time.";
                }

                leaf out-packets {
                    type yang:counter64;
                    description
                        "Indicates the total number of packets transmitted out of the
                         interface, including framing characters.

                         Discontinuities in the value of this counter can occur at
                         re-initialization of the management system, and at other
                         times as indicated by the value of
                         counter-discontinuity-time.";
                }

                leaf out-broadcast-packets {
                    type yang:counter64;
                    description
                        "Indicates the total number of packets that higher-level protocols
                         requested be transmitted, and which were addressed to a
                         broadcast address at this sub-layer, including those that
                         were discarded or not sent.

                         Discontinuities in the value of this counter can occur at
                         re-initialization of the management system, and at other
                         times as indicated by the value of
                         counter-discontinuity-time.";
                }

                leaf out-multicast-packets {
                    type yang:counter64;
                    description
                        "Indicates the total number of packets that higher-level protocols
                         requested be transmitted, and which were addressed to a
                         multicast address at this sub-layer, including those that
                         were discarded or not sent.  For a MAC layer protocol, this
                         includes both Group and Functional addresses.

                         Discontinuities in the value of this counter can occur at
                         re-initialization of the management system, and at other
                         times as indicated by the value of
                         counter-discontinuity-time.";
                }

                leaf out-unicast-packets {
                    type yang:counter64;
                    description
                        "Indicates the total number of packets that higher-level protocols
                         requested be transmitted, and which were not addressed to a
                         multicast or broadcast address at this sub-layer, including
                         those that were discarded or not sent.

                         Discontinuities in the value of this counter can occur at
                         re-initialization of the management system, and at other
                         times as indicated by the value of
                         counter-discontinuity-time.";
                }

                container egress-queue {
                    description "Enter the egress-queue context";

                    list queue {
                        key "queue-id";
                        description "Enter the queue list instance";

                        leaf queue-id {
                            type types-qos:egress-queue-id;
                            description "The unique identifier for the queue.";
                        }

                        leaf forward-unicast-packets {
                            type yang:counter64;
                            description "The number of unicast packets forwarded.";
                        }

                        leaf drop-unicast-packets {
                            type yang:counter64;
                            description "The number of unicast packets dropped.";
                        }

                        leaf forward-multicast-packets {
                            type yang:counter64;
                            description "The number of multicast packets forwarded.";
                        }

                        leaf drop-multicast-packets {
                            type yang:counter64;
                            description "The number of multicast packets dropped.";
                        }

                        leaf pipeline-drop-unicast-packets {
                            type yang:counter64;
                            description "The number of pipeline unicast packets dropped.";
                        }

                        leaf pipeline-drop-multicast-packets {
                            type yang:counter64;
                            description "The number of pipeline multicast packets dropped.";
                        }

                        leaf forward-unicast-octets {
                            type yang:counter64;
                            description "The number of unicast octets forwarded.";
                        }

                        leaf drop-unicast-octets {
                            type yang:counter64;
                            description "The number of unicast octets dropped.";
                        }

                        leaf forward-multicast-octets {
                            type yang:counter64;
                            description "The number of multicast octets forwarded.";
                        }

                        leaf drop-multicast-octets {
                            type yang:counter64;
                            description "The number of multicast octets dropped.";
                        }

                        leaf pipeline-drop-unicast-octets {
                            type yang:counter64;
                            description "The number of pipeline unicast octets dropped.";
                        }

                        leaf pipeline-drop-multicast-octets {
                            type yang:counter64;
                            description "The number of pipeline multicast octets dropped.";
                        }

                    } // list queue

                    list satellite-queue {
                        key "queue-id";
                        description "Enter the satellite-queue list instance";

                        leaf queue-id {
                            type types-qos:egress-queue-id;
                            description "The unique identifier for the queue.";
                        }

                        leaf satellite-forward-packets {
                            type yang:counter64;
                            description "The number of egress packets forwarded by the satellite port.";
                        }

                        leaf satellite-drop-packets {
                            type yang:counter64;
                            description "The number of egress packets dropped by the satellite port.";
                        }

                        leaf satellite-forward-octets {
                            type yang:counter64;
                            description "The number of egress octets forwarded by the satellite port.";
                        }

                        leaf satellite-drop-octets {
                            type yang:counter64;
                            description "The number of egress octets dropped by the satellite port.";
                        }

                    } // list satellite-queue

                } // container egress-queue

                container aggregate-queue {
                    description "Enter the aggregate-queue context";

                    leaf last-cleared-time {
                        type yang:date-and-time;
                        description
                            "Indicates the time, since system startup, when the counters in
                             TIMETRA-PORT-MIB::tmnxPortAggQueueStatsTable were last cleared.";
                    }

                    leaf last-fetched-time {
                        type yang:date-and-time;
                        description
                            "Indicates the time, since system startup, when the counters in TIMETRA-PORT-MIB::tmnxPortAggQueueStatsTable
                             were last fetched.";
                    }

                    leaf ingress-forward-packets {
                        type yang:counter64;
                        description "Indicates the number of ingress packets forwarded by all queues on this port.";
                    }

                    leaf ingress-forward-octets {
                        type yang:counter64;
                        description "Indicates the number of ingress octets forwarded by all queues on this port.";
                    }

                    leaf egress-forward-packets {
                        type yang:counter64;
                        description "Indicates the number of egress packets forwarded by all queues on this port.";
                    }

                    leaf egress-forward-octets {
                        type yang:counter64;
                        description "Indicates the number of egress octets forwarded by all queues on this port.";
                    }

                    leaf ingress-drop-packets {
                        type yang:counter64;
                        description "Indicates the number of dropped ingress packets by all queues on this port.";
                    }

                    leaf ingress-drop-octets {
                        type yang:counter64;
                        description "Indicates the number of dropped ingress octets by all queues on this port.";
                    }

                    leaf egress-drop-packets {
                        type yang:counter64;
                        description "Indicates the number of dropped egress packets by all queues on this port.";
                    }

                    leaf egress-drop-octets {
                        type yang:counter64;
                        description "Indicates the number of dropped egress octets by all queues on this port.";
                    }

                } // container aggregate-queue

            } // container statistics

            container egress {
                description "Enter the egress context";

                list voq {
                    key "queue-id";
                    description "Enter the voq list instance";

                    leaf queue-id {
                        type uint32 {
                            range "1..8";
                        }
                        description "The identifier which uniquely identifies a port egress queue for the port.";
                    }

                    leaf forward-in-prof-packets {
                        type yang:counter64;
                        description "The number of in-profile packets forwarded.";
                    }

                    leaf drop-in-prof-packets {
                        type yang:counter64;
                        description "The number of in-profile packets dropped.";
                    }

                    leaf forward-out-prof-packets {
                        type yang:counter64;
                        description "The number of out-profile packets forwarded.";
                    }

                    leaf drop-out-prof-packets {
                        type yang:counter64;
                        description "The number of out-profile packets dropped.";
                    }

                    leaf forward-in-prof-octets {
                        type yang:counter64;
                        description "The number of in-profile octets forwarded.";
                    }

                    leaf drop-in-prof-octets {
                        type yang:counter64;
                        description "The number of in-profile octets dropped.";
                    }

                    leaf forward-out-prof-octets {
                        type yang:counter64;
                        description "The number of out-profile octets forwarded.";
                    }

                    leaf drop-out-prof-octets {
                        type yang:counter64;
                        description "The number of out-profile octets dropped.";
                    }

                    leaf forward-exd-prof-packets {
                        type yang:counter64;
                        description "The number of exceed profile packets forwarded.";
                    }

                    leaf drop-excd-prof-packets {
                        type yang:counter64;
                        description "The number of exceed profile packets dropped.";
                    }

                    leaf forward-exd-prof-octets {
                        type yang:counter64;
                        description "The number of exceed profile octets forwarded.";
                    }

                    leaf drop-excd-prof-octets {
                        type yang:counter64;
                        description "The number of exceed profile octets dropped.";
                    }

                    leaf forward-inplus-prof-packets {
                        type yang:counter64;
                        description "The number of in-plus profile packets forwarded.";
                    }

                    leaf drop-inplus-prof-packets {
                        type yang:counter64;
                        description "The number of in-plus profile packets dropped.";
                    }

                    leaf forward-inplus-prof-octets {
                        type yang:counter64;
                        description "The number of in-plus profile octets forwarded.";
                    }

                    leaf drop-inplus-prof-octets {
                        type yang:counter64;
                        description "The number of in-plus profile octets dropped.";
                    }

                    leaf forward-packets {
                        type yang:counter64;
                        description "The number of forward packets.";
                    }

                    leaf drop-packets {
                        type yang:counter64;
                        description "The number of drop packets.";
                    }

                    leaf forward-octets {
                        type yang:counter64;
                        description "The number of forward octets.";
                    }

                    leaf drop-octets {
                        type yang:counter64;
                        description "The number of drop octets.";
                    }

                } // list voq

                container state {
                    description "Enter the state context";

                    list queue {
                        key "queue-id";
                        description "Enter the queue list instance";

                        leaf queue-id {
                            type types-qos:egress-queue-id;
                            description "The unique identifier for the queue.";
                        }

                        leaf admin-pir {
                            type uint32;
                            units "kilobps";
                            description "Specifies the administrative PIR.";
                        }

                        leaf oper-pir {
                            type uint32;
                            units "kilobps";
                            description "Specifies the administrative PIR.";
                        }

                        leaf admin-cir {
                            type uint32;
                            units "kilobps";
                            description "Specifies the administrative CIR.";
                        }

                        leaf oper-cir {
                            type uint32;
                            units "kilobps";
                            description "Specifies the administrative CIR.";
                        }

                        leaf admin-pir-weight {
                            type uint32;
                            description "Specifies the administrative pir weight.";
                        }

                        leaf oper-pir-weight {
                            type uint32;
                            description "Specifies the operational pir weight.";
                        }

                        leaf admin-mbs {
                            type uint32;
                            description "Specifies the administrative mbs.";
                        }

                        leaf oper-mbs {
                            type uint32;
                            description "Specifies the operational mbs.";
                        }

                        list slot {
                            key "slot-num";
                            description "Enter the slot list instance";

                            leaf slot-num {
                                type uint32;
                                description "Slot number.";
                            }

                            list unit {
                                key "unit-num";
                                description "Enter the unit list instance";

                                leaf unit-num {
                                    type uint32;
                                    description "Unit number.";
                                }

                                list core {
                                    key "core-num";
                                    description "Enter the core list instance";

                                    leaf core-num {
                                        type uint32;
                                        description "Core number.";
                                    }

                                    leaf depth-bytes {
                                        type uint32;
                                        description "Specifies the depth bytes.";
                                    }

                                    leaf depth-buffers {
                                        type uint32;
                                        description "Specifies the depth buffers.";
                                    }

                                } // list core

                            } // list unit

                        } // list slot

                    } // list queue

                } // container state

            } // container egress

            container subscriber-management {
                description "Enter the subscriber-management context";

                container statistics {
                    description "Enter the statistics context";

                    leaf last-reset-peak-values {
                        type yang:date-and-time;
                        description "Timestamp of the last reset of the peak values";
                    }

                    list ipv4-hosts {
                        key "counter";
                        description "Enter the ipv4-hosts list instance";

                        leaf counter {
                            type types-submgt:submgt-statistics-ipv4-type;
                            description "Type of submgt ipv4 hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list ipv4-hosts

                    list ipv6-hosts {
                        key "counter";
                        description "Enter the ipv6-hosts list instance";

                        leaf counter {
                            type types-submgt:submgt-statistics-ipv6-type;
                            description "Type of submgt ipv6 hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list ipv6-hosts

                    list total-hosts {
                        key "counter";
                        description "Enter the total-hosts list instance";

                        leaf counter {
                            type types-submgt:submgt-statistics-total-type;
                            description "Type of submgt total hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list total-hosts

                    list sessions {
                        key "counter";
                        description "Enter the sessions list instance";

                        leaf counter {
                            type types-submgt:submgt-statistics-session-type;
                            description "Type of submgt sessions counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list sessions

                } // container statistics

                list svlan {
                    key "vlan-id";
                    description "Enter the svlan list instance";

                    leaf vlan-id {
                        type uint32 {
                            range "0..4094";
                        }
                        description "The VLAN identifier.";
                    }

                    leaf active-subscriber-hosts {
                        type yang:counter32;
                        description "The number of active subscriber hosts on this port and VLAN.";
                    }

                    container statistics {
                        description "Enter the statistics context";

                        leaf last-cleared-time {
                            type yang:date-and-time;
                            description "The time when the counters were last cleared.";
                        }

                        leaf ingress-packets {
                            type yang:counter64;
                            description "The number of IP packets received through this port and VLAN.";
                        }

                        leaf ingress-octets {
                            type yang:counter64;
                            description "The number of octets in IP packets received through this port and VLAN.";
                        }

                        leaf egress-packets {
                            type yang:counter64;
                            description "The number of IP packets sent through this port and VLAN.";
                        }

                        leaf egress-octets {
                            type yang:counter64;
                            description "The number of octets in IP packets sent through this port and VLAN.";
                        }

                    } // container statistics

                } // list svlan

            } // container subscriber-management

            container vlan-qos {
                description "Enter the vlan-qos context";

                container statistics {
                    description "Enter the statistics context";

                    list vlan-qos-policy {
                        key "policy-name";
                        description "Enter the vlan-qos-policy list instance";

                        leaf policy-name {
                            type leafref {
                                path "../../../../../qos/vlan-qos-policy/vlan-qos-policy-name";
                            }
                            description "Vlan QOS policy name";
                        }

                        list queue {
                            key "queue-id";
                            description "Enter the queue list instance";

                            leaf queue-id {
                                type types-qos:egress-queue-id;
                                description "The unique identifier for the queue.";
                            }

                            leaf forwarded-packets {
                                type yang:counter64;
                                description "The number of forward packets.";
                            }

                            leaf dropped-packets {
                                type yang:counter64;
                                description "The number of drop packets.";
                            }

                            leaf forwarded-octets {
                                type yang:counter64;
                                description "The number of forward octets.";
                            }

                            leaf dropped-octets {
                                type yang:counter64;
                                description "The number of drop octets.";
                            }

                            leaf forward-in-prof-packets {
                                type yang:counter64;
                                description "The number of in-profile packets forwarded.";
                            }

                            leaf drop-in-prof-packets {
                                type yang:counter64;
                                description "The number of in-profile packets dropped.";
                            }

                            leaf forward-out-prof-packets {
                                type yang:counter64;
                                description "The number of out-profile packets forwarded.";
                            }

                            leaf drop-out-prof-packets {
                                type yang:counter64;
                                description "The number of out-profile packets dropped.";
                            }

                            leaf forward-in-prof-octets {
                                type yang:counter64;
                                description "The number of in-profile octets forwarded.";
                            }

                            leaf drop-in-prof-octets {
                                type yang:counter64;
                                description "The number of in-profile octets dropped.";
                            }

                            leaf forward-out-prof-octets {
                                type yang:counter64;
                                description "The number of out-profile octets forwarded.";
                            }

                            leaf drop-out-prof-octets {
                                type yang:counter64;
                                description "The number of out-profile octets dropped.";
                            }

                            leaf forward-excd-prof-packets {
                                type yang:counter64;
                                description "The number of exceed profile packets forwarded.";
                            }

                            leaf drop-excd-prof-packets {
                                type yang:counter64;
                                description "The number of exceed profile packets dropped.";
                            }

                            leaf forward-excd-prof-octets {
                                type yang:counter64;
                                description "The number of exceed profile octets forwarded.";
                            }

                            leaf drop-excd-prof-octets {
                                type yang:counter64;
                                description "The number of exceed profile octets dropped.";
                            }

                            leaf forward-inplus-prof-packets {
                                type yang:counter64;
                                description "The number of in-plus profile packets forwarded.";
                            }

                            leaf drop-inplus-prof-packets {
                                type yang:counter64;
                                description "The number of in-plus profile packets dropped.";
                            }

                            leaf forward-inplus-prof-octets {
                                type yang:counter64;
                                description "The number of in-plus profile octets forwarded.";
                            }

                            leaf drop-inplus-prof-octets {
                                type yang:counter64;
                                description "The number of in-plus profile octets dropped.";
                            }

                        } // list queue

                    } // list vlan-qos-policy

                } // container statistics

                container state {
                    description "Enter the state context";

                    list vlan-qos-policy {
                        key "policy-name";
                        description "Enter the vlan-qos-policy list instance";

                        leaf policy-name {
                            type leafref {
                                path "../../../../../qos/vlan-qos-policy/vlan-qos-policy-name";
                            }
                            description "Vlan QOS policy name";
                        }

                        list queue {
                            key "queue-id";
                            description "Enter the queue list instance";

                            leaf queue-id {
                                type types-qos:egress-queue-id;
                                description "The unique identifier for the queue.";
                            }

                            leaf admin-pir {
                                type uint32;
                                units "kilobps";
                                description "Specifies the administrative PIR.";
                            }

                            leaf oper-pir {
                                type uint32;
                                units "kilobps";
                                description "Specifies the administrative PIR.";
                            }

                            leaf admin-cir {
                                type uint32;
                                units "kilobps";
                                description "Specifies the administrative CIR.";
                            }

                            leaf oper-cir {
                                type uint32;
                                units "kilobps";
                                description "Specifies the administrative CIR.";
                            }

                            leaf admin-pir-weight {
                                type uint32;
                                description "Specifies the administrative pir weight.";
                            }

                            leaf oper-pir-weight {
                                type uint32;
                                description "Specifies the operational pir weight.";
                            }

                            leaf admin-mbs {
                                type uint32;
                                description "Specifies the administrative mbs.";
                            }

                            leaf oper-mbs {
                                type uint32;
                                description "Specifies the operational mbs.";
                            }

                            list slot {
                                key "slot-num";
                                description "Enter the slot list instance";

                                leaf slot-num {
                                    type uint32;
                                    description "Slot number.";
                                }

                                list unit {
                                    key "unit-num";
                                    description "Enter the unit list instance";

                                    leaf unit-num {
                                        type uint32;
                                        description "Unit number.";
                                    }

                                    list core {
                                        key "core-num";
                                        description "Enter the core list instance";

                                        leaf core-num {
                                            type uint32;
                                            description "Core number.";
                                        }

                                        leaf depth-bytes {
                                            type uint32;
                                            description "Specifies the depth bytes.";
                                        }

                                        leaf depth-buffers {
                                            type uint32;
                                            description "Specifies the depth buffers.";
                                        }

                                    } // list core

                                } // list unit

                            } // list slot

                        } // list queue

                    } // list vlan-qos-policy

                } // container state

            } // container vlan-qos

            container forwarding-engine {
                description "Enter the forwarding-engine context";

                container ingress {
                    description "Enter the ingress context";

                    container drop-reason {
                        description "Enter the drop-reason context";

                        leaf ipv4-header-error {
                            type yang:counter64;
                            description "Error in IPv4 packet header";
                        }

                        leaf ipv4-invalid-address {
                            type yang:counter64;
                            description "Error in IPv4 source or destination address";
                        }

                        leaf ipv6-header-error {
                            type yang:counter64;
                            description "Error in IPv6 packet header";
                        }

                        leaf ipv6-invalid-address {
                            type yang:counter64;
                            description "Error in IPv6 source or destination address";
                        }

                        leaf ip-route-blackholed {
                            type yang:counter64;
                            description "IP address matched a black hole route";
                        }

                        leaf acl-filter-discards {
                            type yang:counter64;
                            description "Drops due to ACL filters on the line card";
                        }

                        leaf unicast-rpf-check-failed {
                            type yang:counter64;
                            description "IP packet failed the unicast reverse path forwarding (uRPF) check";
                        }

                        leaf bfd-spoof-check-failed {
                            type yang:counter64;
                            description
                                "BFD packet either failed the TTL check or failed the source IP address
                                 lookup of known sessions";
                        }

                        leaf unicast-dest-mac-address-mismatch {
                            type yang:counter64;
                            description "Unicast Destination MAC address not known";
                        }

                        leaf mcast-mac-unicast-ip {
                            type yang:counter64;
                            description "Destination MAC is multicast but the IP address is unicast";
                        }

                        leaf unknown-dest-mac-vpls-discard {
                            type yang:counter64;
                            description
                                "Destination MAC address lookup failed and VPLS set to discard unknown
                                 destination MAC frames";
                        }

                        leaf l2-service-mtu-exceeded {
                            type yang:counter64;
                            description
                                "Length of the packet received on a SAP bound to a Layer 2 service exceeded
                                 the configured MTU for the service";
                        }

                        leaf drop-needs-icmp {
                            type yang:counter64;
                            description "Drop of packet required generation of ICMP message";
                        }

                        leaf unknown-labeled-packet {
                            type yang:counter64;
                            description "Unknown label (ILM lookup failure) or unexpected service label";
                        }

                    } // container drop-reason

                } // container ingress

            } // container forwarding-engine

            container cem {
                description "Enter the cem context";

                leaf current-alarms {
                    type types-port:cem-report-alarms;
                    description "Indicates the current CEM alarms on the port.";
                }

                container statistics {
                    description "Enter the statistics context";

                    container ingress {
                        description "Enter the ingress context";

                        leaf forwarded-packets {
                            type yang:counter32;
                            description "Number of packets successfully forwarded.";
                        }

                        leaf ingress-dropped-packets {
                            type yang:counter32;
                            description "Number of packets dropped due to errors.";
                        }

                    } // container ingress

                    container egress {
                        description "Enter the egress context";

                        leaf forwarded-packets {
                            type yang:counter32;
                            description "Number of packets successfully forwarded.";
                        }

                        leaf dropped-packets {
                            type yang:counter32;
                            description "Number of packets dropped due to errors.";
                        }

                        leaf missing-packets {
                            type yang:counter32;
                            description "Number of missing packets.";
                        }

                        leaf packets-reorder {
                            type yang:counter32;
                            description "Number of packets detected out of sequence but successfully re-ordered.";
                        }

                        leaf jitter-buffer-underruns {
                            type yang:counter32;
                            description
                                "Number of times a packet needed to be played out and the jitter buffer
                                 was empty.";
                        }

                        leaf jitter-buffer-overruns {
                            type yang:counter32;
                            description
                                "Number of times a packet was dropped because it could not fit in the
                                 jitter buffer.";
                        }

                        leaf misorder-dropped {
                            type yang:counter32;
                            description
                                "Number of packets detected out of order and could not be re-ordered, or
                                 could not be placed in the jitter buffer because it was out of the
                                 current window.";
                        }

                        leaf malformed-packets {
                            type yang:counter32;
                            description "Number of packets detected with unexpected size, or bad headers' stack.";
                        }

                        leaf l-bit-dropped {
                            type yang:counter32;
                            description "Number of packets dropped due to the L bit set by the far end.";
                        }

                        leaf multiple-dropped {
                            type yang:counter32;
                            description "Number of packets dropped due to multiple sequence numbers.";
                        }

                        leaf error-seconds {
                            type yang:counter32;
                            units "seconds";
                            description
                                "Number of Error Seconds (ESs) encountered. Any malformed packet, seq. error,
                                 LOPS and similar are considered as error seconds.";
                        }

                        leaf severe-error-seconds {
                            type yang:counter32;
                            units "seconds";
                            description
                                "Number of Severely Error Seconds (SESs) encountered.  This is when more than
                                 30 percent of the packets within a one second window are missing.";
                        }

                        leaf unavailable-seconds {
                            type yang:counter32;
                            units "seconds";
                            description
                                "Number of Unavailable Seconds (UASs) encountered. Any consecutive ten seconds
                                 of SESs are counted as one UAS.";
                        }

                        leaf failure-counts {
                            type yang:counter32;
                            description
                                "Number failure events.  A failure event begins when the LOPS failure is declared,
                                 and ends when the failure is cleared.";
                        }

                        leaf underrun-counts {
                            type yang:counter32;
                            description "Number of times the jitter buffer went into an underrun state.";
                        }

                        leaf overrun-counts {
                            type yang:counter32;
                            description "Number of times the jitter buffer went into an overrun state.";
                        }

                        leaf jitter-buffer-depth {
                            type yang:counter32;
                            description "Current packet depth of the jitter buffer.";
                        }

                        leaf jitter-buffer-delay {
                            type yang:counter32;
                            units "microseconds";
                            description
                                "Number of packets remain to be transmitted, including the packets
                                 in the Jitter buffer and the fraction of the currently playing out
                                 packet.";
                        }

                        leaf adc-jitter-buffer-sampling-complete {
                            type yang:counter32;
                            description "Number of times the sampling is done for asymmetric delay control.";
                        }

                        leaf adc-jitter-buffer-adjustment-complete {
                            type yang:counter32;
                            description "Number of times the adjustment is done for asymmetric delay control.";
                        }

                        leaf adc-jitter-buffer-sampling-average-delay {
                            type yang:counter32;
                            description
                                "The average Jitter buffer delay of the samples taken during the last ADC
                                 analysis period.";
                        }

                    } // container egress

                } // container statistics

            } // container cem


            uses state-port-access;
            uses state-port-dwdm;
            uses state-port-ethernet;
            uses state-port-gnss;
            uses state-port-network;
            uses state-port-otu;
            uses state-port-serial;
            uses state-port-sonet-sonet-sdh;
            uses state-port-tdm;
        } // list port

    } // grouping state-port

}
