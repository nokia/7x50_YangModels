submodule nokia-conf-system-script-control {

    yang-version "1.1";

    belongs-to nokia-conf { prefix "conf"; }

    import nokia-sros-yang-extensions     { prefix "sros-ext"; }
    import nokia-types-sros               { prefix "types-sros"; }

    include nokia-conf-groups;
    include nokia-conf-python;

    sros-ext:sros-major-release "rel26";
    organization "Nokia";
    contact
        "Nokia SR OS Support
         Web: <http://www.nokia.com>";
    description
        "Nokia YANG Data model to configure system scrip-control parameters on SR OS based routers.

         Copyright 2016 Nokia. All rights reserved. Reproduction of this document
         is authorized on the condition that the foregoing copyright notice is included.

         This nokia-conf-system-script-control YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-04-22";

    grouping conf-system-script-control {
        container script-control {
            description "Enter the script-control context";

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            list script {
                key "script-name owner";
                max-elements 1500;
                description "Enter the script list instance";

                leaf script-name {
                    type types-sros:named-item;
                    description "Script name";
                }

                leaf owner {
                    type types-sros:named-item;
                    description "Script owner";
                }

                leaf admin-state {
                    type types-sros:admin-state;
                    default "disable";
                    description "Administrative state of the script";
                }

                leaf description {
                    type types-sros:description;
                    description "Text description";
                }

                leaf location {
                    type types-sros:string-not-all-spaces {
                        length "1..255";
                    }
                    sros-ext:auto-restart-to-modify;
                    description "Script location";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list script

            list script-policy {
                key "policy-name owner";
                max-elements 1500;
                description "Enter the script-policy list instance";

                leaf policy-name {
                    type types-sros:named-item;
                    description "Script policy name";
                }

                leaf owner {
                    type types-sros:named-item;
                    description "Script policy owner";
                }

                leaf admin-state {
                    type types-sros:admin-state;
                    default "disable";
                    description "Administrative state of the script policy";
                }

                leaf expire-time {
                    type union {
                        type uint32 {
                            range "0..21474836";
                        }
                        type enumeration {
                            enum forever                        { value 2147483647; }
                        }
                    }
                    units "seconds";
                    default "3600";
                    description "Maximum amount of time to keep a run history status";
                }

                leaf max-completed {
                    type uint32 {
                        range "1..1500";
                    }
                    default "1";
                    description "Maximum number of script history status entries kept";
                }

                leaf results {
                    type types-sros:string-not-all-spaces {
                        length "1..255";
                    }
                    description "Location to receive CLI output of a script run";
                }

                leaf lock-override {
                    type boolean;
                    default "false";
                    description "Allow EHS/CRON script to break database explicit lock";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                choice script-type {
                    case scriptcontrol {

                        leaf lifetime {
                            type union {
                                type uint32 {
                                    range "0..21474836";
                                }
                                type enumeration {
                                    enum forever                        { value 2147483647; }
                                }
                            }
                            units "seconds";
                            default "3600";
                            description "Maximum amount of time the script may run";
                        }

                        container script {
                            description "Enter the script context";

                            leaf name {
                                type types-sros:named-item;
                                sros-ext:auto-restart-to-modify;
                                description "Script name";
                            }

                            leaf owner {
                                type types-sros:named-item;
                                sros-ext:auto-restart-to-modify;
                                description "Script owner";
                            }

                        } // container script

                    }
                    case python3script {

                        leaf python-lifetime {
                            type uint32 {
                                range "30..86400";
                            }
                            units "seconds";
                            description "Maximum time the Python application can run";
                        }

                        container python-script {
                            description "Enter the python-script context";

                            leaf name {
                                type leafref {
                                    path "../../../../../python/python-script/name";
                                }
                                sros-ext:auto-restart-to-modify;
                                description "Python application name";
                            }

                        } // container python-script

                    }
                }
            } // list script-policy

        } // container script-control

    } // grouping conf-system-script-control

}
