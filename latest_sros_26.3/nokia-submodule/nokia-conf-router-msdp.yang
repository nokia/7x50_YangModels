submodule nokia-conf-router-msdp {

    yang-version "1.1";

    belongs-to nokia-conf { prefix "conf"; }

    import nokia-sros-yang-extensions     { prefix "sros-ext"; }
    import nokia-types-sros               { prefix "types-sros"; }

    include nokia-conf-groups;
    include nokia-conf-policy-options;

    sros-ext:sros-major-release "rel26";
    organization "Nokia";
    contact
        "Nokia SR OS Support
         Web: <http://www.nokia.com>";
    description
        "Nokia YANG Data model to configure  The Multicast Source Discovery Protocol (MSDP) is used to connect multicast routing domains. on SR OS based routers.

         Copyright 2016 Nokia. All rights reserved. Reproduction of this document
         is authorized on the condition that the foregoing copyright notice is included.

         This nokia-conf-router-msdp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-05-27";

    grouping conf-router-msdp {
        container msdp {
            when "../router-name = 'Base'" {
                description "only allowed in the Base router";
            }
            presence "Enable the msdp context";
            description "Enable the msdp context";

            leaf active-source-limit {
                type int32 {
                    range "0..1000000";
                }
                description "Maximum source-active messages accepted by MSDP";
            }

            leaf admin-state {
                type types-sros:admin-state;
                default "enable";
                description "Administrative state of MSDP";
            }

            leaf-list export-policy {
                type leafref {
                    path "../../../policy-options/policy-statement/name";
                }
                max-elements 5;
                ordered-by user;
                description "Policy to export source-active states into MSDP";
            }

            leaf-list import-policy {
                type leafref {
                    path "../../../policy-options/policy-statement/name";
                }
                max-elements 5;
                ordered-by user;
                description "Policy to import source-active states into MSDP";
            }

            leaf local-address {
                type types-sros:ipv4-unicast-address;
                description "Local end IP address of the MSDP group";
            }

            leaf data-encapsulation {
                type boolean;
                default "true";
                description "Enable encapsulation of multicast data used by MSDP";
            }

            leaf rpf-table {
                type enumeration {
                    enum rtable-m                       { value 0; }
                    enum rtable-u                       { value 1; }
                    enum both                           { value 2; }
                }
                default "rtable-u";
                description "Route tables for RPF lookup";
            }

            leaf source-active-cache-lifetime {
                type uint32 {
                    range "90..600";
                }
                units "seconds";
                default "90";
                description "Timeout interval for SA entries in the cache";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container receive-message-rate {
                description "Enter the receive-message-rate context";

                leaf rate {
                    type uint32 {
                        range "10..10000";
                    }
                    description "Maximum number of MSDP messages read from TCP session";
                }

                leaf time {
                    type uint32 {
                        range "1..600";
                    }
                    units "seconds";
                    description "Time interval to rate limit MSDP messages";
                }

                leaf threshold {
                    type uint32 {
                        range "1..1000000";
                    }
                    description "Processed MSDP message limit to activate rate limiting";
                }

            } // container receive-message-rate

            list group {
                key "name";
                description "Enter the group list instance";

                leaf name {
                    type types-sros:named-item;
                    description "MSDP group name";
                }

                leaf active-source-limit {
                    type int32 {
                        range "0..1000000";
                    }
                    description "Maximum source-active messages accepted by MSDP";
                }

                leaf admin-state {
                    type types-sros:admin-state;
                    default "enable";
                    description "Administrative state of MSDP";
                }

                leaf-list export-policy {
                    type leafref {
                        path "../../../../policy-options/policy-statement/name";
                    }
                    max-elements 5;
                    ordered-by user;
                    description "Policy to export source-active states into MSDP";
                }

                leaf-list import-policy {
                    type leafref {
                        path "../../../../policy-options/policy-statement/name";
                    }
                    max-elements 5;
                    ordered-by user;
                    description "Policy to import source-active states into MSDP";
                }

                leaf local-address {
                    type types-sros:ipv4-unicast-address;
                    description "Local end IP address of the MSDP group";
                }

                leaf mode {
                    type enumeration {
                        enum standard                       { value 1; }
                        enum mesh-group                     { value 2; }
                    }
                    default "standard";
                    description "Topology of the group of peers";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container receive-message-rate {
                    description "Enter the receive-message-rate context";

                    leaf rate {
                        type uint32 {
                            range "10..10000";
                        }
                        description "Maximum number of MSDP messages read from TCP session";
                    }

                    leaf time {
                        type uint32 {
                            range "1..600";
                        }
                        units "seconds";
                        description "Time interval to rate limit MSDP messages";
                    }

                    leaf threshold {
                        type uint32 {
                            range "1..1000000";
                        }
                        description "Processed MSDP message limit to activate rate limiting";
                    }

                } // container receive-message-rate

                list peer {
                    key "ip-address";
                    description "Enter the peer list instance";

                    leaf ip-address {
                        type types-sros:ipv4-unicast-address;
                        description "IP address of the remote MSDP router for peering";
                    }

                    leaf active-source-limit {
                        type int32 {
                            range "0..1000000";
                        }
                        description "Maximum source-active messages accepted by MSDP";
                    }

                    leaf admin-state {
                        type types-sros:admin-state;
                        default "enable";
                        description "Administrative state of MSDP";
                    }

                    leaf-list export-policy {
                        type leafref {
                            path "../../../../../policy-options/policy-statement/name";
                        }
                        max-elements 5;
                        ordered-by user;
                        description "Policy to export source-active states into MSDP";
                    }

                    leaf-list import-policy {
                        type leafref {
                            path "../../../../../policy-options/policy-statement/name";
                        }
                        max-elements 5;
                        ordered-by user;
                        description "Policy to import source-active states into MSDP";
                    }

                    leaf local-address {
                        type types-sros:ipv4-unicast-address;
                        description "Local end IP address of the MSDP group";
                    }

                    leaf default-peer {
                        type boolean;
                        default "false";
                        description "Set the peer as a default MSDP peer";
                    }

                    leaf authentication-key {
                        type types-sros:encrypted-leaf {
                            length "1..370";
                        }
                        description "MD5 authentication key for the MSDP peering session";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container receive-message-rate {
                        description "Enter the receive-message-rate context";

                        leaf rate {
                            type uint32 {
                                range "10..10000";
                            }
                            description "Maximum number of MSDP messages read from TCP session";
                        }

                        leaf time {
                            type uint32 {
                                range "1..600";
                            }
                            units "seconds";
                            description "Time interval to rate limit MSDP messages";
                        }

                        leaf threshold {
                            type uint32 {
                                range "1..1000000";
                            }
                            description "Processed MSDP message limit to activate rate limiting";
                        }

                    } // container receive-message-rate

                } // list peer

            } // list group

            list peer {
                key "ip-address";
                description "Enter the peer list instance";

                leaf ip-address {
                    type types-sros:ipv4-unicast-address;
                    description "IP address of the remote MSDP router for peering";
                }

                leaf active-source-limit {
                    type int32 {
                        range "0..1000000";
                    }
                    description "Maximum source-active messages accepted by MSDP";
                }

                leaf admin-state {
                    type types-sros:admin-state;
                    default "enable";
                    description "Administrative state of MSDP";
                }

                leaf-list export-policy {
                    type leafref {
                        path "../../../../policy-options/policy-statement/name";
                    }
                    max-elements 5;
                    ordered-by user;
                    description "Policy to export source-active states into MSDP";
                }

                leaf-list import-policy {
                    type leafref {
                        path "../../../../policy-options/policy-statement/name";
                    }
                    max-elements 5;
                    ordered-by user;
                    description "Policy to import source-active states into MSDP";
                }

                leaf local-address {
                    type types-sros:ipv4-unicast-address;
                    description "Local end IP address of the MSDP group";
                }

                leaf default-peer {
                    type boolean;
                    default "false";
                    description "Set the peer as a default MSDP peer";
                }

                leaf authentication-key {
                    type types-sros:encrypted-leaf {
                        length "1..370";
                    }
                    description "MD5 authentication key for the MSDP peering session";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container receive-message-rate {
                    description "Enter the receive-message-rate context";

                    leaf rate {
                        type uint32 {
                            range "10..10000";
                        }
                        description "Maximum number of MSDP messages read from TCP session";
                    }

                    leaf time {
                        type uint32 {
                            range "1..600";
                        }
                        units "seconds";
                        description "Time interval to rate limit MSDP messages";
                    }

                    leaf threshold {
                        type uint32 {
                            range "1..1000000";
                        }
                        description "Processed MSDP message limit to activate rate limiting";
                    }

                } // container receive-message-rate

            } // list peer

            list source {
                key "ip-prefix";
                description "Enter the source list instance";

                leaf ip-prefix {
                    type types-sros:ipv4-unicast-prefix;
                    description "Source IP address for accepted source-active messages";
                }

                leaf active-source-limit {
                    type int32 {
                        range "0..1000000";
                    }
                    description "Number of source-active messages accepted by MSDP";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list source

        } // container msdp

    } // grouping conf-router-msdp

}
