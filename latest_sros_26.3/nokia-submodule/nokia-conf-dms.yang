submodule nokia-conf-dms {

    yang-version "1.1";

    belongs-to nokia-conf { prefix "conf"; }

    import nokia-sros-yang-extensions     { prefix "sros-ext"; }
    import nokia-types-dms                { prefix "types-dms"; }
    import nokia-types-services           { prefix "types-services"; }
    import nokia-types-sros               { prefix "types-sros"; }

    include nokia-conf-esa;
    include nokia-conf-groups;
    include nokia-conf-pxc;
    include nokia-conf-service;
    include nokia-conf-svc-vpls;
    include nokia-conf-svc-vprn;
    include nokia-conf-system;
    include nokia-conf-system-security;
    include nokia-conf-system-security-tls;

    sros-ext:sros-major-release "rel26";
    organization "Nokia";
    contact
        "Nokia SR OS Support
         Web: <http://www.nokia.com>";
    description
        "Nokia YANG Data model to configure defender mitigation system on SR OS based routers.

         Copyright 2016 Nokia. All rights reserved. Reproduction of this document
         is authorized on the condition that the foregoing copyright notice is included.

         This nokia-conf-dms YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-05-27";

    grouping conf-dms-defender-mitigation-system {
        container defender-mitigation-system {
            description "Enter the defender-mitigation-system context";

            leaf deployment-model {
                type types-dms:dms-deployment-model;
                description "Network deployment model";
            }

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            container advanced-countermeasures-group {
                presence "Enable the advanced-countermeasures-group context";
                description "Enable the advanced-countermeasures-group context";

                leaf admin-state {
                    type types-sros:admin-state;
                    default "disable";
                    description "Administrative state of advanced countermeasures group";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list esa {
                    key "esa-id vm";
                    max-elements 8;
                    description "Enter the esa list instance";

                    leaf esa-id {
                        type leafref {
                            path "../../../../esa/esa-id";
                        }
                        description "ESA ID";
                    }

                    leaf vm {
                        type leafref {
                            path "../../../../esa[esa-id=current()/../esa-id]/vm/vm-id";
                        }
                        description "VM ID within the ESA";
                    }

                    leaf pxc {
                        type leafref {
                            path "../../../../port-xc/pxc/pxc-id";
                        }
                        description "Backup PXC port for fail-to-wire";
                    }

                    leaf lag-link-map-profile {
                        type types-services:link-map-profile-id;
                        description "LAG link map profile to direct traffic to the ESA-VM";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list esa


            } // container advanced-countermeasures-group

            container genome-list-import {
                description "Enter the genome-list-import context";

                leaf admin-state {
                    type types-sros:admin-state;
                    default "disable";
                    description "Administrative state of the Genome list import";
                }

                leaf http-client-profile {
                    type leafref {
                        path "../../../system/transmission-profile/name";
                    }
                    description "HTTP transmission profile used to import Genome lists";
                }

                leaf refresh-period {
                    type uint32 {
                        range "0..200";
                    }
                    units "hours";
                    default "0";
                    description "Refresh period to update Genome lists";
                }

                leaf tls-client-profile {
                    type leafref {
                        path "../../../system/security/tls/client-tls-profile/client-profile-name";
                    }
                    description "TLS client profile used to import Genome lists";
                }

                leaf url {
                    type types-sros:http-or-https-url-loose;
                    description "URL from which to import the Genome lists";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container genome-list-import

            container user-list-import {
                description "Enter the user-list-import context";

                leaf admin-state {
                    type types-sros:admin-state;
                    default "disable";
                    description "Administrative state of user-list import";
                }

                leaf http-client-profile {
                    type leafref {
                        path "../../../system/transmission-profile/name";
                    }
                    description "HTTP client profile used to import user lists";
                }

                leaf refresh-period {
                    type uint32 {
                        range "0..200";
                    }
                    units "hours";
                    default "0";
                    description "Refresh period to update imported user lists";
                }

                leaf tls-client-profile {
                    type leafref {
                        path "../../../system/security/tls/client-tls-profile/client-profile-name";
                    }
                    description "TLS client profile used to import user lists";
                }

                leaf url {
                    type types-sros:http-or-https-url-loose;
                    description "HTTP or HTTPS URL from which to import the user lists";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container user-list-import


            list protected-object {
                key "id";
                max-elements 250;
                description "Enter the protected-object list instance";

                leaf id {
                    type uint32 {
                        range "1..4294967295";
                    }
                    description "Unique ID for the PO";
                }

                leaf description {
                    type types-sros:description;
                    description "Text description";
                }

                leaf tracked-flow-limit {
                    type uint32 {
                        range "1..4294967295";
                    }
                    description "Maximum number of tracked flows for the PO";
                }

                leaf tracked-session-limit {
                    type uint32 {
                        range "1..4294967295";
                    }
                    description "Maximum number of inbound tracked sessions";
                }

                leaf tracked-source-limit {
                    type uint32 {
                        range "1..4294967295";
                    }
                    description "Maximum number of tracked sources for the PO";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container dynamic-block {
                    description "Enter the dynamic-block context";

                    leaf initial-time {
                        type uint32 {
                            range "30..3600";
                        }
                        units "seconds";
                        default "60";
                        description "Dynamic block state duration after the initial violation";
                    }

                    leaf repeat-time {
                        type uint32 {
                            range "30..3600";
                        }
                        units "seconds";
                        default "300";
                        description "Duration to block the source after a repeat violation";
                    }

                    leaf monitor {
                        type boolean;
                        default "false";
                        description "Track discards that would have occurred, but did not";
                    }

                } // container dynamic-block

                container outbound {
                    description "Enter the outbound context";

                    leaf tracked-source-limit {
                        type uint32 {
                            range "1..4294967295";
                        }
                        description "Maximum number of outbound tracked sources";
                    }

                } // container outbound

                container traffic {
                    description "Enter the traffic context";

                    leaf vlan {
                        type types-sros:vlan-id;
                        description "VLAN number for inline deployment model";
                    }

                    container routed {
                        description "Enter the routed context";


                        container dirty {
                            description "Enter the dirty context";

                            leaf router-instance {
                                type leafref {
                                    path "../../../../../../service/vprn/service-name";
                                }
                                description "Dirty VPRN instance name";
                            }

                            leaf interface {
                                type leafref {
                                    path "../../../../../../service/vprn[service-name=current()/../router-instance]/interface/interface-name";
                                }
                                description "Dirty VPRN interface within the router instance";
                            }

                            leaf ipv4-nexthop {
                                type types-sros:ipv4-unicast-address;
                                description "PO IPv4 next hop to forward to dirty side ESA-VM";
                            }

                            leaf ipv6-nexthop {
                                type types-sros:ipv6-unicast-address;
                                description "PO IPv6 next hop to forward to dirty side ESA-VM";
                            }

                        } // container dirty

                    } // container routed

                    container bridged {
                        description "Enter the bridged context";

                        leaf vpls-instance {
                            type leafref {
                                path "../../../../../service/vpls/service-name";
                            }
                            description "VPLS instance ID or name";
                        }

                    } // container bridged

                } // container traffic

                container match-list {
                    description "Enter the match-list context";

                    list genome-list-set {
                        key "genome-list-set-name";
                        max-elements 10;
                        description "Enter the genome-list-set list instance";

                        leaf genome-list-set-name {
                            type types-sros:named-item;
                            description "Genome-list set name";
                        }

                        leaf description {
                            type types-sros:description;
                            description "Text description";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        list genome-list {
                            key "id";
                            description "Add a list entry for genome-list";

                            leaf id {
                                type types-dms:genome-list;
                                description "Genome list ID";
                            }

                        } // list genome-list

                    } // list genome-list-set

                    list ip-prefix-list {
                        key "ip-prefix-list-name";
                        max-elements 10;
                        description "Enter the ip-prefix-list list instance";

                        leaf ip-prefix-list-name {
                            type types-sros:named-item;
                            description "IP prefix list name";
                        }

                        leaf description {
                            type types-sros:description;
                            description "Text description";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        list prefix {
                            key "ip-prefix";
                            max-elements 64;
                            description "Add a list entry for prefix";

                            leaf ip-prefix {
                                type types-sros:ip-prefix;
                                description "IP prefix for mitigation-rule matching";
                            }

                        } // list prefix

                    } // list ip-prefix-list

                    list port-list {
                        key "port-list-name";
                        max-elements 10;
                        description "Enter the port-list list instance";

                        leaf port-list-name {
                            type types-sros:named-item;
                            description "Port list name";
                        }

                        leaf description {
                            type types-sros:description;
                            description "Text description";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        list port {
                            key "port-number";
                            max-elements 32;
                            description "Add a list entry for port";

                            leaf port-number {
                                type int32 {
                                    range "0..65535";
                                }
                                description "Port number";
                            }

                        } // list port

                        list range {
                            key "start end";
                            max-elements 32;
                            description "Add a list entry for range";

                            leaf start {
                                type int32 {
                                    range "0..65534";
                                }
                                description "Lower bound of the port range in the port list";
                            }

                            leaf end {
                                type int32 {
                                    range "1..65535";
                                }
                                description "Upper bound of the port range in the port list";
                            }

                        } // list range

                    } // list port-list

                } // container match-list

                container policer {
                    description "Enter the policer context";

                    list source-event-count {
                        key "name";
                        max-elements 16;
                        description "Enter the source-event-count list instance";

                        leaf name {
                            type types-sros:named-item;
                            description "Policer name";
                        }

                        leaf description {
                            type types-sros:description;
                            description "Text description";
                        }

                        leaf dynamic-block {
                            type boolean;
                            default "false";
                            description "Drop packet and block source when policer is violated";
                        }

                        leaf peak {
                            type types-dms:policer-event-count;
                            description "Peak event count limit";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list source-event-count

                    list source-event-rate {
                        key "name";
                        max-elements 16;
                        description "Enter the source-event-rate list instance";

                        leaf name {
                            type types-sros:named-item;
                            description "Policer name";
                        }

                        leaf description {
                            type types-sros:description;
                            description "Text description";
                        }

                        leaf dynamic-block {
                            type boolean;
                            default "false";
                            description "Drop packet and block source when policer is violated";
                        }

                        leaf burst-size {
                            type types-dms:policer-event-burst-size;
                            description "Maximum event rate burst size";
                        }

                        leaf peak {
                            type types-dms:policer-event-rate;
                            description "Peak event rate limit";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list source-event-rate

                    list source-flow-count {
                        key "name";
                        max-elements 16;
                        description "Enter the source-flow-count list instance";

                        leaf name {
                            type types-sros:named-item;
                            description "Policer name";
                        }

                        leaf description {
                            type types-sros:description;
                            description "Text description";
                        }

                        leaf dynamic-block {
                            type boolean;
                            default "false";
                            description "Drop packet and block source when policer is violated";
                        }

                        leaf peak {
                            type types-dms:policer-flow-count;
                            description "Peak flow count limit";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list source-flow-count

                    list source-flow-setup-rate {
                        key "name";
                        max-elements 16;
                        description "Enter the source-flow-setup-rate list instance";

                        leaf name {
                            type types-sros:named-item;
                            description "Policer name";
                        }

                        leaf description {
                            type types-sros:description;
                            description "Text description";
                        }

                        leaf dynamic-block {
                            type boolean;
                            default "false";
                            description "Drop packet and block source when policer is violated";
                        }

                        leaf burst-size {
                            type types-dms:policer-flow-burst-size;
                            description "Maximum flow-setup-rate burst size";
                        }

                        leaf peak {
                            type types-dms:policer-flow-setup-rate;
                            description "Peak flow-setup-rate limit";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list source-flow-setup-rate

                    list event-count {
                        key "name";
                        max-elements 16;
                        description "Enter the event-count list instance";

                        leaf name {
                            type types-sros:named-item;
                            description "Policer name";
                        }

                        leaf description {
                            type types-sros:description;
                            description "Text description";
                        }

                        leaf peak {
                            type types-dms:policer-event-count;
                            description "Peak event count limit";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list event-count

                    list event-rate {
                        key "name";
                        max-elements 16;
                        description "Enter the event-rate list instance";

                        leaf name {
                            type types-sros:named-item;
                            description "Policer name";
                        }

                        leaf description {
                            type types-sros:description;
                            description "Text description";
                        }

                        leaf burst-size {
                            type types-dms:policer-event-burst-size;
                            description "Maximum event rate burst size";
                        }

                        leaf peak {
                            type types-dms:policer-event-rate;
                            description "Peak event rate limit";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list event-rate

                    list flow-count {
                        key "name";
                        max-elements 16;
                        description "Enter the flow-count list instance";

                        leaf name {
                            type types-sros:named-item;
                            description "Policer name";
                        }

                        leaf description {
                            type types-sros:description;
                            description "Text description";
                        }

                        leaf peak {
                            type types-dms:policer-flow-count;
                            description "Peak flow count limit";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list flow-count

                    list flow-setup-rate {
                        key "name";
                        max-elements 16;
                        description "Enter the flow-setup-rate list instance";

                        leaf name {
                            type types-sros:named-item;
                            description "Policer name";
                        }

                        leaf description {
                            type types-sros:description;
                            description "Text description";
                        }

                        leaf burst-size {
                            type types-dms:policer-flow-burst-size;
                            description "Maximum flow-setup-rate burst size";
                        }

                        leaf peak {
                            type types-dms:policer-flow-setup-rate;
                            description "Peak flow-setup-rate limit";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list flow-setup-rate

                } // container policer

                container protocol-handlers {
                    description "Enter the protocol-handlers context";

                    leaf ip-fragment-control {
                        type enumeration {
                            enum discard {
                                value 0;
                                description "Drop all IPv4 fragments";
                            }
                            enum permit {
                                value 1;
                                description "Allow IPv4 fragments to pass for further processing";
                            }
                        }
                        default "discard";
                        description "Processing behavior for IPv4 fragments";
                    }

                    container udp {
                        description "Enter the udp context";

                        leaf flow-inactivity-timeout {
                            type uint32 {
                                range "1..600";
                            }
                            units "seconds";
                            default "5";
                            description "Inactivity timeout for UDP flows";
                        }

                    } // container udp

                    container tcp {
                        description "Enter the tcp context";

                        leaf ack-tolerance {
                            type types-dms:protocol-tolerance;
                            description "Tolerance for invalid TCP ACK";
                        }

                        leaf dynamic-block {
                            type boolean;
                            default "false";
                            description "Block the tracked source upon a TCP flow discard";
                        }

                        leaf flow-inactivity-timeout {
                            type uint32 {
                                range "1..3600";
                            }
                            units "seconds";
                            default "300";
                            description "Inactivity timeout for TCP flows";
                        }

                        leaf flow-protected-object-reset {
                            type enumeration {
                                enum none {
                                    value 0;
                                    description "Do not send any RSTs";
                                }
                                enum authenticated-sources {
                                    value 1;
                                    description "Send an RST for TCP-authenticated tracked sources only";
                                }
                                enum all-sources {
                                    value 2;
                                    description "RST for any tracked-source.";
                                }
                            }
                            default "none";
                            description "Whether to send a TCP RST to the PO if flow ends early";
                        }

                        leaf flow-start-guard-time {
                            type uint32 {
                                range "1..120";
                            }
                            units "seconds";
                            default "25";
                            description "Maximum time to receive payload after a TCP handshake";
                        }

                    } // container tcp

                    container other {
                        description "Enter the other context";

                        leaf flow-inactivity-timeout {
                            type uint32 {
                                range "1..600";
                            }
                            units "seconds";
                            default "5";
                            description "Inactivity timeout for non-TCP and non-UDP flows";
                        }

                    } // container other


                    list dns-validate {
                        key "name";
                        max-elements 2;
                        description "Enter the dns-validate list instance";

                        leaf name {
                            type types-sros:named-item;
                            description "DNS packet validator instance name";
                        }

                        leaf description {
                            type types-sros:description;
                            description "Text description";
                        }

                        leaf dynamic-block {
                            type boolean;
                            default "false";
                            description "Block the tracked source upon a DNS validator discard";
                        }

                        leaf message-size-limit {
                            type uint32 {
                                range "1..10000";
                            }
                            description "Maximum size of the DNS message";
                        }

                        leaf request-rate-policer {
                            type leafref {
                                path "../../../policer/event-rate/name";
                            }
                            description "PO event-rate policer used for DNS requests";
                        }

                        leaf source-request-rate-policer {
                            type leafref {
                                path "../../../policer/source-event-rate/name";
                            }
                            description "Source event-rate policer used for DNS requests";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container dns-redirect-target {
                            description "Enter the dns-redirect-target context";

                            leaf ipv4-server-a {
                                type types-sros:ip-address;
                                description "IPv4 address of a DNS server at the PO";
                            }

                            leaf ipv4-server-b {
                                type types-sros:ip-address;
                                description "IPv4 address of a secondary DNS server at the PO";
                            }

                            leaf ipv6-server-a {
                                type types-sros:ip-address;
                                description "IPv6 address of a DNS server at the PO";
                            }

                            leaf ipv6-server-b {
                                type types-sros:ip-address;
                                description "IPv6 address of a secondary DNS server at the PO";
                            }

                        } // container dns-redirect-target

                        container dns-filter {
                            presence "Enable the dns-filter context";
                            description "Enable the dns-filter context";

                            leaf admin-state {
                                type types-sros:admin-state;
                                default "disable";
                                description "Administrative state of the DNS filter";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            container default-action {
                                description "Enter the default-action context";

                                leaf drop {
                                    type boolean;
                                    default "false";
                                    description "Drop traffic not matching any DNS filter entries";
                                }

                            } // container default-action

                            list entry {
                                key "id";
                                max-elements 16;
                                description "Enter the entry list instance";

                                leaf id {
                                    type uint32 {
                                        range "1..16";
                                    }
                                    description "Unique ID for the DNS filter entry";
                                }

                                leaf description {
                                    type types-sros:description;
                                    description "Text description";
                                }

                                leaf-list apply-groups {
                                    type leafref {
                                        path "../../../../../../../groups/group/name";
                                    }
                                    max-elements 8;
                                    ordered-by user;
                                    description "Apply a configuration group at this level";
                                }

                                leaf-list apply-groups-exclude {
                                    type leafref {
                                        path "../../../../../../../groups/group/name";
                                    }
                                    max-elements 8;
                                    ordered-by user;
                                    description "Exclude a configuration group at this level";
                                }

                                container action {
                                    description "Enter the action context";

                                    leaf drop {
                                        type boolean;
                                        default "false";
                                        description "Drop traffic matching the DNS filter entry";
                                    }

                                    leaf request-rate-policer {
                                        type leafref {
                                            path "../../../../../../policer/event-rate/name";
                                        }
                                        description "PO-granularity event-rate policer for DNS requests";
                                    }

                                    leaf source-request-rate-policer {
                                        type leafref {
                                            path "../../../../../../policer/source-event-rate/name";
                                        }
                                        description "Source-granularity event-rate policer for DNS requests";
                                    }

                                    container query-name-entropy-range {
                                        presence "Enable the query-name-entropy-range context";
                                        description "Enable the query-name-entropy-range context";

                                        leaf minimum {
                                            type decimal64 {
                                                range "0.00..9.99";
                                                fraction-digits 2;
                                            }
                                            mandatory true;
                                            description "Minimum entropy of the DNS query name";
                                        }

                                        leaf maximum {
                                            type decimal64 {
                                                range "0.01..10.00";
                                                fraction-digits 2;
                                            }
                                            mandatory true;
                                            description "Maximum entropy of the DNS query name";
                                        }

                                    } // container query-name-entropy-range

                                } // container action

                                container match {
                                    description "Enter the match context";

                                    container query-type {
                                        description "Enter the query-type context";

                                        list record {
                                            key "record-type";
                                            max-elements 32;
                                            description "Add a list entry for record";

                                            leaf record-type {
                                                type types-dms:dns-record-type;
                                                description "DNS record type";
                                            }

                                        } // list record

                                    } // container query-type

                                    container query-name {
                                        description "Enter the query-name context";

                                        list dns-list {
                                            key "list-name";
                                            max-elements 10;
                                            description "Add a list entry for dns-list";

                                            leaf list-name {
                                                type types-sros:named-item;
                                                description "DNS domain list name";
                                            }

                                        } // list dns-list

                                        list expression {
                                            key "expression-string";
                                            max-elements 5;
                                            description "Add a list entry for expression";

                                            leaf expression-string {
                                                type string {
                                                    length "1..80";
                                                }
                                                description "DNS domain expression";
                                            }

                                        } // list expression

                                    } // container query-name

                                } // container match

                            } // list entry

                        } // container dns-filter

                        container query-name-entropy-range {
                            presence "Enable the query-name-entropy-range context";
                            description "Enable the query-name-entropy-range context";

                            leaf minimum {
                                type decimal64 {
                                    range "0.00..9.99";
                                    fraction-digits 2;
                                }
                                mandatory true;
                                description "Minimum entropy of the DNS query name";
                            }

                            leaf maximum {
                                type decimal64 {
                                    range "0.01..10.00";
                                    fraction-digits 2;
                                }
                                mandatory true;
                                description "Maximum entropy of the DNS query name";
                            }

                        } // container query-name-entropy-range

                    } // list dns-validate

                    list dns-tracker {
                        key "dns-tracker-name";
                        max-elements 2;
                        description "Enter the dns-tracker list instance";

                        leaf dns-tracker-name {
                            type types-sros:named-item;
                            description "DNS tracker name";
                        }

                        leaf description {
                            type types-sros:description;
                            description "Text description";
                        }

                        leaf dynamic-block {
                            type boolean;
                            default "false";
                            description "Block the tracked source upon DNS tracker discard";
                        }

                        leaf inactivity-timeout {
                            type uint32 {
                                range "1..3600";
                            }
                            units "seconds";
                            description "Inactivity timeout for DNS over TCP flows";
                        }

                        leaf start-guard-time {
                            type uint32 {
                                range "1..120";
                            }
                            units "seconds";
                            description "Maximum time to receive DNS request after TCP handshake";
                        }

                        leaf payload-validate {
                            type leafref {
                                path "../../dns-validate/name";
                            }
                            mandatory true;
                            description "DNS over TCP packet validator used to analyze payload";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list dns-tracker


                    list http-tracker {
                        key "http-tracker-name";
                        max-elements 2;
                        description "Enter the http-tracker list instance";

                        leaf http-tracker-name {
                            type types-sros:named-item;
                            description "HTTP flow tracker instance name";
                        }

                        leaf description {
                            type types-sros:description;
                            description "Text description";
                        }

                        leaf dynamic-block {
                            type boolean;
                            default "false";
                            description "Block the tracked source upon an HTTP tracker discard";
                        }

                        leaf inactivity-timeout {
                            type uint32 {
                                range "1..3600";
                            }
                            units "seconds";
                            description "Inactivity timeout for HTTP flows";
                        }

                        leaf start-guard-time {
                            type uint32 {
                                range "1..120";
                            }
                            units "seconds";
                            description "Max time to receive HTTP request after TCP handshake";
                        }

                        leaf request-guard-time {
                            type uint32 {
                                range "1..120";
                            }
                            units "seconds";
                            description "Maximum time to complete an HTTP request";
                        }

                        leaf request-rate-policer {
                            type leafref {
                                path "../../../policer/event-rate/name";
                            }
                            description "PO event-rate policer used for HTTP requests";
                        }

                        leaf source-request-rate-policer {
                            type leafref {
                                path "../../../policer/source-event-rate/name";
                            }
                            description "Source event-rate policer used for HTTP requests";
                        }

                        leaf tolerance {
                            type types-dms:protocol-tolerance;
                            description "Tolerance for unsupported HTTP protocols";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list http-tracker

                    list icmp-validate {
                        key "name";
                        max-elements 2;
                        description "Enter the icmp-validate list instance";

                        leaf name {
                            type types-sros:named-item;
                            description "ICMP packet validator instance name";
                        }

                        leaf description {
                            type types-sros:description;
                            description "Text description";
                        }

                        leaf dynamic-block {
                            type boolean;
                            default "false";
                            description "Block the tracked source upon ICMP validator discard";
                        }

                        leaf echo-rate-policer {
                            type leafref {
                                path "../../../policer/event-rate/name";
                            }
                            description "PO event-rate policer used for ICMP echo messages";
                        }

                        leaf track-source {
                            type boolean;
                            default "false";
                            description "Valid ICMP can optionally trigger tracked-source state to be kept.";
                        }

                        leaf source-echo-rate-policer {
                            type leafref {
                                path "../../../policer/source-event-rate/name";
                            }
                            description "Source event-rate policer used for ICMP echo messages";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list icmp-validate

                    list quic-tracker {
                        key "quic-tracker-name";
                        max-elements 2;
                        description "Enter the quic-tracker list instance";

                        leaf quic-tracker-name {
                            type types-sros:named-item;
                            description "QUIC flow tracker instance name";
                        }

                        leaf description {
                            type types-sros:description;
                            description "Text description";
                        }

                        leaf dynamic-block {
                            type boolean;
                            default "false";
                            description "Block the tracked source upon QUIC tracker discard";
                        }

                        leaf fragment-limit {
                            type uint32 {
                                range "1..31";
                            }
                            description "Maximum number of QUIC message fragments in handshake";
                        }

                        leaf application-data-guard-time {
                            type uint32 {
                                range "1..120";
                            }
                            units "seconds";
                            description "Maximum time to send data after flow initialization";
                        }

                        leaf inactivity-timeout {
                            type uint32 {
                                range "1..3600";
                            }
                            units "seconds";
                            description "Inactivity timeout for QUIC flows";
                        }

                        leaf concurrent-handshake-limit {
                            type leafref {
                                path "../../../policer/event-count/name";
                            }
                            description "PO-level event-count policer to limit QUIC sessions";
                        }

                        leaf source-concurrent-handshake-limit {
                            type leafref {
                                path "../../../policer/source-event-count/name";
                            }
                            description "Source-level policer to limit number of QUIC sessions";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list quic-tracker

                    list sip-tracker {
                        key "sip-tracker-name";
                        max-elements 2;
                        description "Enter the sip-tracker list instance";

                        leaf sip-tracker-name {
                            type types-sros:named-item;
                            description "SIP flow tracker instance name";
                        }

                        leaf description {
                            type types-sros:description;
                            description "Text description";
                        }

                        leaf dynamic-block {
                            type boolean;
                            default "false";
                            description "Block the tracked source upon SIP tracker discard";
                        }

                        leaf request-rate-policer {
                            type leafref {
                                path "../../../policer/event-rate/name";
                            }
                            description "PO-level event-rate policer to use for SIP requests";
                        }

                        leaf source-request-rate-policer {
                            type leafref {
                                path "../../../policer/source-event-rate/name";
                            }
                            description "Source-level event-rate policer to use for SIP requests";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container udp {
                            description "Enter the udp context";

                            leaf inactivity-timeout {
                                type uint32 {
                                    range "1..3600";
                                }
                                units "seconds";
                                description "Inactivity timeout for SIP over UDP flows";
                            }

                        } // container udp


                    } // list sip-tracker

                    list tls-tracker {
                        key "tls-tracker-name";
                        max-elements 2;
                        description "Enter the tls-tracker list instance";

                        leaf tls-tracker-name {
                            type types-sros:named-item;
                            description "TLS flow tracker instance name";
                        }

                        leaf description {
                            type types-sros:description;
                            description "Text description";
                        }

                        leaf dynamic-block {
                            type boolean;
                            default "false";
                            description "Block the tracked source upon TLS tracker discard";
                        }

                        leaf inactivity-timeout {
                            type uint32 {
                                range "1..3600";
                            }
                            units "seconds";
                            description "Inactivity timeout for TLS flows";
                        }

                        leaf client-cipher-limit {
                            type uint32 {
                                range "1..255";
                            }
                            description "Maximum number of cipher suites in the client Hello";
                        }

                        leaf client-extension-limit {
                            type uint32 {
                                range "1..31";
                            }
                            description "Maximum number of TLS extensions in the client Hello";
                        }

                        leaf concurrent-handshake-limit {
                            type leafref {
                                path "../../../policer/event-count/name";
                            }
                            description "PO-level event-count policer to limit TLS sessions";
                        }

                        leaf source-concurrent-handshake-limit {
                            type leafref {
                                path "../../../policer/source-event-count/name";
                            }
                            description "Source-level event-count policer to limit TLS sessions";
                        }

                        leaf start-guard-time {
                            type uint32 {
                                range "1..120";
                            }
                            units "seconds";
                            description "Max time to receive client Hello after TCP handshake";
                        }

                        leaf handshake-guard-time {
                            type uint32 {
                                range "1..120";
                            }
                            units "seconds";
                            description "Maximum time to complete the TLS security handshake";
                        }

                        leaf application-data-guard-time {
                            type uint32 {
                                range "1..120";
                            }
                            units "seconds";
                            description "Maximum time to send data after the TLS handshake";
                        }

                        leaf tls-client-filter {
                            type leafref {
                                path "../../tls-client-filter/tls-client-filter-name";
                            }
                            description "TLS client filter used to filter TLS client Hellos";
                        }

                        leaf tolerance {
                            type types-dms:protocol-tolerance;
                            description "Tolerance for unsupported TLS protocols";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list tls-tracker

                    list tls-client-filter {
                        key "tls-client-filter-name";
                        max-elements 3;
                        description "Enter the tls-client-filter list instance";

                        leaf tls-client-filter-name {
                            type types-sros:named-item;
                            description "TLS client filter name";
                        }

                        leaf description {
                            type types-sros:description;
                            description "Text description";
                        }

                        leaf admin-state {
                            type types-sros:admin-state;
                            default "disable";
                            description "Administrative state of the TLS client filter";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container default-action {
                            description "Enter the default-action context";

                            leaf drop {
                                type boolean;
                                default "false";
                                description "Drop traffic not matching any TLS client filter entries";
                            }

                        } // container default-action

                        list entry {
                            key "id";
                            max-elements 8;
                            description "Enter the entry list instance";

                            leaf id {
                                type uint32 {
                                    range "1..8";
                                }
                                description "TLS client filter entry ID";
                            }

                            leaf description {
                                type types-sros:description;
                                description "Text description";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            container action {
                                description "Enter the action context";

                                leaf drop {
                                    type boolean;
                                    default "false";
                                    description "Drop traffic matching the TLS client filter entry";
                                }

                            } // container action

                            container match {
                                description "Enter the match context";

                                list tls-fingerprint-list {
                                    key "list-name";
                                    max-elements 2;
                                    description "Add a list entry for tls-fingerprint-list";

                                    leaf list-name {
                                        type types-sros:named-item;
                                        description "TLS fingerprint list name";
                                    }

                                } // list tls-fingerprint-list

                            } // container match

                        } // list entry

                    } // list tls-client-filter

                } // container protocol-handlers

                container mitigation-rules {
                    description "Enter the mitigation-rules context";

                    list entry {
                        key "id";
                        max-elements 100;
                        description "Enter the entry list instance";

                        leaf id {
                            type uint32 {
                                range "1..65535";
                            }
                            description "Mitigation-rule entry ID";
                        }

                        leaf description {
                            type types-sros:description;
                            description "Text description";
                        }

                        leaf admin-state {
                            type types-sros:admin-state;
                            default "disable";
                            description "Administrative state of the PO mitigation-rule entry";
                        }

                        leaf monitor {
                            type boolean;
                            default "false";
                            description "Track discards that would have occurred, but did not";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container action {
                            description "Enter the action context";

                            leaf drop {
                                type boolean;
                                default "false";
                                description "Drop traffic that matches the mitigation-rule entry";
                            }

                            leaf flow-count-policer {
                                type leafref {
                                    path "../../../../../protected-object/policer/flow-count/name";
                                }
                                description "PO-level flow-count policer to apply to traffic";
                            }

                            leaf flow-setup-rate-policer {
                                type leafref {
                                    path "../../../../../protected-object/policer/flow-setup-rate/name";
                                }
                                description "PO-level flow setup-rate policer to apply to traffic";
                            }

                            leaf source-flow-count-policer {
                                type leafref {
                                    path "../../../../../protected-object/policer/source-flow-count/name";
                                }
                                description "Source flow-count policer to apply to traffic";
                            }

                            leaf source-flow-setup-rate-policer {
                                type leafref {
                                    path "../../../../../protected-object/policer/source-flow-setup-rate/name";
                                }
                                description "Source flow-setup-rate policer to apply to traffic";
                            }

                            leaf dns-client-authentication {
                                type enumeration {
                                    enum none {
                                        value 0;
                                        description "No DNS authentication";
                                    }
                                    enum active-ns-redirect {
                                        value 1;
                                        description "Actively challenge using custom NS redirect";
                                    }
                                    enum active-force-tcp {
                                        value 2;
                                        description "Actively challenge by forcing to use TCP";
                                    }
                                    enum active-cookie-ns-redirect {
                                        value 3;
                                        description "Actively challenge with NS redirect and cookie exchange";
                                    }
                                }
                                default "none";
                                description "DNS client authentication for DNS requests";
                            }

                            leaf http-client-authentication {
                                type enumeration {
                                    enum none {
                                        value 0;
                                        description "No HTTP authentication";
                                    }
                                    enum active-302-redirect {
                                        value 1;
                                        description "Actively challenge the HTTP client using a 302 redirect";
                                    }
                                }
                                default "none";
                                description "HTTP client authentication for HTTP flows";
                            }

                            leaf quic-client-authentication {
                                type enumeration {
                                    enum none {
                                        value 0;
                                        description "No QUIC authentication";
                                    }
                                    enum active-challenge {
                                        value 1;
                                        description "Actively challenge the session with a SynAck cookie";
                                    }
                                }
                                default "none";
                                description "QUIC client authentication for QUIC flows";
                            }

                            leaf tcp-client-authentication {
                                type enumeration {
                                    enum none {
                                        value 0;
                                        description "No TCP authentication";
                                    }
                                    enum active-challenge {
                                        value 1;
                                        description "Actively challenge session with a SynAck cookie";
                                    }
                                    enum active-invalid-ack {
                                        value 2;
                                        description "Actively interrupt session with an out of sequence Ack";
                                    }
                                    enum active-invalid-syn-ack {
                                        value 3;
                                        description "Actively interrupt session with a SynAck invalid AckNum";
                                    }
                                }
                                default "none";
                                description "TCP client authentication for TCP flows";
                            }

                            container protocol-tracker {
                                description "Enter the protocol-tracker context";

                                choice tracker {
                                    case any {

                                        leaf any {
                                            type empty;
                                            description "Track matching traffic as a stateful flow";
                                        }

                                    }
                                    case dns {

                                        leaf dns {
                                            type leafref {
                                                path "../../../../../../protected-object/protocol-handlers/dns-tracker/dns-tracker-name";
                                            }
                                            description "Flow tracker to analyze matching DNS over TCP traffic";
                                        }

                                    }
                                    case http {

                                        leaf http {
                                            type leafref {
                                                path "../../../../../../protected-object/protocol-handlers/http-tracker/http-tracker-name";
                                            }
                                            description "Flow tracker used to analyze matching HTTP traffic";
                                        }

                                    }
                                    case quic {

                                        leaf quic {
                                            type leafref {
                                                path "../../../../../../protected-object/protocol-handlers/quic-tracker/quic-tracker-name";
                                            }
                                            description "Flow tracker used to analyze matching QUIC traffic";
                                        }

                                    }
                                    case sip {

                                        leaf sip {
                                            type leafref {
                                                path "../../../../../../protected-object/protocol-handlers/sip-tracker/sip-tracker-name";
                                            }
                                            description "Flow tracker used to analyze matching SIP traffic";
                                        }

                                    }
                                    case tls {

                                        leaf tls {
                                            type leafref {
                                                path "../../../../../../protected-object/protocol-handlers/tls-tracker/tls-tracker-name";
                                            }
                                            description "Flow tracker used to analyze matching TLS traffic";
                                        }

                                    }
                                }
                            } // container protocol-tracker

                            container protocol-validate {
                                description "Enter the protocol-validate context";

                                choice validate {
                                    case dns {

                                        leaf dns {
                                            type leafref {
                                                path "../../../../../../protected-object/protocol-handlers/dns-validate/name";
                                            }
                                            description "DNS protocol packet validator used to analyze traffic";
                                        }

                                    }
                                    case icmp {

                                        leaf icmp {
                                            type leafref {
                                                path "../../../../../../protected-object/protocol-handlers/icmp-validate/name";
                                            }
                                            description "ICMP protocol packet validator used to analyze traffic";
                                        }

                                    }
                                }
                            } // container protocol-validate

                        } // container action

                        container match {
                            description "Enter the match context";

                            container dst-ip {
                                description "Enter the dst-ip context";

                                leaf operator {
                                    type types-dms:match-operator;
                                    description "Match condition for the IP address";
                                }

                                choice value {
                                    case prefix {

                                        leaf prefix {
                                            type types-sros:ip-prefix;
                                            description "IP prefix to match against the IP address";
                                        }

                                    }
                                    case prefix-list {

                                        leaf prefix-list {
                                            type leafref {
                                                path "../../../../../../protected-object/match-list/ip-prefix-list/ip-prefix-list-name";
                                            }
                                            description "IP prefix list to match to the IP address";
                                        }

                                    }
                                }
                            } // container dst-ip

                            container dst-port {
                                description "Enter the dst-port context";

                                leaf operator {
                                    type types-dms:match-operator;
                                    description "Match condition for the port";
                                }

                                choice value {
                                    case port-number {

                                        leaf port-number {
                                            type types-sros:tcp-udp-port;
                                            default "0";
                                            description "TCP or UDP port number";
                                        }

                                    }
                                    case port-range {

                                        leaf range-start {
                                            type int32 {
                                                range "0..65534";
                                            }
                                            mandatory true;
                                            description "Lower bound of the port range";
                                        }

                                        leaf range-end {
                                            type int32 {
                                                range "1..65535";
                                            }
                                            mandatory true;
                                            description "Upper bound of the port range";
                                        }

                                    }
                                    case port-list {

                                        leaf port-list {
                                            type leafref {
                                                path "../../../../../../protected-object/match-list/port-list/port-list-name";
                                            }
                                            description "Port list to match against the port";
                                        }

                                    }
                                }
                            } // container dst-port

                            container ip-protocol {
                                description "Enter the ip-protocol context";

                                leaf operator {
                                    type types-dms:match-operator;
                                    description "Match condition for the IP protocol";
                                }

                                leaf value {
                                    type types-sros:match-ip-protocol;
                                    description "IP protocol to match to the protocol used by traffic";
                                }

                            } // container ip-protocol

                            container src-ip {
                                description "Enter the src-ip context";

                                leaf operator {
                                    type types-dms:match-operator;
                                    description "Match condition for the source IP address";
                                }

                                choice value {
                                    case prefix {

                                        leaf prefix {
                                            type types-sros:ip-prefix;
                                            description "IP prefix to match against the source IP address";
                                        }

                                    }
                                    case prefix-list {

                                        leaf prefix-list {
                                            type leafref {
                                                path "../../../../../../protected-object/match-list/ip-prefix-list/ip-prefix-list-name";
                                            }
                                            description "IP prefix list to match against the source IP address";
                                        }

                                    }
                                    case genome-list {

                                        leaf genome-list {
                                            type types-dms:genome-list;
                                            description "Genome list to match against the source IP address";
                                        }

                                    }
                                    case genome-list-set {

                                        leaf genome-list-set {
                                            type leafref {
                                                path "../../../../../../protected-object/match-list/genome-list-set/genome-list-set-name";
                                            }
                                            description "Genome-list set to match against the source IP address";
                                        }

                                    }
                                }
                            } // container src-ip

                            container src-port {
                                description "Enter the src-port context";

                                leaf operator {
                                    type types-dms:match-operator;
                                    description "Match condition for the port";
                                }

                                choice value {
                                    case port-number {

                                        leaf port-number {
                                            type types-sros:tcp-udp-port;
                                            default "0";
                                            description "TCP or UDP port number";
                                        }

                                    }
                                    case port-range {

                                        leaf range-start {
                                            type int32 {
                                                range "0..65534";
                                            }
                                            mandatory true;
                                            description "Lower bound of the port range";
                                        }

                                        leaf range-end {
                                            type int32 {
                                                range "1..65535";
                                            }
                                            mandatory true;
                                            description "Upper bound of the port range";
                                        }

                                    }
                                    case port-list {

                                        leaf port-list {
                                            type leafref {
                                                path "../../../../../../protected-object/match-list/port-list/port-list-name";
                                            }
                                            description "Port list to match against the port";
                                        }

                                    }
                                }
                            } // container src-port

                        } // container match

                    } // list entry


                } // container mitigation-rules

                container pre-filter {
                    description "Enter the pre-filter context";

                    list genome-list {
                        key "id";
                        description "Enter the genome-list list instance";

                        leaf id {
                            type types-dms:genome-list;
                            description "Genome list ID";
                        }

                        leaf action {
                            type types-dms:pre-filter-action;
                            mandatory true;
                            description "Action to take on traffic matching Genome list source";
                        }

                        leaf monitor {
                            type boolean;
                            default "false";
                            description "Use monitor mode to track genome-list packet actions";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list genome-list

                } // container pre-filter

            } // list protected-object

        } // container defender-mitigation-system

    } // grouping conf-dms-defender-mitigation-system

}
