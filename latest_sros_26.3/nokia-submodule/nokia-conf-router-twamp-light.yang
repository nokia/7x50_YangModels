submodule nokia-conf-router-twamp-light {

    yang-version "1.1";

    belongs-to nokia-conf { prefix "conf"; }

    import nokia-sros-yang-extensions     { prefix "sros-ext"; }
    import nokia-types-sros               { prefix "types-sros"; }

    include nokia-conf-groups;

    sros-ext:sros-major-release "rel26";
    organization "Nokia";
    contact
        "Nokia SR OS Support
         Web: <http://www.nokia.com>";
    description
        "Nokia YANG Data model to configure  OAM Performance Monitoring TWAMP-Light (Two-Way Active Measurement Protocol, Light) on SR OS based routers.

         Copyright 2016 Nokia. All rights reserved. Reproduction of this document
         is authorized on the condition that the foregoing copyright notice is included.

         This nokia-conf-router-twamp-light YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-04-22";

    grouping conf-router-twamp-light {
        container twamp-light {
            when "../router-name = 'Base'" {
                description "router-name must be 'Base'";
            }
            description "Enter the twamp-light context";

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container reflector {
                presence "Enable the reflector context";
                description "Enable the reflector context";

                leaf admin-state {
                    type types-sros:admin-state;
                    default "disable";
                    description "Administrative state of the TWAMP Light reflector";
                }

                leaf description {
                    type types-sros:description;
                    description "Text description";
                }

                leaf udp-port {
                    type types-sros:tcp-udp-port-non-zero {
                        range "862|64364..64373";
                    }
                    sros-ext:auto-restart-to-modify;
                    mandatory true;
                    description "UDP port on which the specified TWAMP-Light reflector listens for TWAMP PDUs";
                }

                leaf allow-ipv6-udp-checksum-zero {
                    type boolean;
                    sros-ext:auto-restart-to-modify;
                    default "false";
                    description "Process IPv6 packets with a zero UDP checksum";
                }

                leaf type {
                    type enumeration {
                        enum stamp {
                            value 1;
                            description "Reflector finds and processes supported STAMP TLVs";
                        }
                        enum twamp-light {
                            value 2;
                            description "Reflector does not check received PDU";
                        }
                    }
                    default "twamp-light";
                    description "Processing behavior type for the reflector";
                }

                leaf lag-ip-measurement {
                    type boolean;
                    default "false";
                    description "Process the TWAMP Light packet micro-session fields";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list prefix {
                    key "ip-prefix";
                    max-elements 50;
                    description "Enter the prefix list instance";

                    leaf ip-prefix {
                        type types-sros:ip-prefix;
                        description "Source prefix for the TWAMP-Light reflector";
                    }

                    leaf description {
                        type types-sros:description;
                        description "Text description";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list prefix

            } // container reflector

        } // container twamp-light

    } // grouping conf-router-twamp-light

}
