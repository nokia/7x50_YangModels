submodule nokia-conf-port-eth-egress {

    yang-version "1.1";

    belongs-to nokia-conf { prefix "conf"; }

    import nokia-sros-yang-extensions     { prefix "sros-ext"; }
    import nokia-types-qos                { prefix "types-qos"; }
    import nokia-types-sros               { prefix "types-sros"; }

    include nokia-conf-groups;
    include nokia-conf-qos;

    sros-ext:sros-major-release "rel26";
    organization "Nokia";
    contact
        "Nokia SR OS Support
         Web: <http://www.nokia.com>";
    description
        "Nokia YANG Data model to configure egress capabilities for ethernet ports on SR OS based routers.

         Copyright 2016 Nokia. All rights reserved. Reproduction of this document
         is authorized on the condition that the foregoing copyright notice is included.

         This nokia-conf-port-eth-egress YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-04-22";

    grouping conf-port-eth-egress {
        container egress {
            description "Enter the egress context";

            leaf hs-port-pool-policy {
                type leafref {
                    path "../../../../qos/hs-port-pool-policy/name";
                }
                description "HS port pool policy";
            }

            leaf monitor-port-scheduler {
                type boolean;
                default "false";
                description "Enable monitoring of egress scheduler";
            }

            leaf rate {
                type int32;
                units "kilobps";
                description "Rate of egress traffic";
            }

            leaf eth-bn-rate-changes {
                type boolean;
                default "false";
                description "Allow rate changes in ETH-BN messages on port-based MEP";
            }

            leaf-list apply-groups {
                type leafref {
                    path "../../../../groups/group/name";
                }
                max-elements 8;
                ordered-by user;
                description "Apply a configuration group at this level";
            }

            leaf-list apply-groups-exclude {
                type leafref {
                    path "../../../../groups/group/name";
                }
                max-elements 8;
                ordered-by user;
                description "Exclude a configuration group at this level";
            }

            container port-qos-policy {
                description "Enter the port-qos-policy context";

                leaf policy-name {
                    type leafref {
                        path "../../../../../qos/port-qos-policy/port-qos-policy-name";
                    }
                    description "Port QoS policy name";
                }

            } // container port-qos-policy


            container hs-scheduler-policy {
                description "Enter the hs-scheduler-policy context";

                leaf policy-name {
                    type leafref {
                        path "../../../../../qos/hs-scheduler-policy/name";
                    }
                    description "HS scheduler policy name";
                }

                container overrides {
                    presence "Enable the overrides context";
                    description "Enable the overrides context";

                    leaf max-rate {
                        type types-qos:hs-pir-rate-override;
                        units "megabps";
                        description "Maximum frame-based bandwidth limit";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                    list group {
                        key "group-id";
                        description "Enter the group list instance";

                        leaf group-id {
                            type uint32 {
                                range "1";
                            }
                            description "Group ID";
                        }

                        leaf rate {
                            type types-qos:hs-pir-rate-override;
                            units "megabps";
                            description "Maximum rate";
                        }

                        leaf-list apply-groups {
                            type leafref {
                                path "../../../../../../../groups/group/name";
                            }
                            max-elements 8;
                            ordered-by user;
                            description "Apply a configuration group at this level";
                        }

                        leaf-list apply-groups-exclude {
                            type leafref {
                                path "../../../../../../../groups/group/name";
                            }
                            max-elements 8;
                            ordered-by user;
                            description "Exclude a configuration group at this level";
                        }

                    } // list group

                    list scheduling-class {
                        key "class-number";
                        description "Enter the scheduling-class list instance";

                        leaf class-number {
                            type uint32 {
                                range "1..6";
                            }
                            description "Scheduling class value";
                        }

                        leaf rate {
                            type types-qos:hs-pir-rate-override;
                            units "megabps";
                            description "Maximum frame-based bandwidth limit";
                        }

                        leaf weight {
                            type types-qos:hs-wrr-weight-override;
                            description "Weight of the scheduling class within the group";
                        }

                        leaf-list apply-groups {
                            type leafref {
                                path "../../../../../../../groups/group/name";
                            }
                            max-elements 8;
                            ordered-by user;
                            description "Apply a configuration group at this level";
                        }

                        leaf-list apply-groups-exclude {
                            type leafref {
                                path "../../../../../../../groups/group/name";
                            }
                            max-elements 8;
                            ordered-by user;
                            description "Exclude a configuration group at this level";
                        }

                    } // list scheduling-class

                } // container overrides

            } // container hs-scheduler-policy

            container port-scheduler-policy {
                description "Enter the port-scheduler-policy context";

                leaf policy-name {
                    type leafref {
                        path "../../../../../qos/port-scheduler-policy/name";
                    }
                    description "Egress scheduler policy name";
                }

                container overrides {
                    presence "Enable the overrides context";
                    description "Enable the overrides context";

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                    container max-rate {
                        description "Enter the max-rate context";

                        choice rate-or-percent-rate {
                            case rate {

                                leaf rate {
                                    type types-qos:sched-pir-rate;
                                    units "kilobps";
                                    default "max";
                                    description "PIR rate";
                                }

                            }
                            case percent-rate {

                                leaf percent-rate {
                                    type decimal64 {
                                        range "0.01..100";
                                        fraction-digits 2;
                                    }
                                    units "percent";
                                    default "100";
                                    description "PIR rate";
                                }

                            }
                        }
                    } // container max-rate

                    list level {
                        key "priority-level";
                        description "Enter the level list instance";

                        leaf priority-level {
                            type uint32 {
                                range "1..8";
                            }
                            description "Port priority level to be overridden";
                        }

                        leaf-list apply-groups {
                            type leafref {
                                path "../../../../../../../groups/group/name";
                            }
                            max-elements 8;
                            ordered-by user;
                            description "Apply a configuration group at this level";
                        }

                        leaf-list apply-groups-exclude {
                            type leafref {
                                path "../../../../../../../groups/group/name";
                            }
                            max-elements 8;
                            ordered-by user;
                            description "Exclude a configuration group at this level";
                        }

                        choice rate-or-percent-rate {
                            case rate {

                                container rate {
                                    description "Enter the rate context";

                                    leaf pir {
                                        type types-qos:sched-pir-rate-ovr;
                                        units "kilobps";
                                        description "PIR";
                                    }

                                    leaf cir {
                                        type types-qos:sched-cir-rate-ovr;
                                        units "kilobps";
                                        description "CIR";
                                    }

                                } // container rate

                            }
                            case percent-rate {

                                container percent-rate {
                                    description "Enter the percent-rate context";

                                    leaf pir {
                                        type types-qos:pir-percent-override;
                                        units "percent";
                                        description "PIR for the the port scheduler policy";
                                    }

                                    leaf cir {
                                        type types-qos:cir-percent-override;
                                        units "percent";
                                        description "CIR for the port scheduler policy";
                                    }

                                } // container percent-rate

                            }
                        }
                    } // list level

                } // container overrides

            } // container port-scheduler-policy

            list hs-secondary-shaper {
                key "secondary-shaper-name";
                description "Enter the hs-secondary-shaper list instance";

                leaf secondary-shaper-name {
                    type types-sros:named-item;
                    description "Secondary shaper name";
                }

                leaf description {
                    type types-sros:description;
                    description "Text description";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                container aggregate {
                    description "Enter the aggregate context";

                    leaf low-burst-max-class {
                        type uint32 {
                            range "1..6";
                        }
                        default "6";
                        description "Highest scheduling class mapped to the low burst limit";
                    }

                    leaf rate {
                        type union {
                            type int32 {
                                range "1..100000000";
                            }
                            type enumeration {
                                enum max                            { value -1; }
                            }
                        }
                        units "kilobps";
                        default "max";
                        description "Rate allowed for the HS secondary shaper aggregate";
                    }

                } // container aggregate

                list class {
                    key "class-number";
                    description "Enter the class list instance";

                    leaf class-number {
                        type uint32 {
                            range "1..6";
                        }
                        description "HS secondary shaper class ID";
                    }

                    leaf rate {
                        type union {
                            type int32 {
                                range "1..100000000";
                            }
                            type enumeration {
                                enum max                            { value -1; }
                            }
                        }
                        units "kilobps";
                        default "max";
                        description "Rate allowed for the HS secondary shaper class";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // list class

            } // list hs-secondary-shaper

            container hw-agg-shaper-scheduler {
                description "Enter the hw-agg-shaper-scheduler context";

                leaf policy-name {
                    type leafref {
                        path "../../../../../qos/hw-agg-shaper-scheduler-policy/name";
                    }
                    description "Name of HW aggregate shaper scheduler policy";
                }

                leaf monitor {
                    type boolean;
                    default "false";
                    description "Allow monitoring of the HW aggregate shaper scheduler";
                }

            } // container hw-agg-shaper-scheduler

        } // container egress

    } // grouping conf-port-eth-egress

}
