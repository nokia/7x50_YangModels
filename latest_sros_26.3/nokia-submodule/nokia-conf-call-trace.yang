submodule nokia-conf-call-trace {

    yang-version "1.1";

    belongs-to nokia-conf { prefix "conf"; }

    import nokia-sros-yang-extensions     { prefix "sros-ext"; }
    import nokia-types-nat                { prefix "types-nat"; }
    import nokia-types-sros               { prefix "types-sros"; }

    include nokia-conf-groups;

    sros-ext:sros-major-release "rel26";
    organization "Nokia";
    contact
        "Nokia SR OS Support
         Web: <http://www.nokia.com>";
    description
        "Nokia YANG Data model to configure call-trace parameters on SR OS based routers.

         Copyright 2016 Nokia. All rights reserved. Reproduction of this document
         is authorized on the condition that the foregoing copyright notice is included.

         This nokia-conf-call-trace YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-05-27";

    grouping conf-call-trace {
        container call-trace {
            description "Enter the call-trace context";

            leaf max-files-number {
                type uint32 {
                    range "1..1024";
                }
                default "200";
                description "Maximum number of files call trace can create";
            }

            leaf primary-cf {
                type enumeration {
                    enum cf1                            { value 1; }
                    enum cf2                            { value 2; }
                }
                default "cf1";
                description "Primary CF card as local storage location";
            }

            leaf buffering {
                type boolean;
                default "false";
                description "Buffer messages until the trace key is known";
            }

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list location {
                key "location-type";
                description "Enter the location list instance";

                leaf location-type {
                    type enumeration {
                        enum cf1                            { value 1; }
                        enum cf2                            { value 2; }
                    }
                    description "Compact flash card to be used";
                }

                leaf admin-state {
                    type types-sros:admin-state;
                    default "enable";
                    description "Administrative state of compact flash for log storage";
                }

                leaf size-limit {
                    type union {
                        type uint32 {
                            range "1..65536";
                        }
                        type enumeration {
                            enum unlimited                      { value 0; }
                        }
                    }
                    default "1000";
                    description "Maximum cumulative size of call trace files on the card";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list location

            list trace-profile {
                key "name";
                description "Enter the trace-profile list instance";

                leaf name {
                    type types-sros:named-item;
                    description "Call trace profile name";
                }

                leaf description {
                    type types-sros:description;
                    description "Text description";
                }

                leaf size-limit {
                    type uint32 {
                        range "1..1000";
                    }
                    units "megabytes";
                    default "10";
                    description "Maximum data output for a single call trace operation";
                }

                leaf time-limit {
                    type types-sros:time-duration {
                        range "1..604800";
                    }
                    default "86400";
                    description "Maximum time for a single call trace job";
                }

                leaf events {
                    type enumeration {
                        enum public-only                    { value 2; }
                        enum all                            { value 3; }
                    }
                    description "Events to include in the captured trace";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container applications {
                    description "Enter the applications context";

                    leaf connectivity-management {
                        type boolean;
                        default "true";
                        description "Trace messages used for connectivity protocols";
                    }

                    leaf gx {
                        type boolean;
                        description "Trace Diameter messages used for the Gx application";
                    }

                    leaf gy {
                        type boolean;
                        description "Trace Diameter messages used for the Gy application";
                    }

                    leaf nasreq {
                        type boolean;
                        description "Trace Diameter messages used for NASREQ application";
                    }

                    leaf radius-auth {
                        type boolean;
                        default "true";
                        description "Trace RADIUS authentication messages and events";
                    }

                    leaf radius-acct {
                        type boolean;
                        default "true";
                        description "Trace messages and events for RADIUS-based accounting";
                    }

                    leaf pfcp {
                        type boolean;
                        description "Trace PFCP messages";
                    }

                    leaf python {
                        type boolean;
                        default "true";
                        description "Trace Python script execution";
                    }

                    leaf ludb {
                        type boolean;
                        default "true";
                        description "Trace local user database lookups";
                    }

                    leaf msap {
                        type boolean;
                        default "true";
                        description "Trace MSAP creation events";
                    }

                    leaf ppp-event {
                        type boolean;
                        default "false";
                        description "Allow tracing for PPP state machine related events";
                    }

                } // container applications

                container output {
                    description "Enter the output context";

                    choice destination {
                        default "local-storage";
                        case local-storage {

                            leaf local-storage {
                                type empty;
                                description "Destination for output";
                            }

                        }
                        case debug {

                            leaf debug {
                                type empty;
                                description "Enable output to the debug log";
                            }

                        }
                        case live {

                            container live {
                                presence "Enable the live context";
                                description "Enable the live context";

                                leaf port {
                                    type types-nat:port-number;
                                    default "29770";
                                    description "TCP IP port";
                                }

                                leaf router-instance {
                                    type string;
                                    default "Base";
                                    description "Router instance or VPRN service name";
                                }

                                choice live {
                                    mandatory true;
                                    case ip-address {

                                        leaf ip-address {
                                            type types-sros:ip-address;
                                            description "IP address of the live output destination server";
                                        }

                                    }
                                    case fqdn {

                                        leaf fqdn {
                                            type string {
                                                length "1..255";
                                            }
                                            description "Fully qualified domain name of live output destination";
                                        }

                                    }
                                }
                            } // container live

                        }
                    }
                } // container output

            } // list trace-profile

        } // container call-trace

    } // grouping conf-call-trace

}
