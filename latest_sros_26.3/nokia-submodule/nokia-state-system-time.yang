submodule nokia-state-system-time {

    yang-version "1.1";

    belongs-to nokia-state { prefix "state"; }

    import ietf-yang-types                { prefix "yang"; }
    import nokia-sros-yang-extensions     { prefix "sros-ext"; }
    import nokia-types-sros               { prefix "types-sros"; }
    import nokia-types-system             { prefix "types-system"; }

    include nokia-state-router;

    sros-ext:sros-major-release "rel26";
    organization "Nokia";
    contact
        "Nokia SR OS Support
         Web: <http://www.nokia.com>";
    description
        "Nokia YANG Data model with operational state for system time parameters on SR OS based routers.

         Copyright 2016 Nokia. All rights reserved. Reproduction of this document
         is authorized on the condition that the foregoing copyright notice is included.

         This nokia-state-system-time YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-05-27";

    grouping state-system-time {
        container time {
            description "Enter the time context";

            leaf zone-type {
                status obsolete;
                type enumeration {
                    enum system                         { value 1; }
                    enum user                           { value 2; }
                }
                description
                    "Zone-type will be 'system' if the zone defined by
                     'zone-name' is a system-defined zone. It will be
                     'user' if the zone has been defined by the user.

                     Deprecated in Release 24.3";
            }

            leaf current-active-time-zone {
                type string {
                    length "1..5";
                }
                description "The currently active time zone for this node.";
            }

            leaf daylight-saving-time-active {
                type boolean;
                description "Indicates if daylight saving time (DST) is currently active for this node.";
            }

            leaf offset-from-utc {
                type string {
                    length "4..6";
                }
                description
                    "The offset of the current time zone compared to Coordinated
                     Universal Time (UTC).
                     Represented as a string of the form '[-][h]h:mm'
                     where hh represents the number of hours, and mm represents the number of minutes
                     either behind (when negative) or ahead (when positive) of UTC";
            }

            container daylight-saving-time-zone {
                description "Enter the daylight-saving-time-zone context";

                leaf offset {
                    type uint32 {
                        range "0..60";
                    }
                    units "minutes";
                    description "Offset for summer time";
                }

                container end {
                    description "Enter the end context";

                    leaf week {
                        type types-system:week;
                        description "The week of the month when the summer time setting will end.";
                    }

                    leaf day {
                        type types-system:day-of-week-name-long;
                        description "The day of the week when the summer time setting will end.";
                    }

                    leaf month {
                        type types-system:month-name-long;
                        description "The month of the year when the summer time setting will end.";
                    }

                    leaf hours-minutes {
                        type types-system:hours-minutes-twenty-four;
                        description
                            "The hour and number of minutes after which the summer time will
                             stop taking effect.
                               hh - [00..23]
                               mm - [00..59]";
                    }

                } // container end

                container start {
                    description "Enter the start context";

                    leaf week {
                        type types-system:week;
                        description "The week of the month when the summer time setting will start.";
                    }

                    leaf day {
                        type types-system:day-of-week-name-long;
                        description "The day of the week when the summer time setting will start.";
                    }

                    leaf month {
                        type types-system:month-name-long;
                        description "The month of the year when the summer time setting will start.";
                    }

                    leaf hours-minutes {
                        type types-system:hours-minutes-twenty-four;
                        description
                            "The hour and number of minutes after which the summer time will
                             start taking effect.
                               hh - [00..23]
                               mm - [00..59]";
                    }

                } // container start

            } // container daylight-saving-time-zone

            container ntp {
                description "Enter the ntp context";

                container system-status {
                    description "Enter the system-status context";

                    leaf clock-refid {
                        type types-system:ntp-refid;
                        description
                            "A code identifying the particular server or reference
                             clock.  The interpretation depends upon stratum.  It
                             could be an IPv4 address, the first 32 bits of the MD5
                             hash of the IPv6 address, or a string for the Reference
                             Identifier and kiss codes.  Some examples:

                             -- a refclock ID like '127.127.1.0' for local clock sync

                             -- uni/multi/broadcast associations for IPv4 will look
                                like '203.0.113.1' and '0x4321FEDC' for IPv6

                             -- sync with primary source will look like 'DCN', 'NIST', 'ATOM'

                             -- kiss codes will look like 'AUTH', 'DROP', 'RATE'

                             Note that the use of MD5 hash for IPv6 address is not
                             for cryptographic purposes.";
                    }

                    leaf clock-stratum {
                        type types-system:ntp-stratum;
                        description
                            "The NTP entity's own stratum value.  Should be one
                             greater than the preceding level.
                             16 if unsynchronized.";
                    }

                    leaf current-time {
                        type types-system:ntp-date-and-time;
                        description "The time as currently known by the local ntp clock.";
                    }

                    leaf leap-pending {
                        type enumeration {
                            enum no-warning                     { value 0; }
                            enum add-second                     { value 1; }
                            enum subtract-second                { value 2; }
                            enum alarm                          { value 3; }
                        }
                        description
                            "Warning of an impending leap second to be inserted in the
                             NTP timescale.  The leaf will have a value on the day
                             of the leap second and then shall be cleared after midnight.
                             leap-pending causes the number of seconds (rollover interval)
                             in the day of insertion to be increased or decreased by one.";
                    }

                    leaf oper-state {
                        type types-sros:oper-state;
                        description "The operational state of NTP on the node.";
                    }

                    leaf poll {
                        type types-system:log2seconds;
                        description
                            "The minimum interval, in seconds as a power of two,
                             at which this NTP host polls other NTP servers to
                             synchronize its clock. For instance, a value of six
                             indicates a minimum interval of 64 seconds.";
                    }

                    leaf reference-time {
                        type types-system:ntp-date-and-time;
                        description
                            "The reference timestamp.  Time when the system clock was
                             last set or corrected.";
                    }

                    container time-source {
                        description "Enter the time-source context";

                        choice external-or-local {
                            case external {

                                leaf ip-address {
                                    type types-sros:ip-address;
                                    description "Identifies a node that is providing time to the NTP client of this system.";
                                }

                                leaf router-instance {
                                    type string;
                                }

                            }
                            case local {

                                leaf local {
                                    type enumeration {
                                        enum ptp                            { value 1; }
                                    }
                                }

                            }
                            case none {

                                leaf none {
                                    type empty;
                                }

                            }
                        }
                    } // container time-source

                    container authentication-errors {
                        description "Enter the authentication-errors context";

                        leaf total {
                            type yang:counter64;
                            description "The number of authentication check failures for this NTP clock.";
                        }

                        leaf ignored {
                            type yang:counter64;
                            description "The number of authentication check failures ignored for this NTP clock.";
                        }

                        leaf key-id {
                            type yang:counter64;
                            description "The number of authentication check failures due to key id.";
                        }

                        leaf key-type {
                            type yang:counter64;
                            description "The number of authentication check failures due to key type.";
                        }

                    } // container authentication-errors

                } // container system-status

                list server {
                    key "ip-address router-instance";
                    description "Enter the server list instance";

                    leaf ip-address {
                        type union {
                            type types-sros:ip-address;
                            type enumeration {
                                enum ptp                            { value 1; }
                            }
                        }
                    }

                    leaf router-instance {
                        type string;
                    }

                    leaf association-id {
                        type int32 {
                            range "0..2147483647";
                        }
                        description "Indicates the association identifier of this NTP server.";
                    }

                    leaf authentication-errors {
                        type yang:counter32;
                        description "Indicates the number of authentication check failures for this NTP server.";
                    }

                    leaf attributes {
                        type bits {
                            bit config                         { position 0; }
                            bit authenable                     { position 1; }
                            bit authentic                      { position 2; }
                            bit reachable                      { position 3; }
                            bit broadcastclient                { position 4; }
                            bit multicastclient                { position 5; }
                            bit broadcast                      { position 6; }
                            bit multicast                      { position 7; }
                        }
                        description
                            "Atributes for the peer assoication.
                             1 or more bits may be set, with values coded as follows:

                                0, config - If 1, the peer is a configured association.
                                   If 0, the peer is a temporary association.
                                1, authenable - If 1, the peer requires authentication.
                                   If 0, the peer does not require authentication.
                                2, authentic - If authenable is 1, if 1 the peer has passed
                                   authentication, if 0, the peer has failed authentication.
                                   If authenable is 0, this bit has no meaning.
                                3, reachable - If 1, the peer has been reached in 1 of the last 8
                                   polls. If 0, the peer is not reachable in the last 8 polls.
                                4, broadcastclient - If 1, the peer is a broadcast client temporary
                                   association created in response to discovering a broadcast
                                   server. If 0, the peer is not a broadcast client association.
                                5, multicastclient - If 1, the peer is a multicast client temporary
                                   association created in response to discovering a multicast
                                   server. If 0, the peer is not a multicast client association.
                                6, broadcast - If 1, the peer is a broadcast server association.
                                   If 0, the peer is not a broadcast association.
                                7, multicast - If 1, the peer is a multicast server association.
                                   If 0, the peer is not a multicast association.";
                    }

                    leaf last-message-received {
                        type types-system:ntp-date-and-time;
                        description
                            "The local time when the latest NTP message from this peer arrived.
                             If this peer becomes unreachable the value is set to zero.";
                    }

                    leaf local-poll {
                        type types-system:log2seconds;
                        description "The minimum interval, in seconds as a power of two, at which the local clock polls the peer";
                    }

                    leaf mode {
                        type enumeration {
                            enum unspecified                    { value 0; }
                            enum symmetric-active               { value 1; }
                            enum symmetric-passive              { value 2; }
                            enum client                         { value 3; }
                            enum server                         { value 4; }
                            enum broadcast                      { value 5; }
                            enum reserved-control               { value 6; }
                            enum reserved-private               { value 7; }
                            enum broadcast-client               { value 8; }
                        }
                        description
                            "Indicates the association mode, with values coded as follows:

                                0, unspecified
                                1, symmetric active - The host sends periodic messages regardless
                                        of the reachability state or stratum of this peer and so
                                        announces its willingness to synchronize and be synchronized
                                        by the peer.
                                2, symmetric passive - This association type is created upon receipt
                                        of a message from a peer operating in the symmetric active
                                        mode and lasts as long as the peer is reachable and operating
                                        at a stratum level less than or equal to the host.  Else the
                                        association is dissolved.  Such an association always lasts
                                        until at least one message has been sent in reply.  A host in
                                        this mode announces its willingness to synchronize and be
                                        synchronized by the peer.
                                3, client - Periodic messages are sent regardless of the reachability
                                        state or stratum of the peer.  A host in this mode announces
                                        its willingness to be synchronized by but not to synchronize
                                        the peer.
                                4, server - This association is created upon receipt of a client
                                        request message and exists only in order to reply to that
                                        request, after which the association is dissolved.  A host
                                        in this mode announces its willingness to synchronize,
                                        but not to be synchronized by the peer.
                                5, broadcast - Periodic messages are sent regardless of the
                                        reachability state or stratum of the peers.  A host in this
                                        mode announces its willingness to synchronize all of the
                                        peers but not to be synchronized by any of them.
                                6, reserved for NTP control messages
                                7, reserved for private use
                                8, broadcastclient - Messages are sent only in response to messages
                                        received from a broadcast server. A host in this mode is
                                        willing to be synchronized by any broadcast server.";
                    }

                    leaf offset {
                        type decimal64 {
                            fraction-digits 3;
                        }
                        units "milliseconds";
                        description
                            "The signed offset between the local clock and the peer clock,
                             e.g., '0.032ms' or '1.232ms'.
                             The negative value indicates that the local clock is behind the peer.";
                    }

                    leaf peer-poll {
                        type types-system:log2seconds;
                        description "The minimum interval, in seconds as a power of two, at which the peer polls the local clock";
                    }

                    leaf peer-refid {
                        type types-system:ntp-refid;
                        description
                            "The particular reference clock for this peer.
                             In the case of stratum 0 (unspecified) or stratum
                             1 (primary reference source), this is a four-octet,
                             left-justified,zero-padded ASCII string. In the case of stratum 2 and
                             greater (secondary reference) this is the four-octet Internet Address
                             for an IPv4 address or the first 32 bits of the MD5
                             hash of the IPv6 address.";
                    }

                    leaf preferred {
                        type boolean;
                        description "Indicates if this association is preferred";
                    }

                    leaf reach {
                        type string {
                            length "8";
                        }
                        description
                            "A string of length 8 where each character represents 1 bit in an 8-bit shift
                             register that tracks packet generation and receipt.
                             The character 'Y' represent receipt, or '.' otherwise.
                             A peer is considered reachable if at least one bit in this register is
                             set to one.  The data in this shift register is populated by
                             the NTP protocol processing.";
                    }

                    leaf receive-port {
                        type uint32;
                        description "UDP port number on which the peer receives NTP messages";
                    }

                    leaf status {
                        type enumeration {
                            enum reject                         { value 0; }
                            enum inaccurate                     { value 1; }
                            enum excess                         { value 2; }
                            enum outlyer                        { value 3; }
                            enum candidate                      { value 4; }
                            enum selected                       { value 5; }
                            enum syspeer                        { value 6; }
                            enum ppspeer                        { value 7; }
                        }
                        description
                            "Indicates the status of the peer, with values coded as follows:

                                0, reject - The peer is rejected and will not be used for
                                        synchronization. Rejection reasons could be the peer is
                                        unreachable, the peer is synchronized to this local server
                                        so synchronizing with it would create a sync loop, or the
                                        synchronization distance is too large.
                                1, inaccurate - The peer is not maintaining an accurate clock. This
                                        peer will not be used for synchronization.
                                2, excess - The peer's synchronization distance is greater than ten
                                        other peers. This peer will not be used for synchronization.
                                3, outlyer - The peer is discarded as an outlyer. This peer will not
                                        be used for synchronization.
                                4, candidate - The peer is accepted as a possible source of
                                        synchronization.
                                5, selected - The peer is an acceptable source of synchronization,
                                        but it's synchronization distance is greater than six other
                                        peers.
                                6, syspeer - The peer is chosen as the source of synchronization.
                                7, ppspeer - The peer is chosen as the source of synchronization, but
                                        the actual synchronization is occurring from a
                                        pulse-per-second (PPS) signal.";
                    }

                    leaf stratum {
                        type types-system:ntp-stratum;
                        description "Stratum level of the peer.";
                    }

                } // list server

                list peer {
                    key "ip-address router-instance";
                    description "Enter the peer list instance";

                    leaf ip-address {
                        type types-sros:ip-address;
                        description "Identifies a node that will provide time to the NTP client of this system.";
                    }

                    leaf router-instance {
                        type string;
                    }

                    leaf association-id {
                        type int32 {
                            range "0..2147483647";
                        }
                        description "Indicates the association identifier of this NTP server.";
                    }

                    leaf authentication-errors {
                        type yang:counter32;
                        description "Indicates the number of authentication check failures for this NTP server.";
                    }

                    leaf attributes {
                        type bits {
                            bit config                         { position 0; }
                            bit authenable                     { position 1; }
                            bit authentic                      { position 2; }
                            bit reachable                      { position 3; }
                            bit broadcastclient                { position 4; }
                            bit multicastclient                { position 5; }
                            bit broadcast                      { position 6; }
                            bit multicast                      { position 7; }
                        }
                        description
                            "Atributes for the peer assoication.
                             1 or more bits may be set, with values coded as follows:

                                0, config - If 1, the peer is a configured association.
                                   If 0, the peer is a temporary association.
                                1, authenable - If 1, the peer requires authentication.
                                   If 0, the peer does not require authentication.
                                2, authentic - If authenable is 1, if 1 the peer has passed
                                   authentication, if 0, the peer has failed authentication.
                                   If authenable is 0, this bit has no meaning.
                                3, reachable - If 1, the peer has been reached in 1 of the last 8
                                   polls. If 0, the peer is not reachable in the last 8 polls.
                                4, broadcastclient - If 1, the peer is a broadcast client temporary
                                   association created in response to discovering a broadcast
                                   server. If 0, the peer is not a broadcast client association.
                                5, multicastclient - If 1, the peer is a multicast client temporary
                                   association created in response to discovering a multicast
                                   server. If 0, the peer is not a multicast client association.
                                6, broadcast - If 1, the peer is a broadcast server association.
                                   If 0, the peer is not a broadcast association.
                                7, multicast - If 1, the peer is a multicast server association.
                                   If 0, the peer is not a multicast association.";
                    }

                    leaf last-message-received {
                        type types-system:ntp-date-and-time;
                        description
                            "The local time when the latest NTP message from this peer arrived.
                             If this peer becomes unreachable the value is set to zero.";
                    }

                    leaf local-poll {
                        type types-system:log2seconds;
                        description "The minimum interval, in seconds as a power of two, at which the local clock polls the peer";
                    }

                    leaf mode {
                        type enumeration {
                            enum unspecified                    { value 0; }
                            enum symmetric-active               { value 1; }
                            enum symmetric-passive              { value 2; }
                            enum client                         { value 3; }
                            enum server                         { value 4; }
                            enum broadcast                      { value 5; }
                            enum reserved-control               { value 6; }
                            enum reserved-private               { value 7; }
                            enum broadcast-client               { value 8; }
                        }
                        description
                            "Indicates the association mode, with values coded as follows:

                                0, unspecified
                                1, symmetric active - The host sends periodic messages regardless
                                        of the reachability state or stratum of this peer and so
                                        announces its willingness to synchronize and be synchronized
                                        by the peer.
                                2, symmetric passive - This association type is created upon receipt
                                        of a message from a peer operating in the symmetric active
                                        mode and lasts as long as the peer is reachable and operating
                                        at a stratum level less than or equal to the host.  Else the
                                        association is dissolved.  Such an association always lasts
                                        until at least one message has been sent in reply.  A host in
                                        this mode announces its willingness to synchronize and be
                                        synchronized by the peer.
                                3, client - Periodic messages are sent regardless of the reachability
                                        state or stratum of the peer.  A host in this mode announces
                                        its willingness to be synchronized by but not to synchronize
                                        the peer.
                                4, server - This association is created upon receipt of a client
                                        request message and exists only in order to reply to that
                                        request, after which the association is dissolved.  A host
                                        in this mode announces its willingness to synchronize,
                                        but not to be synchronized by the peer.
                                5, broadcast - Periodic messages are sent regardless of the
                                        reachability state or stratum of the peers.  A host in this
                                        mode announces its willingness to synchronize all of the
                                        peers but not to be synchronized by any of them.
                                6, reserved for NTP control messages
                                7, reserved for private use
                                8, broadcastclient - Messages are sent only in response to messages
                                        received from a broadcast server. A host in this mode is
                                        willing to be synchronized by any broadcast server.";
                    }

                    leaf offset {
                        type decimal64 {
                            fraction-digits 3;
                        }
                        units "milliseconds";
                        description
                            "The signed offset between the local clock and the peer clock,
                             e.g., '0.032ms' or '1.232ms'.
                             The negative value indicates that the local clock is behind the peer.";
                    }

                    leaf peer-poll {
                        type types-system:log2seconds;
                        description "The minimum interval, in seconds as a power of two, at which the peer polls the local clock";
                    }

                    leaf peer-refid {
                        type types-system:ntp-refid;
                        description
                            "The particular reference clock for this peer.
                             In the case of stratum 0 (unspecified) or stratum
                             1 (primary reference source), this is a four-octet,
                             left-justified,zero-padded ASCII string. In the case of stratum 2 and
                             greater (secondary reference) this is the four-octet Internet Address
                             for an IPv4 address or the first 32 bits of the MD5
                             hash of the IPv6 address.";
                    }

                    leaf preferred {
                        type boolean;
                        description "Indicates if this association is preferred";
                    }

                    leaf reach {
                        type string {
                            length "8";
                        }
                        description
                            "A string of length 8 where each character represents 1 bit in an 8-bit shift
                             register that tracks packet generation and receipt.
                             The character 'Y' represent receipt, or '.' otherwise.
                             A peer is considered reachable if at least one bit in this register is
                             set to one.  The data in this shift register is populated by
                             the NTP protocol processing.";
                    }

                    leaf receive-port {
                        type uint32;
                        description "UDP port number on which the peer receives NTP messages";
                    }

                    leaf status {
                        type enumeration {
                            enum reject                         { value 0; }
                            enum inaccurate                     { value 1; }
                            enum excess                         { value 2; }
                            enum outlyer                        { value 3; }
                            enum candidate                      { value 4; }
                            enum selected                       { value 5; }
                            enum syspeer                        { value 6; }
                            enum ppspeer                        { value 7; }
                        }
                        description
                            "Indicates the status of the peer, with values coded as follows:

                                0, reject - The peer is rejected and will not be used for
                                        synchronization. Rejection reasons could be the peer is
                                        unreachable, the peer is synchronized to this local server
                                        so synchronizing with it would create a sync loop, or the
                                        synchronization distance is too large.
                                1, inaccurate - The peer is not maintaining an accurate clock. This
                                        peer will not be used for synchronization.
                                2, excess - The peer's synchronization distance is greater than ten
                                        other peers. This peer will not be used for synchronization.
                                3, outlyer - The peer is discarded as an outlyer. This peer will not
                                        be used for synchronization.
                                4, candidate - The peer is accepted as a possible source of
                                        synchronization.
                                5, selected - The peer is an acceptable source of synchronization,
                                        but it's synchronization distance is greater than six other
                                        peers.
                                6, syspeer - The peer is chosen as the source of synchronization.
                                7, ppspeer - The peer is chosen as the source of synchronization, but
                                        the actual synchronization is occurring from a
                                        pulse-per-second (PPS) signal.";
                    }

                    leaf stratum {
                        type types-system:ntp-stratum;
                        description "Stratum level of the peer.";
                    }

                } // list peer

                list broadcast {
                    key "router-instance interface-name";
                    description "Enter the broadcast list instance";

                    leaf router-instance {
                        type leafref {
                            path "../../../../../router/router-name";
                        }
                        description
                            "The administrative name for this virtual router. The router
                             name must be unique among all virtual routers in the system.";
                    }

                    leaf interface-name {
                        type types-sros:interface-name;
                        description "Router interface name.";
                    }

                    leaf association-id {
                        type int32 {
                            range "0..max";
                        }
                        description
                            "Indicates the association identifier of this NTP broadcast server.
                             This is the index value for NTP Peers Association Id of the row in the 'system-time-ntp-peer' table
                             that represents this NTP broadcast server.";
                    }

                    leaf auth-errors {
                        status obsolete;
                        type yang:counter32;
                        description
                            "Indicates the number of times the NTP Authentication Mismatch notification has been
                             generated because of an authentication check failure on this broadcast interface.

                             Deprecated in Release 23.10 and replaced with authentication-errors.
                             Obsoleted in Release 24.3";
                    }

                    leaf authentication-errors {
                        type yang:counter32;
                        description
                            "Indicates the number of times the NTP Authentication Mismatch notification has been
                             generated because of an authentication check failure on this broadcast interface.";
                    }

                } // list broadcast

                list broadcast-client {
                    key "router-instance interface-name";
                    description "Enter the broadcast-client list instance";

                    leaf router-instance {
                        type string;
                        description
                            "The administrative name for this virtual router. The router
                             name must be unique among all virtual routers in the system.";
                    }

                    leaf interface-name {
                        type types-sros:interface-name;
                        description "Router interface name.";
                    }

                    leaf association-id {
                        type int32 {
                            range "0..max";
                        }
                        description
                            "Indicates the association identifier of this NTP broadcast server.
                             This is the index value for NTP Peers Association Id of the row in the 'system-time-ntp-peer' table
                             that represents this NTP broadcast server.";
                    }

                    leaf auth-errors {
                        status obsolete;
                        type yang:counter32;
                        description
                            "Indicates the number of times the NTP Authentication Mismatch notification has been
                             generated because of an authentication check failure on this broadcast interface.

                             Deprecated in Release 23.10 and replaced with authentication-errors.
                             Obsoleted in Release 24.3";
                    }

                    leaf authentication-errors {
                        type yang:counter32;
                        description
                            "Indicates the number of times the NTP Authentication Mismatch notification has been
                             generated because of an authentication check failure on this broadcast interface.";
                    }

                    leaf attributes {
                        type bits {
                            bit config                         { position 0; }
                            bit authenable                     { position 1; }
                            bit authentic                      { position 2; }
                            bit reachable                      { position 3; }
                            bit broadcastclient                { position 4; }
                            bit multicastclient                { position 5; }
                            bit broadcast                      { position 6; }
                            bit multicast                      { position 7; }
                        }
                        description
                            "Atributes for the peer assoication.
                             1 or more bits may be set, with values coded as follows:

                                0, config - If 1, the peer is a configured association.
                                   If 0, the peer is a temporary association.
                                1, authenable - If 1, the peer requires authentication.
                                   If 0, the peer does not require authentication.
                                2, authentic - If authenable is 1, if 1 the peer has passed
                                   authentication, if 0, the peer has failed authentication.
                                   If authenable is 0, this bit has no meaning.
                                3, reachable - If 1, the peer has been reached in 1 of the last 8
                                   polls. If 0, the peer is not reachable in the last 8 polls.
                                4, broadcastclient - If 1, the peer is a broadcast client temporary
                                   association created in response to discovering a broadcast
                                   server. If 0, the peer is not a broadcast client association.
                                5, multicastclient - If 1, the peer is a multicast client temporary
                                   association created in response to discovering a multicast
                                   server. If 0, the peer is not a multicast client association.
                                6, broadcast - If 1, the peer is a broadcast server association.
                                   If 0, the peer is not a broadcast association.
                                7, multicast - If 1, the peer is a multicast server association.
                                   If 0, the peer is not a multicast association.";
                    }

                    leaf last-message-received {
                        type types-system:ntp-date-and-time;
                        description
                            "The local time when the latest NTP message from this peer arrived.
                             If this peer becomes unreachable the value is set to zero.";
                    }

                    leaf local-poll {
                        type types-system:log2seconds;
                        description "The minimum interval, in seconds as a power of two, at which the local clock polls the peer";
                    }

                    leaf mode {
                        type enumeration {
                            enum unspecified                    { value 0; }
                            enum symmetric-active               { value 1; }
                            enum symmetric-passive              { value 2; }
                            enum client                         { value 3; }
                            enum server                         { value 4; }
                            enum broadcast                      { value 5; }
                            enum reserved-control               { value 6; }
                            enum reserved-private               { value 7; }
                            enum broadcast-client               { value 8; }
                        }
                        description
                            "Indicates the association mode, with values coded as follows:

                                0, unspecified
                                1, symmetric active - The host sends periodic messages regardless
                                        of the reachability state or stratum of this peer and so
                                        announces its willingness to synchronize and be synchronized
                                        by the peer.
                                2, symmetric passive - This association type is created upon receipt
                                        of a message from a peer operating in the symmetric active
                                        mode and lasts as long as the peer is reachable and operating
                                        at a stratum level less than or equal to the host.  Else the
                                        association is dissolved.  Such an association always lasts
                                        until at least one message has been sent in reply.  A host in
                                        this mode announces its willingness to synchronize and be
                                        synchronized by the peer.
                                3, client - Periodic messages are sent regardless of the reachability
                                        state or stratum of the peer.  A host in this mode announces
                                        its willingness to be synchronized by but not to synchronize
                                        the peer.
                                4, server - This association is created upon receipt of a client
                                        request message and exists only in order to reply to that
                                        request, after which the association is dissolved.  A host
                                        in this mode announces its willingness to synchronize,
                                        but not to be synchronized by the peer.
                                5, broadcast - Periodic messages are sent regardless of the
                                        reachability state or stratum of the peers.  A host in this
                                        mode announces its willingness to synchronize all of the
                                        peers but not to be synchronized by any of them.
                                6, reserved for NTP control messages
                                7, reserved for private use
                                8, broadcastclient - Messages are sent only in response to messages
                                        received from a broadcast server. A host in this mode is
                                        willing to be synchronized by any broadcast server.";
                    }

                    leaf offset {
                        type decimal64 {
                            fraction-digits 3;
                        }
                        units "milliseconds";
                        description
                            "The signed offset between the local clock and the peer clock,
                             e.g., '0.032ms' or '1.232ms'.
                             The negative value indicates that the local clock is behind the peer.";
                    }

                    leaf peer-poll {
                        type types-system:log2seconds;
                        description "The minimum interval, in seconds as a power of two, at which the peer polls the local clock";
                    }

                    leaf peer-refid {
                        type types-system:ntp-refid;
                        description
                            "The particular reference clock for this peer.
                             In the case of stratum 0 (unspecified) or stratum
                             1 (primary reference source), this is a four-octet,
                             left-justified,zero-padded ASCII string. In the case of stratum 2 and
                             greater (secondary reference) this is the four-octet Internet Address
                             for an IPv4 address or the first 32 bits of the MD5
                             hash of the IPv6 address.";
                    }

                    leaf preferred {
                        type boolean;
                        description "Indicates if this association is preferred";
                    }

                    leaf reach {
                        type string {
                            length "8";
                        }
                        description
                            "A string of length 8 where each character represents 1 bit in an 8-bit shift
                             register that tracks packet generation and receipt.
                             The character 'Y' represent receipt, or '.' otherwise.
                             A peer is considered reachable if at least one bit in this register is
                             set to one.  The data in this shift register is populated by
                             the NTP protocol processing.";
                    }

                    leaf receive-port {
                        type uint32;
                        description "UDP port number on which the peer receives NTP messages";
                    }

                    leaf status {
                        type enumeration {
                            enum reject                         { value 0; }
                            enum inaccurate                     { value 1; }
                            enum excess                         { value 2; }
                            enum outlyer                        { value 3; }
                            enum candidate                      { value 4; }
                            enum selected                       { value 5; }
                            enum syspeer                        { value 6; }
                            enum ppspeer                        { value 7; }
                        }
                        description
                            "Indicates the status of the peer, with values coded as follows:

                                0, reject - The peer is rejected and will not be used for
                                        synchronization. Rejection reasons could be the peer is
                                        unreachable, the peer is synchronized to this local server
                                        so synchronizing with it would create a sync loop, or the
                                        synchronization distance is too large.
                                1, inaccurate - The peer is not maintaining an accurate clock. This
                                        peer will not be used for synchronization.
                                2, excess - The peer's synchronization distance is greater than ten
                                        other peers. This peer will not be used for synchronization.
                                3, outlyer - The peer is discarded as an outlyer. This peer will not
                                        be used for synchronization.
                                4, candidate - The peer is accepted as a possible source of
                                        synchronization.
                                5, selected - The peer is an acceptable source of synchronization,
                                        but it's synchronization distance is greater than six other
                                        peers.
                                6, syspeer - The peer is chosen as the source of synchronization.
                                7, ppspeer - The peer is chosen as the source of synchronization, but
                                        the actual synchronization is occurring from a
                                        pulse-per-second (PPS) signal.";
                    }

                    leaf stratum {
                        type types-system:ntp-stratum;
                        description "Stratum level of the peer.";
                    }

                } // list broadcast-client

                container multicast {
                    description "Enter the multicast context";

                    leaf association-id {
                        type int32 {
                            range "0..max";
                        }
                        description
                            "Indicates the association identifier of this NTP broadcast server.
                             This is the index value for NTP Peers Association Id of the row in the 'system-time-ntp-peer' table
                             that represents this NTP broadcast server.";
                    }

                    leaf auth-errors {
                        status obsolete;
                        type yang:counter32;
                        description
                            "Indicates the number of times the NTP Authentication Mismatch notification has been
                             generated because of an authentication check failure on this broadcast interface.

                             Deprecated in Release 23.10 and replaced with authentication-errors.
                             Obsoleted in Release 24.3";
                    }

                    leaf authentication-errors {
                        type yang:counter32;
                        description
                            "Indicates the number of times the NTP Authentication Mismatch notification has been
                             generated because of an authentication check failure on this broadcast interface.";
                    }

                } // container multicast

                container multicast-client {
                    description "Enter the multicast-client context";

                    leaf association-id {
                        type int32 {
                            range "0..max";
                        }
                        description
                            "Indicates the association identifier of this NTP broadcast server.
                             This is the index value for NTP Peers Association Id of the row in the 'system-time-ntp-peer' table
                             that represents this NTP broadcast server.";
                    }

                    leaf auth-errors {
                        status obsolete;
                        type yang:counter32;
                        description
                            "Indicates the number of times the NTP Authentication Mismatch notification has been
                             generated because of an authentication check failure on this broadcast interface.

                             Deprecated in Release 23.10 and replaced with authentication-errors.
                             Obsoleted in Release 24.3";
                    }

                    leaf authentication-errors {
                        type yang:counter32;
                        description
                            "Indicates the number of times the NTP Authentication Mismatch notification has been
                             generated because of an authentication check failure on this broadcast interface.";
                    }

                    leaf attributes {
                        type bits {
                            bit config                         { position 0; }
                            bit authenable                     { position 1; }
                            bit authentic                      { position 2; }
                            bit reachable                      { position 3; }
                            bit broadcastclient                { position 4; }
                            bit multicastclient                { position 5; }
                            bit broadcast                      { position 6; }
                            bit multicast                      { position 7; }
                        }
                        description
                            "Atributes for the peer assoication.
                             1 or more bits may be set, with values coded as follows:

                                0, config - If 1, the peer is a configured association.
                                   If 0, the peer is a temporary association.
                                1, authenable - If 1, the peer requires authentication.
                                   If 0, the peer does not require authentication.
                                2, authentic - If authenable is 1, if 1 the peer has passed
                                   authentication, if 0, the peer has failed authentication.
                                   If authenable is 0, this bit has no meaning.
                                3, reachable - If 1, the peer has been reached in 1 of the last 8
                                   polls. If 0, the peer is not reachable in the last 8 polls.
                                4, broadcastclient - If 1, the peer is a broadcast client temporary
                                   association created in response to discovering a broadcast
                                   server. If 0, the peer is not a broadcast client association.
                                5, multicastclient - If 1, the peer is a multicast client temporary
                                   association created in response to discovering a multicast
                                   server. If 0, the peer is not a multicast client association.
                                6, broadcast - If 1, the peer is a broadcast server association.
                                   If 0, the peer is not a broadcast association.
                                7, multicast - If 1, the peer is a multicast server association.
                                   If 0, the peer is not a multicast association.";
                    }

                    leaf last-message-received {
                        type types-system:ntp-date-and-time;
                        description
                            "The local time when the latest NTP message from this peer arrived.
                             If this peer becomes unreachable the value is set to zero.";
                    }

                    leaf local-poll {
                        type types-system:log2seconds;
                        description "The minimum interval, in seconds as a power of two, at which the local clock polls the peer";
                    }

                    leaf mode {
                        type enumeration {
                            enum unspecified                    { value 0; }
                            enum symmetric-active               { value 1; }
                            enum symmetric-passive              { value 2; }
                            enum client                         { value 3; }
                            enum server                         { value 4; }
                            enum broadcast                      { value 5; }
                            enum reserved-control               { value 6; }
                            enum reserved-private               { value 7; }
                            enum broadcast-client               { value 8; }
                        }
                        description
                            "Indicates the association mode, with values coded as follows:

                                0, unspecified
                                1, symmetric active - The host sends periodic messages regardless
                                        of the reachability state or stratum of this peer and so
                                        announces its willingness to synchronize and be synchronized
                                        by the peer.
                                2, symmetric passive - This association type is created upon receipt
                                        of a message from a peer operating in the symmetric active
                                        mode and lasts as long as the peer is reachable and operating
                                        at a stratum level less than or equal to the host.  Else the
                                        association is dissolved.  Such an association always lasts
                                        until at least one message has been sent in reply.  A host in
                                        this mode announces its willingness to synchronize and be
                                        synchronized by the peer.
                                3, client - Periodic messages are sent regardless of the reachability
                                        state or stratum of the peer.  A host in this mode announces
                                        its willingness to be synchronized by but not to synchronize
                                        the peer.
                                4, server - This association is created upon receipt of a client
                                        request message and exists only in order to reply to that
                                        request, after which the association is dissolved.  A host
                                        in this mode announces its willingness to synchronize,
                                        but not to be synchronized by the peer.
                                5, broadcast - Periodic messages are sent regardless of the
                                        reachability state or stratum of the peers.  A host in this
                                        mode announces its willingness to synchronize all of the
                                        peers but not to be synchronized by any of them.
                                6, reserved for NTP control messages
                                7, reserved for private use
                                8, broadcastclient - Messages are sent only in response to messages
                                        received from a broadcast server. A host in this mode is
                                        willing to be synchronized by any broadcast server.";
                    }

                    leaf offset {
                        type decimal64 {
                            fraction-digits 3;
                        }
                        units "milliseconds";
                        description
                            "The signed offset between the local clock and the peer clock,
                             e.g., '0.032ms' or '1.232ms'.
                             The negative value indicates that the local clock is behind the peer.";
                    }

                    leaf peer-poll {
                        type types-system:log2seconds;
                        description "The minimum interval, in seconds as a power of two, at which the peer polls the local clock";
                    }

                    leaf peer-refid {
                        type types-system:ntp-refid;
                        description
                            "The particular reference clock for this peer.
                             In the case of stratum 0 (unspecified) or stratum
                             1 (primary reference source), this is a four-octet,
                             left-justified,zero-padded ASCII string. In the case of stratum 2 and
                             greater (secondary reference) this is the four-octet Internet Address
                             for an IPv4 address or the first 32 bits of the MD5
                             hash of the IPv6 address.";
                    }

                    leaf preferred {
                        type boolean;
                        description "Indicates if this association is preferred";
                    }

                    leaf reach {
                        type string {
                            length "8";
                        }
                        description
                            "A string of length 8 where each character represents 1 bit in an 8-bit shift
                             register that tracks packet generation and receipt.
                             The character 'Y' represent receipt, or '.' otherwise.
                             A peer is considered reachable if at least one bit in this register is
                             set to one.  The data in this shift register is populated by
                             the NTP protocol processing.";
                    }

                    leaf receive-port {
                        type uint32;
                        description "UDP port number on which the peer receives NTP messages";
                    }

                    leaf status {
                        type enumeration {
                            enum reject                         { value 0; }
                            enum inaccurate                     { value 1; }
                            enum excess                         { value 2; }
                            enum outlyer                        { value 3; }
                            enum candidate                      { value 4; }
                            enum selected                       { value 5; }
                            enum syspeer                        { value 6; }
                            enum ppspeer                        { value 7; }
                        }
                        description
                            "Indicates the status of the peer, with values coded as follows:

                                0, reject - The peer is rejected and will not be used for
                                        synchronization. Rejection reasons could be the peer is
                                        unreachable, the peer is synchronized to this local server
                                        so synchronizing with it would create a sync loop, or the
                                        synchronization distance is too large.
                                1, inaccurate - The peer is not maintaining an accurate clock. This
                                        peer will not be used for synchronization.
                                2, excess - The peer's synchronization distance is greater than ten
                                        other peers. This peer will not be used for synchronization.
                                3, outlyer - The peer is discarded as an outlyer. This peer will not
                                        be used for synchronization.
                                4, candidate - The peer is accepted as a possible source of
                                        synchronization.
                                5, selected - The peer is an acceptable source of synchronization,
                                        but it's synchronization distance is greater than six other
                                        peers.
                                6, syspeer - The peer is chosen as the source of synchronization.
                                7, ppspeer - The peer is chosen as the source of synchronization, but
                                        the actual synchronization is occurring from a
                                        pulse-per-second (PPS) signal.";
                    }

                    leaf stratum {
                        type types-system:ntp-stratum;
                        description "Stratum level of the peer.";
                    }

                } // container multicast-client

                list client {
                    key "ip-address router-instance";
                    description "Enter the client list instance";

                    leaf ip-address {
                        type types-sros:ip-address-with-zone;
                        description "Identifies a node that will provide time to the NTP client of this system.";
                    }

                    leaf router-instance {
                        type string;
                    }

                    leaf last-message-received {
                        type types-system:ntp-date-and-time;
                        description "The local time when the latest NTP message from this client arrived.";
                    }

                } // list client

                container statistics {
                    description "Enter the statistics context";

                    leaf transmitted-packets {
                        type yang:counter64;
                        description "Total packets transmitted by the NTP process.";
                    }

                    leaf received-packets {
                        type yang:counter64;
                        description "Total packets received into the NTP process";
                    }

                    leaf processed-packets {
                        type yang:counter64;
                        description
                            "Total valid packets received into the NTP process.
                             A packet is not included if it discarded before processing based on it
                             being malformed or including invalid field values or other reasons.";
                    }

                } // container statistics

            } // container ntp


            container sntp {
                description "Enter the sntp context";

                leaf oper-state {
                    type types-sros:oper-state;
                    description "Indicates the current operational status of SNTP.";
                }

            } // container sntp

        } // container time

    } // grouping state-system-time

}
