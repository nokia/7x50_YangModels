submodule nokia-conf-anysec {

    yang-version "1.1";

    belongs-to nokia-conf { prefix "conf"; }

    import nokia-sros-yang-extensions     { prefix "sros-ext"; }
    import nokia-types-router             { prefix "types-router"; }
    import nokia-types-security           { prefix "types-security"; }
    import nokia-types-sros               { prefix "types-sros"; }

    include nokia-conf-groups;
    include nokia-conf-macsec;
    include nokia-conf-router;

    sros-ext:sros-major-release "rel26";
    organization "Nokia";
    contact
        "Nokia SR OS Support
         Web: <http://www.nokia.com>";
    description
        "Nokia YANG Data model to configure ANYsec on SR OS based routers.

         Copyright 2016 Nokia. All rights reserved. Reproduction of this document
         is authorized on the condition that the foregoing copyright notice is included.

         This nokia-conf-anysec YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-04-22";

    grouping conf-anysec {
        container anysec {
            description "Enter the anysec context";

            leaf reserved-label-block {
                type leafref {
                    path "../../router/mpls-labels/reserved-label-block/label-block-name";
                }
                description "ANYSec reserved label block";
            }

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            container mka-over-ip {
                description "Enter the mka-over-ip context";

                leaf mka-udp-port {
                    type types-sros:tcp-udp-port {
                        range "1024..49151";
                    }
                    description "ANYSec MKA UDP port";
                }

            } // container mka-over-ip

            container mpls {
                description "Enter the mpls context";

                container security-termination-policies {
                    description "Enter the security-termination-policies context";

                    list policy {
                        key "policy-name";
                        max-elements 1023;
                        description "Enter the policy list instance";

                        leaf policy-name {
                            type types-sros:named-item;
                            description "ANYsec security termination policy name";
                        }

                        leaf local-address {
                            type types-sros:ip-unicast-address;
                            sros-ext:auto-restart-to-modify;
                            description "Local address of node SID associated with ANYsec tunnel";
                        }

                        leaf rx-must-be-encrypted {
                            type boolean;
                            default "false";
                            description "Enforce encryption for received packets";
                        }

                        leaf admin-state {
                            type types-sros:admin-state;
                            default "disable";
                            description "Administrative state of the security termination policy";
                        }

                        leaf protocol {
                            type types-security:anysec-protocol;
                            sros-ext:auto-restart-to-modify;
                            description "Protocol used to advertise node SID of incoming tunnel";
                        }

                        leaf igp-instance-id {
                            type types-security:anysec-igp-instance-id;
                            sros-ext:auto-restart-to-modify;
                            description "IGP instance ID";
                        }

                        leaf flex-algo-id {
                            type types-router:flex-algo-id;
                            sros-ext:auto-restart-to-modify;
                            description "Flexible algorithm ID";
                        }

                        leaf-list apply-groups {
                            type leafref {
                                path "../../../../../groups/group/name";
                            }
                            max-elements 8;
                            ordered-by user;
                            sros-ext:auto-restart-to-modify;
                            description "Apply a configuration group at this level";
                        }

                        leaf-list apply-groups-exclude {
                            type leafref {
                                path "../../../../../groups/group/name";
                            }
                            max-elements 8;
                            ordered-by user;
                            sros-ext:auto-restart-to-modify;
                            description "Exclude a configuration group at this level";
                        }

                    } // list policy

                } // container security-termination-policies

                container tunnel-encryption {
                    description "Enter the tunnel-encryption context";

                    list encryption-group {
                        key "group-name";
                        max-elements 1023;
                        description "Enter the encryption-group list instance";

                        leaf group-name {
                            type types-sros:named-item;
                            description "ANYsec encryption group name";
                        }

                        leaf security-termination-policy {
                            type leafref {
                                path "../../../security-termination-policies/policy/policy-name";
                            }
                            sros-ext:auto-restart-to-modify;
                            description "Security termination policy used by encryption group";
                        }

                        leaf encryption-label {
                            type types-sros:mpls-label-or-zero;
                            sros-ext:auto-restart-to-modify;
                            description "Label identifying packets sent from the node to peers";
                        }

                        leaf ca-name {
                            type leafref {
                                path "../../../../../macsec/connectivity-association/ca-name";
                            }
                            sros-ext:auto-restart-to-modify;
                            description "Connectivity association for the encryption group";
                        }

                        leaf admin-state {
                            type types-sros:admin-state;
                            default "disable";
                            description "Administrative state of the encryption group";
                        }

                        leaf allow-entropy-label {
                            type boolean;
                            sros-ext:auto-restart-to-modify;
                            default "false";
                            description "Allow EL and ELI by this encryption group";
                        }

                        leaf-list apply-groups {
                            type leafref {
                                path "../../../../../groups/group/name";
                            }
                            max-elements 8;
                            ordered-by user;
                            sros-ext:auto-restart-to-modify;
                            description "Apply a configuration group at this level";
                        }

                        leaf-list apply-groups-exclude {
                            type leafref {
                                path "../../../../../groups/group/name";
                            }
                            max-elements 8;
                            ordered-by user;
                            sros-ext:auto-restart-to-modify;
                            description "Exclude a configuration group at this level";
                        }

                        container peer-tunnel-attributes {
                            sros-ext:auto-restart-to-modify;
                            description "Enter the peer-tunnel-attributes context";

                            leaf protocol {
                                type types-security:anysec-protocol;
                                sros-ext:auto-restart-to-modify;
                                description "Protocol used to advertise node SID of incoming tunnel";
                            }

                            leaf igp-instance-id {
                                type types-security:anysec-igp-instance-id;
                                sros-ext:auto-restart-to-modify;
                                description "IGP instance ID";
                            }

                            leaf flex-algo-id {
                                type types-router:flex-algo-id;
                                sros-ext:auto-restart-to-modify;
                                description "Flexible algorithm ID";
                            }

                        } // container peer-tunnel-attributes

                        list peer {
                            key "peer-ip-address";
                            max-elements 1023;
                            description "Enter the peer list instance";

                            leaf peer-ip-address {
                                type types-sros:ip-unicast-address;
                                description "Peer IP address of the node SID";
                            }

                            leaf admin-state {
                                type types-sros:admin-state;
                                default "disable";
                                description "Administrative state of the encryption group peer";
                            }

                            leaf-list apply-groups {
                                type leafref {
                                    path "../../../../../../groups/group/name";
                                }
                                max-elements 8;
                                ordered-by user;
                                sros-ext:auto-restart-to-modify;
                                description "Apply a configuration group at this level";
                            }

                            leaf-list apply-groups-exclude {
                                type leafref {
                                    path "../../../../../../groups/group/name";
                                }
                                max-elements 8;
                                ordered-by user;
                                sros-ext:auto-restart-to-modify;
                                description "Exclude a configuration group at this level";
                            }

                        } // list peer

                    } // list encryption-group

                } // container tunnel-encryption

                container service-encryption {
                    description "Enter the service-encryption context";

                    list encryption-group {
                        key "group-name";
                        max-elements 1023;
                        description "Enter the encryption-group list instance";

                        leaf group-name {
                            type types-sros:named-item;
                            description "ANYsec encryption group name";
                        }

                        leaf security-termination-policy {
                            type leafref {
                                path "../../../security-termination-policies/policy/policy-name";
                            }
                            sros-ext:auto-restart-to-modify;
                            description "Security termination policy used by encryption group";
                        }

                        leaf encryption-label {
                            type types-sros:mpls-label-or-zero;
                            sros-ext:auto-restart-to-modify;
                            description "Label identifying packets sent from the node to peers";
                        }

                        leaf ca-name {
                            type leafref {
                                path "../../../../../macsec/connectivity-association/ca-name";
                            }
                            sros-ext:auto-restart-to-modify;
                            description "Connectivity association for the encryption group";
                        }

                        leaf admin-state {
                            type types-sros:admin-state;
                            default "disable";
                            description "Administrative state of the encryption group";
                        }

                        leaf-list apply-groups {
                            type leafref {
                                path "../../../../../groups/group/name";
                            }
                            max-elements 8;
                            ordered-by user;
                            sros-ext:auto-restart-to-modify;
                            description "Apply a configuration group at this level";
                        }

                        leaf-list apply-groups-exclude {
                            type leafref {
                                path "../../../../../groups/group/name";
                            }
                            max-elements 8;
                            ordered-by user;
                            sros-ext:auto-restart-to-modify;
                            description "Exclude a configuration group at this level";
                        }

                        list peer {
                            key "peer-ip-address";
                            max-elements 1023;
                            description "Enter the peer list instance";

                            leaf peer-ip-address {
                                type types-sros:ip-unicast-address;
                                description "Peer IP address of the node SID";
                            }

                            leaf admin-state {
                                type types-sros:admin-state;
                                default "disable";
                                description "Administrative state of the encryption group peer";
                            }

                            leaf-list apply-groups {
                                type leafref {
                                    path "../../../../../../groups/group/name";
                                }
                                max-elements 8;
                                ordered-by user;
                                sros-ext:auto-restart-to-modify;
                                description "Apply a configuration group at this level";
                            }

                            leaf-list apply-groups-exclude {
                                type leafref {
                                    path "../../../../../../groups/group/name";
                                }
                                max-elements 8;
                                ordered-by user;
                                sros-ext:auto-restart-to-modify;
                                description "Exclude a configuration group at this level";
                            }

                        } // list peer

                    } // list encryption-group

                } // container service-encryption

            } // container mpls

            container security-termination-policies {
                status obsolete;
                description "Enter the security-termination-policies context";

                leaf-list apply-groups {
                    status obsolete;
                    type leafref {
                        path "../../../groups/group/name";
                    }
                    max-elements 8;
                    ordered-by user;
                    description "Apply a configuration group at this level";
                }

                leaf-list apply-groups-exclude {
                    status obsolete;
                    type leafref {
                        path "../../../groups/group/name";
                    }
                    max-elements 8;
                    ordered-by user;
                    description "Exclude a configuration group at this level";
                }

                list policy {
                    status obsolete;
                    key "policy-name";
                    max-elements 1023;
                    description "Enter the policy list instance";

                    leaf policy-name {
                        status obsolete;
                        type types-sros:named-item;
                        description "ANYsec security termination policy name";
                    }

                    leaf local-address {
                        status obsolete;
                        type types-sros:ip-unicast-address;
                        sros-ext:auto-restart-to-modify;
                        description "Local address of node SID associated with ANYsec tunnel";
                    }

                    leaf rx-must-be-encrypted {
                        status obsolete;
                        type boolean;
                        default "false";
                        description "Enforce encryption for received packets";
                    }

                    leaf admin-state {
                        status obsolete;
                        type types-sros:admin-state;
                        default "disable";
                        description "Administrative state of the security termination policy";
                    }

                    leaf protocol {
                        status obsolete;
                        type types-security:anysec-protocol;
                        sros-ext:auto-restart-to-modify;
                        description "Protocol used to advertise node SID of incoming tunnel";
                    }

                    leaf igp-instance-id {
                        status obsolete;
                        type types-security:anysec-igp-instance-id;
                        sros-ext:auto-restart-to-modify;
                        description "IGP instance ID";
                    }

                    leaf flex-algo-id {
                        status obsolete;
                        type types-router:flex-algo-id;
                        sros-ext:auto-restart-to-modify;
                        description "Flexible algorithm ID";
                    }

                    leaf-list apply-groups {
                        status obsolete;
                        type leafref {
                            path "../../../../groups/group/name";
                        }
                        max-elements 8;
                        ordered-by user;
                        sros-ext:auto-restart-to-modify;
                        description "Apply a configuration group at this level";
                    }

                    leaf-list apply-groups-exclude {
                        status obsolete;
                        type leafref {
                            path "../../../../groups/group/name";
                        }
                        max-elements 8;
                        ordered-by user;
                        sros-ext:auto-restart-to-modify;
                        description "Exclude a configuration group at this level";
                    }

                } // list policy

            } // container security-termination-policies

            container tunnel-encryption {
                status obsolete;
                description "Enter the tunnel-encryption context";

                leaf-list apply-groups {
                    status obsolete;
                    type leafref {
                        path "../../../groups/group/name";
                    }
                    max-elements 8;
                    ordered-by user;
                    description "Apply a configuration group at this level";
                }

                leaf-list apply-groups-exclude {
                    status obsolete;
                    type leafref {
                        path "../../../groups/group/name";
                    }
                    max-elements 8;
                    ordered-by user;
                    description "Exclude a configuration group at this level";
                }

                list security-termination-policy {
                    status obsolete;
                    key "policy-name";
                    max-elements 1023;
                    description "Enter the security-termination-policy list instance";

                    leaf policy-name {
                        status obsolete;
                        type types-sros:named-item;
                        description "ANYsec security termination policy name";
                    }

                    leaf local-address {
                        status obsolete;
                        type types-sros:ip-unicast-address;
                        sros-ext:auto-restart-to-modify;
                        description "Local address of node SID associated with ANYsec tunnel";
                    }

                    leaf rx-must-be-encrypted {
                        status obsolete;
                        type boolean;
                        default "false";
                        description "Enforce encryption for received packets";
                    }

                    leaf admin-state {
                        status obsolete;
                        type types-sros:admin-state;
                        default "disable";
                        description "Administrative state of the security termination policy";
                    }

                    leaf protocol {
                        status obsolete;
                        type types-security:anysec-protocol;
                        sros-ext:auto-restart-to-modify;
                        description "Protocol used to advertise node SID of incoming tunnel";
                    }

                    leaf igp-instance-id {
                        status obsolete;
                        type types-security:anysec-igp-instance-id;
                        sros-ext:auto-restart-to-modify;
                        description "IGP instance ID";
                    }

                    leaf flex-algo-id {
                        status obsolete;
                        type types-router:flex-algo-id;
                        sros-ext:auto-restart-to-modify;
                        description "Flexible algorithm ID";
                    }

                    leaf-list apply-groups {
                        status obsolete;
                        type leafref {
                            path "../../../../groups/group/name";
                        }
                        max-elements 8;
                        ordered-by user;
                        sros-ext:auto-restart-to-modify;
                        description "Apply a configuration group at this level";
                    }

                    leaf-list apply-groups-exclude {
                        status obsolete;
                        type leafref {
                            path "../../../../groups/group/name";
                        }
                        max-elements 8;
                        ordered-by user;
                        sros-ext:auto-restart-to-modify;
                        description "Exclude a configuration group at this level";
                    }

                } // list security-termination-policy

                list encryption-group {
                    status obsolete;
                    key "group-name";
                    max-elements 1023;
                    description "Enter the encryption-group list instance";

                    leaf group-name {
                        status obsolete;
                        type types-sros:named-item;
                        description "ANYsec encryption group name";
                    }

                    leaf security-termination-policy {
                        status obsolete;
                        type leafref {
                            path "../../../mpls/security-termination-policies/policy/policy-name";
                        }
                        sros-ext:auto-restart-to-modify;
                        description "Security termination policy used by encryption group";
                    }

                    leaf encryption-label {
                        status obsolete;
                        type types-sros:mpls-label-or-zero;
                        sros-ext:auto-restart-to-modify;
                        description "Label identifying packets sent from the node to peers";
                    }

                    leaf ca-name {
                        status obsolete;
                        type leafref {
                            path "../../../../macsec/connectivity-association/ca-name";
                        }
                        sros-ext:auto-restart-to-modify;
                        description "Connectivity association for the encryption group";
                    }

                    leaf admin-state {
                        status obsolete;
                        type types-sros:admin-state;
                        default "disable";
                        description "Administrative state of the encryption group";
                    }

                    leaf allow-entropy-label {
                        status obsolete;
                        type boolean;
                        sros-ext:auto-restart-to-modify;
                        default "false";
                        description "Allow EL and ELI by this encryption group";
                    }

                    leaf-list apply-groups {
                        status obsolete;
                        type leafref {
                            path "../../../../groups/group/name";
                        }
                        max-elements 8;
                        ordered-by user;
                        sros-ext:auto-restart-to-modify;
                        description "Apply a configuration group at this level";
                    }

                    leaf-list apply-groups-exclude {
                        status obsolete;
                        type leafref {
                            path "../../../../groups/group/name";
                        }
                        max-elements 8;
                        ordered-by user;
                        sros-ext:auto-restart-to-modify;
                        description "Exclude a configuration group at this level";
                    }

                    container peer-tunnel-attributes {
                        status obsolete;
                        sros-ext:auto-restart-to-modify;
                        description "Enter the peer-tunnel-attributes context";

                        leaf protocol {
                            status obsolete;
                            type types-security:anysec-protocol;
                            sros-ext:auto-restart-to-modify;
                            description "Protocol used to advertise node SID of incoming tunnel";
                        }

                        leaf igp-instance-id {
                            status obsolete;
                            type types-security:anysec-igp-instance-id;
                            sros-ext:auto-restart-to-modify;
                            description "IGP instance ID";
                        }

                        leaf flex-algo-id {
                            status obsolete;
                            type types-router:flex-algo-id;
                            sros-ext:auto-restart-to-modify;
                            description "Flexible algorithm ID";
                        }

                    } // container peer-tunnel-attributes

                    list peer {
                        status obsolete;
                        key "peer-ip-address";
                        max-elements 1023;
                        description "Enter the peer list instance";

                        leaf peer-ip-address {
                            status obsolete;
                            type types-sros:ip-unicast-address;
                            description "Peer IP address of the node SID";
                        }

                        leaf admin-state {
                            status obsolete;
                            type types-sros:admin-state;
                            default "disable";
                            description "Administrative state of the encryption group peer";
                        }

                        leaf-list apply-groups {
                            status obsolete;
                            type leafref {
                                path "../../../../../groups/group/name";
                            }
                            max-elements 8;
                            ordered-by user;
                            sros-ext:auto-restart-to-modify;
                            description "Apply a configuration group at this level";
                        }

                        leaf-list apply-groups-exclude {
                            status obsolete;
                            type leafref {
                                path "../../../../../groups/group/name";
                            }
                            max-elements 8;
                            ordered-by user;
                            sros-ext:auto-restart-to-modify;
                            description "Exclude a configuration group at this level";
                        }

                    } // list peer

                } // list encryption-group

            } // container tunnel-encryption

            container service-encryption {
                status obsolete;
                description "Enter the service-encryption context";

                leaf-list apply-groups {
                    status obsolete;
                    type leafref {
                        path "../../../groups/group/name";
                    }
                    max-elements 8;
                    ordered-by user;
                    description "Apply a configuration group at this level";
                }

                leaf-list apply-groups-exclude {
                    status obsolete;
                    type leafref {
                        path "../../../groups/group/name";
                    }
                    max-elements 8;
                    ordered-by user;
                    description "Exclude a configuration group at this level";
                }

                list encryption-group {
                    status obsolete;
                    key "group-name";
                    max-elements 1023;
                    description "Enter the encryption-group list instance";

                    leaf group-name {
                        status obsolete;
                        type types-sros:named-item;
                        description "ANYsec encryption group name";
                    }

                    leaf security-termination-policy {
                        status obsolete;
                        type leafref {
                            path "../../../mpls/security-termination-policies/policy/policy-name";
                        }
                        sros-ext:auto-restart-to-modify;
                        description "Security termination policy used by encryption group";
                    }

                    leaf encryption-label {
                        status obsolete;
                        type types-sros:mpls-label-or-zero;
                        sros-ext:auto-restart-to-modify;
                        description "Label identifying packets sent from the node to peers";
                    }

                    leaf ca-name {
                        status obsolete;
                        type leafref {
                            path "../../../../macsec/connectivity-association/ca-name";
                        }
                        sros-ext:auto-restart-to-modify;
                        description "Connectivity association for the encryption group";
                    }

                    leaf admin-state {
                        status obsolete;
                        type types-sros:admin-state;
                        default "disable";
                        description "Administrative state of the encryption group";
                    }

                    leaf-list apply-groups {
                        status obsolete;
                        type leafref {
                            path "../../../../groups/group/name";
                        }
                        max-elements 8;
                        ordered-by user;
                        sros-ext:auto-restart-to-modify;
                        description "Apply a configuration group at this level";
                    }

                    leaf-list apply-groups-exclude {
                        status obsolete;
                        type leafref {
                            path "../../../../groups/group/name";
                        }
                        max-elements 8;
                        ordered-by user;
                        sros-ext:auto-restart-to-modify;
                        description "Exclude a configuration group at this level";
                    }

                    list peer {
                        status obsolete;
                        key "peer-ip-address";
                        max-elements 1023;
                        description "Enter the peer list instance";

                        leaf peer-ip-address {
                            status obsolete;
                            type types-sros:ip-unicast-address;
                            description "Peer IP address of the node SID";
                        }

                        leaf admin-state {
                            status obsolete;
                            type types-sros:admin-state;
                            default "disable";
                            description "Administrative state of the encryption group peer";
                        }

                        leaf-list apply-groups {
                            status obsolete;
                            type leafref {
                                path "../../../../../groups/group/name";
                            }
                            max-elements 8;
                            ordered-by user;
                            sros-ext:auto-restart-to-modify;
                            description "Apply a configuration group at this level";
                        }

                        leaf-list apply-groups-exclude {
                            status obsolete;
                            type leafref {
                                path "../../../../../groups/group/name";
                            }
                            max-elements 8;
                            ordered-by user;
                            sros-ext:auto-restart-to-modify;
                            description "Exclude a configuration group at this level";
                        }

                    } // list peer

                } // list encryption-group

            } // container service-encryption

        } // container anysec

    } // grouping conf-anysec

}
