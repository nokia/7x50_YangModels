submodule nokia-conf-router-firewall {

    yang-version "1.1";

    belongs-to nokia-conf { prefix "conf"; }

    import nokia-sros-yang-extensions     { prefix "sros-ext"; }
    import nokia-types-sros               { prefix "types-sros"; }

    include nokia-conf-groups;
    include nokia-conf-isa;

    sros-ext:sros-major-release "rel26";
    organization "Nokia";
    contact
        "Nokia SR OS Support
         Web: <http://www.nokia.com>";
    description
        "Nokia YANG Data model to configure Configure firewall on SR OS based routers.

         Copyright 2016 Nokia. All rights reserved. Reproduction of this document
         is authorized on the condition that the foregoing copyright notice is included.

         This nokia-conf-router-firewall YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    grouping conf-router-firewall {
        container firewall {
            when "../router-name = 'Base'" {
                description "router-name must be 'Base'";
            }
            description "Enter the firewall context";

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            list domain {
                key "name";
                max-elements 1024;
                description "Enter the domain list instance";

                leaf name {
                    type types-sros:named-item;
                    description "Firewall domain name";
                }

                leaf admin-state {
                    type types-sros:admin-state;
                    default "disable";
                    description "Administrative state of the firewall domain";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                choice isa {
                    mandatory true;
                    case nat {

                        leaf nat-group {
                            type leafref {
                                path "../../../../isa/nat-group/id";
                            }
                            sros-ext:immutable;
                            description "NAT group for this domain";
                        }

                    }
                    case wlan-gw {

                        leaf wlan-gw-group {
                            type leafref {
                                path "../../../../isa/wlan-gw-group/id";
                            }
                            sros-ext:immutable;
                            description "WLAN GW group used for NAT";
                        }

                    }
                }
                container dhcpv6-server {
                    description "Enter the dhcpv6-server context";

                    leaf router-instance {
                        type string;
                        sros-ext:auto-restart-to-modify;
                        description "Router name";
                    }

                    leaf name {
                        type types-sros:named-item;
                        sros-ext:auto-restart-to-modify;
                        description "DHCPv6 server name";
                    }

                } // container dhcpv6-server

                list prefix {
                    key "ip-prefix";
                    max-elements 4096;
                    description "Enter the prefix list instance";

                    leaf ip-prefix {
                        type types-sros:ipv6-unicast-prefix;
                        description "IP prefix and prefix length for the domain firewall";
                    }

                    leaf description {
                        type types-sros:description;
                        description "Text description";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list prefix

            } // list domain

        } // container firewall

    } // grouping conf-router-firewall

}
