submodule nokia-conf-cflowd {

    yang-version "1.1";

    belongs-to nokia-conf { prefix "conf"; }

    import nokia-sros-yang-extensions     { prefix "sros-ext"; }
    import nokia-types-cflowd             { prefix "types-cflowd"; }
    import nokia-types-qos                { prefix "types-qos"; }
    import nokia-types-sros               { prefix "types-sros"; }

    include nokia-conf-groups;
    include nokia-conf-router;
    include nokia-conf-service;
    include nokia-conf-svc-ies;
    include nokia-conf-svc-ies-sub-if;
    include nokia-conf-svc-vprn;
    include nokia-conf-svc-vprn-sub-if;
    include nokia-conf-system;
    include nokia-conf-system-security;
    include nokia-conf-system-security-tls;

    sros-ext:sros-major-release "rel26";
    organization "Nokia";
    contact
        "Nokia SR OS Support
         Web: <http://www.nokia.com>";
    description
        "Nokia YANG Data model to configure Cflowd configuration on SR OS based routers.

         Copyright 2016 Nokia. All rights reserved. Reproduction of this document
         is authorized on the condition that the foregoing copyright notice is included.

         This nokia-conf-cflowd YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-04-22";

    grouping conf-cflowd {
        container cflowd {
            presence "Enable the cflowd context";
            description "Enable the cflowd context";

            leaf active-timeout {
                status obsolete;
                type uint32 {
                    range "1..600";
                }
                units "minutes";
                default "30";
                description "Maximum time before an active flow is exported";
            }

            leaf admin-state {
                type types-sros:admin-state;
                default "enable";
                description "Administrative state of cflowd";
            }

            leaf analyze-gre-payload {
                type boolean;
                default "false";
                description "Perform cflowd analysis on the inner IP packet";
            }

            leaf analyze-l2tp-traffic {
                type boolean;
                default "false";
                description "Analyze the inner IP header of an L2TP packet";
            }

            leaf analyze-srv6-payload {
                type boolean;
                default "false";
                description "Instruct flow data to be based on inner header";
            }

            leaf analyze-v4overv6-traffic {
                type boolean;
                default "false";
                description "Analyze the inner IPv4 packet within an IPv6 packet";
            }

            leaf cache-size {
                type uint32 {
                    range "1000..4000000";
                }
                units "flows";
                description "Maximum number of active flows in the flow cache table";
            }

            leaf enhanced-distribution {
                type boolean;
                default "false";
                description "Include ingress port ID in hashing algorithm for cflowd";
            }

            leaf export-mode {
                type enumeration {
                    enum automatic                      { value 1; }
                    enum manual                         { value 2; }
                }
                default "automatic";
                description "Export mode for flow data";
            }

            leaf inactive-timeout {
                status obsolete;
                type uint32 {
                    range "10..600";
                }
                units "seconds";
                default "15";
                description "Time before the flow is considered inactive";
            }

            leaf inband-collector-export-only {
                type boolean;
                default "false";
                description "Export the traffic to all collectors only via in-band interfaces";
            }

            leaf overflow {
                type uint32 {
                    range "1..50";
                }
                units "percent";
                default "1";
                description "Percentage of entries to remove from Cflowd cache when the maximum number of entries is exceeded";
            }

            leaf rate {
                status obsolete;
                type uint32 {
                    range "1..10000";
                }
                units "packets";
                default "1000";
                description "Rate at which traffic is sampled and sent for Cflowd analysis";
            }

            leaf template-retransmit {
                type uint32 {
                    range "10..600";
                }
                units "seconds";
                default "600";
                description "Time to resend template information";
            }

            leaf use-vrtr-if-index {
                type boolean;
                default "false";
                description "Export flow data using virtual router interface indexes";
            }

            leaf active-flow-timeout {
                type uint32 {
                    range "30..36000";
                }
                units "seconds";
                default "1800";
                description "Maximum time before an active flow is exported";
            }

            leaf inactive-flow-timeout {
                type uint32 {
                    range "10..600";
                }
                units "seconds";
                default "15";
                description "Time without matching packet before flow is inactive";
            }

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list sample-profile {
                key "profile-id";
                max-elements 5;
                description "Enter the sample-profile list instance";

                leaf profile-id {
                    type uint32 {
                        range "1..5";
                    }
                    description "Sample profile ID";
                }

                leaf sample-rate {
                    type uint32 {
                        range "1..60000";
                    }
                    default "1000";
                    description "Cflowd sampling rate for sample profile ID";
                }

                leaf metering-process {
                    type types-cflowd:metering-process;
                    default "standard";
                    description "Metering process for samples taken";
                }

                leaf slice-selection {
                    type types-cflowd:slice-selection;
                    default "standard";
                    description "Cflowd slice selection for sample profile ID";
                }

                leaf export-ie315 {
                    type boolean;
                    default "false";
                    description "Enable reporting on sample packets using IE315 format";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list sample-profile

            list collector {
                key "ip-address port";
                max-elements 8;
                description "Enter the collector list instance";

                leaf ip-address {
                    type types-sros:ip-unicast-address;
                    description "IP address of the remote cflowd collector host";
                }

                leaf port {
                    type types-qos:tcp-udp-match-port {
                        range "1..65535";
                    }
                    description "UDP port number of the remote cflowd collector host";
                }

                leaf admin-state {
                    type types-sros:admin-state;
                    default "enable";
                    description "Administrative state of the cflowd collector";
                }

                leaf autonomous-system-type {
                    type enumeration {
                        enum origin                         { value 1; }
                        enum peer                           { value 2; }
                    }
                    default "origin";
                    description "Basis of the AS information included in flow data";
                }

                leaf description {
                    type types-sros:description;
                    description "Text description";
                }

                leaf router-instance {
                    type string;
                    default "management";
                    description "Router or service name";
                }

                leaf template-set {
                    type enumeration {
                        enum not-applicable                 { value 0; }
                        enum basic                          { value 1; }
                        enum mpls-ip                        { value 2; }
                        enum l2-ip                          { value 3; }
                        enum mpls-transport                 { value 4; }
                        enum compact                        { value 5; }
                        enum fastpath                       { value 6; }
                    }
                    description "Templates sent to the collector";
                }

                leaf version {
                    type types-cflowd:collector-version;
                    sros-ext:immutable;
                    mandatory true;
                    description "Flow data collector version";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container aggregation {
                    description "Enter the aggregation context";

                    leaf as-matrix {
                        type boolean;
                        default "false";
                        description "Base aggregation data based on AS information";
                    }

                    leaf protocol-port {
                        type boolean;
                        default "false";
                        description "Aggregate flows based on the IP protocol and ports";
                    }

                    leaf source-prefix {
                        type boolean;
                        default "false";
                        description "Aggregate flows based on the source prefix information";
                    }

                    leaf destination-prefix {
                        type boolean;
                        default "false";
                        description "Aggregate data based on destination prefix information";
                    }

                    leaf source-destination-prefix {
                        type boolean;
                        default "false";
                        description "Aggregate data based on prefix information";
                    }

                    leaf raw {
                        type boolean;
                        default "false";
                        description "Export flow data without aggregation";
                    }

                } // container aggregation

                container export-filter {
                    when "../version = 9 or ../version = 10" {
                        description "export-filter can only be configured for collector versions 9 or 10";
                    }
                    description "Enter the export-filter context";

                    container family {
                        description "Enter the family context";

                        leaf ipv4 {
                            type boolean;
                            default "false";
                            description "Prevent IPv4 flow data from going to collector";
                        }

                        leaf ipv6 {
                            type boolean;
                            default "false";
                            description "Prevent IPv6 flow data from going to collector";
                        }

                        leaf mcast-ipv4 {
                            type boolean;
                            default "false";
                            description "Prevent multicast IPv4 data from going to the collector";
                        }

                        leaf mcast-ipv6 {
                            type boolean;
                            default "false";
                            description "Prevent multicast IPv6 data from going to collector";
                        }

                        leaf l2-ip {
                            type boolean;
                            default "false";
                            description "Prevent Layer 2 IP flow data from going to collector";
                        }

                        leaf mpls {
                            type boolean;
                            default "false";
                            description "Prevent MPLS flow data from going to collector";
                        }

                        leaf non-ip {
                            type boolean;
                            default "false";
                            description "Prevent non-IP flow data from going to collector";
                        }

                    } // container family

                    list router {
                        key "router-instance";
                        description "Add a list entry for router";

                        leaf router-instance {
                            type string;
                            description "Router instance name";
                        }

                    } // list router

                    container interface-list {
                        description "Enter the interface-list context";

                        list router {
                            key "router-name interface-name";
                            description "Enter the router list instance";

                            leaf router-name {
                                type leafref {
                                    path "../../../../../../router/router-name";
                                }
                                description "Administrative router name";
                            }

                            leaf interface-name {
                                type leafref {
                                    path "../../../../../../router[router-name=current()/../router-name]/interface/interface-name";
                                }
                                description "Name for the router to the service interface or SAP";
                            }

                            leaf direction {
                                type enumeration {
                                    enum ingress                        { value 1; }
                                    enum egress                         { value 2; }
                                    enum both                           { value 3; }
                                }
                                default "both";
                                description "Flow match condition direction for the export filter";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                        } // list router

                        container service {
                            description "Enter the service context";

                            list ies-interface {
                                key "service-name interface-name";
                                description "Enter the ies-interface list instance";

                                leaf service-name {
                                    type leafref {
                                        path "../../../../../../../service/ies/service-name";
                                    }
                                    description "Administrative service name";
                                }

                                leaf interface-name {
                                    type leafref {
                                        path "../../../../../../../service/ies[service-name=current()/../service-name]/interface/interface-name";
                                    }
                                    description "IP interface name";
                                }

                                leaf direction {
                                    type enumeration {
                                        enum ingress                        { value 1; }
                                        enum egress                         { value 2; }
                                        enum both                           { value 3; }
                                    }
                                    default "both";
                                    description "Flow match condition direction for the export filter";
                                }

                                leaf-list apply-groups {
                                    type leafref {
                                        path "../../../../../../../groups/group/name";
                                    }
                                    max-elements 8;
                                    ordered-by user;
                                    description "Apply a configuration group at this level";
                                }

                                leaf-list apply-groups-exclude {
                                    type leafref {
                                        path "../../../../../../../groups/group/name";
                                    }
                                    max-elements 8;
                                    ordered-by user;
                                    description "Exclude a configuration group at this level";
                                }

                            } // list ies-interface

                            list ies-group-interface {
                                key "service-name subscriber-interface-name group-interface-name";
                                description "Enter the ies-group-interface list instance";

                                leaf service-name {
                                    type leafref {
                                        path "../../../../../../../service/ies/service-name";
                                    }
                                    description "Administrative service name";
                                }

                                leaf subscriber-interface-name {
                                    type leafref {
                                        path "../../../../../../../service/ies[service-name=current()/../service-name]/subscriber-interface/interface-name";
                                    }
                                    description "Subscriber interface name";
                                }

                                leaf group-interface-name {
                                    type leafref {
                                        path "../../../../../../../service/ies[service-name=current()/../service-name]/subscriber-interface[interface-name=current()/../subscriber-interface-name]/group-interface/group-interface-name";
                                    }
                                    description "Group interface name";
                                }

                                leaf direction {
                                    type enumeration {
                                        enum ingress                        { value 1; }
                                        enum egress                         { value 2; }
                                        enum both                           { value 3; }
                                    }
                                    default "both";
                                    description "Flow match condition direction for the export filter";
                                }

                                leaf-list apply-groups {
                                    type leafref {
                                        path "../../../../../../../groups/group/name";
                                    }
                                    max-elements 8;
                                    ordered-by user;
                                    description "Apply a configuration group at this level";
                                }

                                leaf-list apply-groups-exclude {
                                    type leafref {
                                        path "../../../../../../../groups/group/name";
                                    }
                                    max-elements 8;
                                    ordered-by user;
                                    description "Exclude a configuration group at this level";
                                }

                            } // list ies-group-interface

                            list vprn-interface {
                                key "service-name interface-name";
                                description "Enter the vprn-interface list instance";

                                leaf service-name {
                                    type leafref {
                                        path "../../../../../../../service/vprn/service-name";
                                    }
                                    description "Administrative service name";
                                }

                                leaf interface-name {
                                    type leafref {
                                        path "../../../../../../../service/vprn[service-name=current()/../service-name]/interface/interface-name";
                                    }
                                    description "IP interface name";
                                }

                                leaf direction {
                                    type enumeration {
                                        enum ingress                        { value 1; }
                                        enum egress                         { value 2; }
                                        enum both                           { value 3; }
                                    }
                                    default "both";
                                    description "Flow match condition direction for the export filter";
                                }

                                leaf-list apply-groups {
                                    type leafref {
                                        path "../../../../../../../groups/group/name";
                                    }
                                    max-elements 8;
                                    ordered-by user;
                                    description "Apply a configuration group at this level";
                                }

                                leaf-list apply-groups-exclude {
                                    type leafref {
                                        path "../../../../../../../groups/group/name";
                                    }
                                    max-elements 8;
                                    ordered-by user;
                                    description "Exclude a configuration group at this level";
                                }

                            } // list vprn-interface

                            list vprn-network-interface {
                                key "service-name network-interface-name";
                                description "Enter the vprn-network-interface list instance";

                                leaf service-name {
                                    type leafref {
                                        path "../../../../../../../service/vprn/service-name";
                                    }
                                    description "Administrative service name";
                                }

                                leaf network-interface-name {
                                    type leafref {
                                        path "../../../../../../../service/vprn[service-name=current()/../service-name]/network-interface/interface-name";
                                    }
                                    description "Network interface name";
                                }

                                leaf direction {
                                    type enumeration {
                                        enum ingress                        { value 1; }
                                        enum egress                         { value 2; }
                                        enum both                           { value 3; }
                                    }
                                    default "both";
                                    description "Flow match condition direction for the export filter";
                                }

                                leaf-list apply-groups {
                                    type leafref {
                                        path "../../../../../../../groups/group/name";
                                    }
                                    max-elements 8;
                                    ordered-by user;
                                    description "Apply a configuration group at this level";
                                }

                                leaf-list apply-groups-exclude {
                                    type leafref {
                                        path "../../../../../../../groups/group/name";
                                    }
                                    max-elements 8;
                                    ordered-by user;
                                    description "Exclude a configuration group at this level";
                                }

                            } // list vprn-network-interface

                            list vprn-group-interface {
                                key "service-name subscriber-interface-name group-interface-name";
                                description "Enter the vprn-group-interface list instance";

                                leaf service-name {
                                    type leafref {
                                        path "../../../../../../../service/vprn/service-name";
                                    }
                                    description "Administrative service name";
                                }

                                leaf subscriber-interface-name {
                                    type leafref {
                                        path "../../../../../../../service/vprn[service-name=current()/../service-name]/subscriber-interface/interface-name";
                                    }
                                    description "Subscriber interface name";
                                }

                                leaf group-interface-name {
                                    type leafref {
                                        path "../../../../../../../service/vprn[service-name=current()/../service-name]/subscriber-interface[interface-name=current()/../subscriber-interface-name]/group-interface/group-interface-name";
                                    }
                                    description "Group interface name";
                                }

                                leaf direction {
                                    type enumeration {
                                        enum ingress                        { value 1; }
                                        enum egress                         { value 2; }
                                        enum both                           { value 3; }
                                    }
                                    default "both";
                                    description "Flow match condition direction for the export filter";
                                }

                                leaf-list apply-groups {
                                    type leafref {
                                        path "../../../../../../../groups/group/name";
                                    }
                                    max-elements 8;
                                    ordered-by user;
                                    description "Apply a configuration group at this level";
                                }

                                leaf-list apply-groups-exclude {
                                    type leafref {
                                        path "../../../../../../../groups/group/name";
                                    }
                                    max-elements 8;
                                    ordered-by user;
                                    description "Exclude a configuration group at this level";
                                }

                            } // list vprn-group-interface

                        } // container service

                    } // container interface-list

                } // container export-filter

            } // list collector

        } // container cflowd

    } // grouping conf-cflowd

}
