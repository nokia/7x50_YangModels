submodule nokia-conf-port-tdm {

    yang-version "1.1";

    belongs-to nokia-conf { prefix "conf"; }

    import ietf-yang-types                { prefix "yang"; }
    import nokia-sros-yang-extensions     { prefix "sros-ext"; }
    import nokia-types-port               { prefix "types-port"; }
    import nokia-types-qos                { prefix "types-qos"; }
    import nokia-types-sros               { prefix "types-sros"; }

    include nokia-conf-groups;
    include nokia-conf-log;
    include nokia-conf-qos;

    sros-ext:sros-major-release "rel19";

    organization "Nokia";

    contact
        "Nokia SR OS Support
         Web: <http://www.nokia.com>";

    description
        "Nokia YANG Data model to configure TDM ports on SR OS based routers.

         Copyright 2016 Nokia. All rights reserved. Reproduction of this document
         is authorized on the condition that the foregoing copyright notice is included.

         This nokia-conf-port-tdm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-06-27";

    grouping conf-port-tdm {
        container tdm {
            description "Enter the tdm context";

            leaf buildout {
                type enumeration {
                    enum "short"                        { value 1; }
                    enum "long"                         { value 2; }
                }
                default "short";
                description "Configure the line buildout for a physical DS1/DS3 port.";
            }

            leaf lbo {
                when "../buildout = 'long'";
                type decimal64 {
                    range "-22.5 | -15 | -7.5 | 0";
                    fraction-digits 1;
                }
                units "decibels";
                default "0";
                description "Configure the transmitter attenuation for a long buildout on a physical DS1 port.";
            }

            leaf length {
                when "../buildout = 'short'";
                type uint32 {
                    range "133 | 266 | 399 | 533 | 655";
                }
                default "133";
                description "Configure the cable length for a short buildout on a physical DS1 port.";
            }

            container hold-time {
                description "Enter the hold-time context";

                leaf up {
                    type uint32 {
                        range "1..100";
                    }
                    description "Configure the hold timer for link up event dampening on the physical DS3 port.";
                }

                leaf down {
                    type uint32 {
                        range "0..100";
                    }
                    default "5";
                    description "Configure the hold timer for link down event dampening on the physical DS3 port.";
                }

            } // container hold-time

        } // container tdm

    } // grouping conf-port-tdm

}
