submodule nokia-conf-submgt-gtp {

    yang-version "1.1";

    belongs-to nokia-conf { prefix "conf"; }

    import nokia-sros-yang-extensions     { prefix "sros-ext"; }
    import nokia-types-qos                { prefix "types-qos"; }
    import nokia-types-services           { prefix "types-services"; }
    import nokia-types-sros               { prefix "types-sros"; }

    include nokia-conf-groups;
    include nokia-conf-python;
    include nokia-conf-submgt-local-user-db;
    include nokia-conf-subscriber-mgmt;

    sros-ext:sros-major-release "rel19";

    organization "Nokia";

    contact
        "Nokia SR OS Support
         Web: <http://www.nokia.com>";

    description
        "Nokia YANG Data model to configure subscriber management gtp on SR OS based routers.

         Copyright 2016 Nokia. All rights reserved. Reproduction of this document
         is authorized on the condition that the foregoing copyright notice is included.

         This nokia-conf-submgt-gtp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-04-24";

    grouping conf-submgt-gtp {
        container gtp {
            description "Enter the gtp context";

            leaf max-held-uplink-sessions {
                type uint32 {
                    range "0..500000";
                }
                default "2000";
                description "Maximum GTP sessions to be held while there is no corresponding ESM state";
            }

            container serving-network {
                presence "Serving network Identifier";
                description "Enter the serving-network context";

                leaf mcc {
                    type string {
                        length "3";
                        pattern "\\d{3}" {
                            error-message "mcc must be digits";
                        }
                    }
                    mandatory true;
                    description "Mobile Country Code (MCC) portion of serving network";
                }

                leaf mnc {
                    type string {
                        length "2..3";
                        pattern "\\d{2,3}" {
                            error-message "mnc must be digits";
                        }
                    }
                    mandatory true;
                    description "Mobile Network Code (MNC) portion of serving network";
                }

            } // container serving-network

            list apn-policy {
                key "name";
                max-elements 128;
                description "Enter the apn-policy list instance";

                leaf name {
                    type types-sros:named-item;
                    description "GTP APN policy name";
                }

                list apn {
                    key "apn-name";
                    max-elements 1024;
                    description "Enter the apn list instance";

                    leaf apn-name {
                        type string {
                            length "1..80";
                            pattern "([a-zA-Z0-9]+-+)*([a-zA-Z0-9]+\\.([a-zA-Z0-9]+-+)*)*[a-zA-Z0-9]+" {
                                error-message "wrong format of apn name";
                            }
                        }
                        description "GTP APN name";
                    }

                    leaf skip-gtp-ipv4-allocation {
                        type boolean;
                        default "false";
                        description "defer IPv4 address allocation to DHCP";
                    }

                    choice auth-policy {
                        case diameter {

                            leaf diameter-nasreq-policy {
                                type leafref {
                                    path "../../../../diameter-nasreq-policy/name";
                                }
                                description "NASREQ authentication policy name";
                            }

                        }
                        case radius {

                            leaf radius-auth-policy {
                                type leafref {
                                    path "../../../../radius-authentication-policy/name";
                                }
                                description "RADIUS authentication policy name";
                            }

                        }
                        case user-db {

                            leaf user-db {
                                type leafref {
                                    path "../../../../local-user-db/name";
                                }
                                description "Local user database name";
                            }

                        }
                    }
                    container ambr-qos-mapping {
                        description "Enter the ambr-qos-mapping context";

                        container downlink {
                            presence "Downlink APN-AMBR QoS override";
                            description "Enter the downlink context";

                            choice downlink {
                                mandatory true;
                                case aggregate-rate {

                                    leaf aggregate-rate {
                                        type empty;
                                        description "Map the downlink APN-AMBR rate to an Aggregate Rate override";
                                    }

                                }
                                case arbiter {

                                    leaf arbiter {
                                        type types-sros:named-item;
                                        description "Map the downlink APN-AMBR rate to an override for the specified arbiter";
                                    }

                                }
                                case policer {

                                    leaf policer {
                                        type types-qos:sap-egress-policer-id;
                                        description "Map the downlink APN-AMBR rate to a policer PIR override";
                                    }

                                }
                                case queue {

                                    leaf queue {
                                        type types-qos:egress-queue-id;
                                        description "Map the downlink APN-AMBR rate to a queue PIR override";
                                    }

                                }
                                case scheduler {

                                    leaf scheduler {
                                        type types-sros:named-item;
                                        description "Map the downlink APN-AMBR rate to a scheduler rate override";
                                    }

                                }
                            }
                        } // container downlink

                        container uplink {
                            presence "Uplink APN-AMBR QoS override";
                            description "Enter the uplink context";

                            choice uplink {
                                mandatory true;
                                case arbiter {

                                    leaf arbiter {
                                        type types-sros:named-item;
                                        description "Map the uplink APN-AMBR rate to an override for the specified arbiter";
                                    }

                                }
                                case policer {

                                    leaf policer {
                                        type types-qos:ingress-policer-id;
                                        description "Map the uplink APN-AMBR rate to a policer PIR override";
                                    }

                                }
                                case queue {

                                    leaf queue {
                                        type types-qos:ingress-queue-id;
                                        description "Map the uplink APN-AMBR rate to a queue PIR override";
                                    }

                                }
                                case scheduler {

                                    leaf scheduler {
                                        type types-sros:named-item;
                                        description "Map the uplink APN-AMBR rate to a scheduler rate override";
                                    }

                                }
                            }
                        } // container uplink

                    } // container ambr-qos-mapping

                    container defaults {
                        description "Enter the defaults context";

                        container group-interface {
                            presence "default group-interface.";
                            description "Enter the group-interface context";

                            leaf svc-name {
                                type types-services:service-name;
                                mandatory true;
                                description "Group interface service name";
                            }

                            leaf name {
                                type types-sros:interface-name;
                                mandatory true;
                                description "Group interface name";
                            }

                        } // container group-interface

                    } // container defaults

                } // list apn

            } // list apn-policy

            list peer-profile {
                key "name";
                description "Enter the peer-profile list instance";

                leaf name {
                    type types-sros:named-item;
                    description "GTP peer profile name";
                }

                leaf description {
                    type types-sros:description;
                    description "Text description";
                }

                leaf interface-type {
                    type enumeration {
                        enum "gn"                           { value 1; }
                        enum "s2a"                          { value 2; }
                        enum "s2b"                          { value 3; }
                        enum "s11"                          { value 4; }
                    }
                    description "3GPP interface type for connections toward this peer";
                }

                leaf ip-ttl {
                    type uint8 {
                        range "1..255";
                    }
                    default "255";
                    description "IP TTL value for GTP control messages.";
                }

                leaf python-policy {
                    type leafref {
                        path "../../../../python/python-policy/name";
                    }
                    description "Python policy used to process GTP messages.";
                }

                container keep-alive {
                    description "Enter the keep-alive context";

                    leaf admin-state {
                        type types-sros:admin-state;
                        default "enable";
                        description "Administrative state of GTP-C echo request messages";
                    }

                    leaf interval {
                        when "../admin-state = 'enable'";
                        type types-sros:time-duration {
                            range "60..180";
                        }
                        units "seconds";
                        default "60";
                        description "Frequency for sending keepalives";
                    }

                    leaf retry-count {
                        when "../admin-state = 'enable'";
                        type uint32 {
                            range "1..15";
                        }
                        default "4";
                        description "Maximum number of unanswered echo retries after which keepalive failure is detected";
                    }

                    leaf timeout {
                        when "../admin-state = 'enable'";
                        type uint32 {
                            range "1..20";
                        }
                        units "seconds";
                        default "5";
                        description "Timeout after which an echo request is considered unanswered";
                    }

                } // container keep-alive

                container message-retransmit {
                    description "Enter the message-retransmit context";

                    leaf timeout {
                        type uint32 {
                            range "1..30";
                        }
                        units "seconds";
                        default "5";
                        description "Timeout after which a message is considered unanswered";
                    }

                    leaf retry-count {
                        type uint32 {
                            range "1..8";
                        }
                        default "3";
                        description "Maximum number of unanswered retries after which the message is considered failed";
                    }

                } // container message-retransmit

                container s11 {
                    when "../interface-type = 's11'";
                    description "Enter the s11 context";

                    leaf ipv4-mtu {
                        type uint32 {
                            range "512..9000";
                        }
                        default "1400";
                        description "IPv4 MTU signaled in the Protocol Configuration Options (PCO)";
                    }

                    leaf end-marker-count {
                        type uint32 {
                            range "0..5";
                        }
                        default "1";
                        description "The number of GTP-U end-marker packets sent after mobility.";
                    }

                    leaf change-reporting-action {
                        type union {
                            type uint32 {
                                range "0..255";
                            }
                            type enumeration {
                                enum "cgi-sai"                      { value 1; }
                                enum "rai"                          { value 2; }
                                enum "tai"                          { value 3; }
                                enum "ecgi"                         { value 4; }
                                enum "cgi-sai-rai"                  { value 5; }
                                enum "tai-ecgi"                     { value 6; }
                            }
                        }
                        description "The value of the Change Reporting Action Information Element sent to the peer.";
                    }

                    container qos {
                        description "Enter the qos context";

                        leaf arp {
                            type uint32 {
                                range "1..15";
                            }
                            default "1";
                            description "Allocation or retention priority";
                        }

                        leaf qci {
                            type uint32 {
                                range "1..9";
                            }
                            default "8";
                            description "QoS Class Identifier (QCI) value that is used in GTP messages";
                        }

                        container ambr {
                            description "Enter the ambr context";

                            leaf down-link {
                                type int32 {
                                    range "0..10000000";
                                }
                                units "kilobps";
                                default "20000";
                                description "Downlink Aggregated Maximum Bit Rate (AMBR)";
                            }

                            leaf up-link {
                                type int32 {
                                    range "0..10000000";
                                }
                                units "kilobps";
                                default "10000";
                                description "Uplink Aggregated Maximum Bit Rate (AMBR)";
                            }

                        } // container ambr

                        container down-link {
                            description "Enter the down-link context";

                            leaf gbr {
                                type uint32 {
                                    range "0..100000";
                                }
                                units "kilobps";
                                default "0";
                                description "Guaranteed Bit Rate (GBR)";
                            }

                            leaf mbr {
                                type uint32 {
                                    range "0..100000";
                                }
                                units "kilobps";
                                default "0";
                                description "Maximum Bit Rate (MBR)";
                            }

                        } // container down-link

                        container up-link {
                            description "Enter the up-link context";

                            leaf gbr {
                                type uint32 {
                                    range "0..100000";
                                }
                                units "kilobps";
                                default "0";
                                description "Guaranteed Bit Rate (GBR)";
                            }

                            leaf mbr {
                                type uint32 {
                                    range "0..100000";
                                }
                                units "kilobps";
                                default "0";
                                description "Maximum Bit Rate (MBR)";
                            }

                        } // container up-link

                    } // container qos

                } // container s11

                container uplink {
                    when "../interface-type = 'gn' or ../interface-type = 's2a' or ../interface-type = 's2b'";
                    description "Enter the uplink context";

                    leaf protocol-configuration-options {
                        type enumeration {
                            enum "pco"                          { value 1; }
                            enum "apco"                         { value 2; }
                        }
                        default "pco";
                        description "Information element to use for the protocol configuration options";
                    }

                    leaf rat-type {
                        type union {
                            type uint32 {
                                range "0..255";
                            }
                            type enumeration {
                                enum "utran"                        { value 1; }
                                enum "geran"                        { value 2; }
                                enum "wlan"                         { value 3; }
                                enum "gan"                          { value 4; }
                                enum "hspa"                         { value 5; }
                                enum "eutran"                       { value 6; }
                                enum "virtual"                      { value 7; }
                            }
                        }
                        default "wlan";
                        description "The default Radio Access Technology type signaled during GTP set-up.";
                    }

                    leaf report-wlan-location {
                        type boolean;
                        default "false";
                        description "Report the wlan location of the UE during session set-up.";
                    }

                    leaf session-hold-time {
                        type union {
                            type types-sros:time-duration {
                                range "0..3600";
                            }
                            type enumeration {
                                enum "remaining-lease-time"         { value -1; }
                            }
                        }
                        default "30";
                        description "Time to hold a GTP session after its UE is disconnected";
                    }

                    container charging-characteristics {
                        description "Enter the charging-characteristics context";

                        container home {
                            description "Enter the home context";

                            leaf bit0 {
                                type boolean;
                                default "false";
                                description "Set bit 0 in charging characteristics information element (IE) for home UE";
                            }

                            leaf bit1 {
                                type boolean;
                                default "false";
                                description "Set bit 1 in charging characteristics information element (IE) for home UE";
                            }

                            leaf bit2 {
                                type boolean;
                                default "false";
                                description "Set bit 2 in charging characteristics information element (IE) for home UE";
                            }

                            leaf bit3 {
                                type boolean;
                                default "false";
                                description "Set bit 3 in charging characteristics information element (IE) for home UE";
                            }

                            leaf bit4 {
                                type boolean;
                                default "false";
                                description "Set bit 4 in charging characteristics information element (IE) for home UE";
                            }

                            leaf bit5 {
                                type boolean;
                                default "false";
                                description "Set bit 5 in charging characteristics information element (IE) for home UE";
                            }

                            leaf bit6 {
                                type boolean;
                                default "false";
                                description "Set bit 6 in charging characteristics information element (IE) for home UE";
                            }

                            leaf bit7 {
                                type boolean;
                                default "false";
                                description "Set bit 7 in charging characteristics information element (IE) for home UE";
                            }

                            leaf bit8 {
                                type boolean;
                                default "false";
                                description "Set bit 8 in charging characteristics information element (IE) for home UE";
                            }

                            leaf bit9 {
                                type boolean;
                                default "false";
                                description "Set bit 9 in charging characteristics information element (IE) for home UE";
                            }

                            leaf bit10 {
                                type boolean;
                                default "false";
                                description "Set bit 10 in charging characteristics information element (IE) for home UE";
                            }

                            leaf bit11 {
                                type boolean;
                                default "false";
                                description "Set bit 11 in charging characteristics information element (IE) for home UE";
                            }

                            leaf bit12 {
                                type boolean;
                                default "false";
                                description "Set bit 12 in charging characteristics information element (IE) for home UE";
                            }

                            leaf bit13 {
                                type boolean;
                                default "false";
                                description "Set bit 13 in charging characteristics information element (IE) for home UE";
                            }

                            leaf bit14 {
                                type boolean;
                                default "false";
                                description "Set bit 14 in charging characteristics information element (IE) for home UE";
                            }

                            leaf bit15 {
                                type boolean;
                                default "false";
                                description "Set bit 15 in charging characteristics information element (IE) for home UE";
                            }

                        } // container home

                        container roaming {
                            description "Enter the roaming context";

                            leaf bit0 {
                                type boolean;
                                default "false";
                                description "Set bit 0 in charging characteristics information element (IE) for home UE";
                            }

                            leaf bit1 {
                                type boolean;
                                default "false";
                                description "Set bit 1 in charging characteristics information element (IE) for home UE";
                            }

                            leaf bit2 {
                                type boolean;
                                default "false";
                                description "Set bit 2 in charging characteristics information element (IE) for home UE";
                            }

                            leaf bit3 {
                                type boolean;
                                default "false";
                                description "Set bit 3 in charging characteristics information element (IE) for home UE";
                            }

                            leaf bit4 {
                                type boolean;
                                default "false";
                                description "Set bit 4 in charging characteristics information element (IE) for home UE";
                            }

                            leaf bit5 {
                                type boolean;
                                default "false";
                                description "Set bit 5 in charging characteristics information element (IE) for home UE";
                            }

                            leaf bit6 {
                                type boolean;
                                default "false";
                                description "Set bit 6 in charging characteristics information element (IE) for home UE";
                            }

                            leaf bit7 {
                                type boolean;
                                default "false";
                                description "Set bit 7 in charging characteristics information element (IE) for home UE";
                            }

                            leaf bit8 {
                                type boolean;
                                default "false";
                                description "Set bit 8 in charging characteristics information element (IE) for home UE";
                            }

                            leaf bit9 {
                                type boolean;
                                default "false";
                                description "Set bit 9 in charging characteristics information element (IE) for home UE";
                            }

                            leaf bit10 {
                                type boolean;
                                default "false";
                                description "Set bit 10 in charging characteristics information element (IE) for home UE";
                            }

                            leaf bit11 {
                                type boolean;
                                default "false";
                                description "Set bit 11 in charging characteristics information element (IE) for home UE";
                            }

                            leaf bit12 {
                                type boolean;
                                default "false";
                                description "Set bit 12 in charging characteristics information element (IE) for home UE";
                            }

                            leaf bit13 {
                                type boolean;
                                default "false";
                                description "Set bit 13 in charging characteristics information element (IE) for home UE";
                            }

                            leaf bit14 {
                                type boolean;
                                default "false";
                                description "Set bit 14 in charging characteristics information element (IE) for home UE";
                            }

                            leaf bit15 {
                                type boolean;
                                default "false";
                                description "Set bit 15 in charging characteristics information element (IE) for home UE";
                            }

                        } // container roaming

                    } // container charging-characteristics

                    container ggsn {
                        description "Enter the ggsn context";

                        container qos {
                            description "Enter the qos context";

                            leaf arp {
                                type uint32 {
                                    range "1..3";
                                }
                                default "1";
                                description "Allocation or retention priority";
                            }

                            container ambr {
                                presence "The Aggregated maximum bitrate.";
                                description "Enter the ambr context";

                                leaf down-link {
                                    type int32 {
                                        range "0..10000000";
                                    }
                                    units "kilobps";
                                    mandatory true;
                                    description "Downlink Aggregated Maximum Bit Rate (AMBR)";
                                }

                                leaf up-link {
                                    type int32 {
                                        range "0..10000000";
                                    }
                                    units "kilobps";
                                    mandatory true;
                                    description "Uplink Aggregated Maximum Bit Rate (AMBR)";
                                }

                            } // container ambr

                            container down-link {
                                description "Enter the down-link context";

                                leaf gbr {
                                    type uint32 {
                                        range "0..100000";
                                    }
                                    units "kilobps";
                                    default "2000";
                                    description "Guaranteed Bit Rate (GBR)";
                                }

                                leaf mbr {
                                    type uint32 {
                                        range "0..100000";
                                    }
                                    units "kilobps";
                                    default "2000";
                                    description "Maximum Bit Rate (MBR)";
                                }

                            } // container down-link

                            container up-link {
                                description "Enter the up-link context";

                                leaf gbr {
                                    type uint32 {
                                        range "0..100000";
                                    }
                                    units "kilobps";
                                    default "5000";
                                    description "Guaranteed Bit Rate (GBR)";
                                }

                                leaf mbr {
                                    type uint32 {
                                        range "0..100000";
                                    }
                                    units "kilobps";
                                    default "5000";
                                    description "Maximum Bit Rate (MBR)";
                                }

                            } // container up-link

                        } // container qos

                    } // container ggsn

                    container pgw {
                        description "Enter the pgw context";

                        container qos {
                            description "Enter the qos context";

                            leaf arp {
                                type uint32 {
                                    range "1..15";
                                }
                                default "1";
                                description "Allocation or retention priority";
                            }

                            leaf qci {
                                type uint32 {
                                    range "1..9";
                                }
                                default "8";
                                description "QoS Class Identifier (QCI) value that is used in GTP messages";
                            }

                            container ambr {
                                description "Enter the ambr context";

                                leaf down-link {
                                    type int32 {
                                        range "0..10000000";
                                    }
                                    units "kilobps";
                                    default "20000";
                                    description "Downlink Aggregated Maximum Bit Rate (AMBR)";
                                }

                                leaf up-link {
                                    type int32 {
                                        range "0..10000000";
                                    }
                                    units "kilobps";
                                    default "10000";
                                    description "Uplink Aggregated Maximum Bit Rate (AMBR)";
                                }

                            } // container ambr

                            container down-link {
                                description "Enter the down-link context";

                                leaf gbr {
                                    type uint32 {
                                        range "0..100000";
                                    }
                                    units "kilobps";
                                    default "0";
                                    description "Guaranteed Bit Rate (GBR)";
                                }

                                leaf mbr {
                                    type uint32 {
                                        range "0..100000";
                                    }
                                    units "kilobps";
                                    default "0";
                                    description "Maximum Bit Rate (MBR)";
                                }

                            } // container down-link

                            container up-link {
                                description "Enter the up-link context";

                                leaf gbr {
                                    type uint32 {
                                        range "0..100000";
                                    }
                                    units "kilobps";
                                    default "0";
                                    description "Guaranteed Bit Rate (GBR)";
                                }

                                leaf mbr {
                                    type uint32 {
                                        range "0..100000";
                                    }
                                    units "kilobps";
                                    default "0";
                                    description "Maximum Bit Rate (MBR)";
                                }

                            } // container up-link

                        } // container qos

                    } // container pgw

                } // container uplink

            } // list peer-profile

        } // container gtp

    } // grouping conf-submgt-gtp

}
