module nokia-yang-deviations {
    yang-version "1.1";

    namespace "urn:nokia.com:sros:ns:yang:sr:nokia-yang-deviations";

    prefix nokia-yang-deviations;

    import yang {
        prefix yang;
        revision-date 2017-02-20;
    }
    import nokia-sros-yang-extensions     { prefix "sros-ext"; }

    sros-ext:sros-major-release "rel16";

    organization "Nokia";

    contact
        "Nokia SR OS Support
         Web: <http://www.nokia.com>";

    description
        "YANG Data model for Nokia yang deviations.

         Copyright 2019 Nokia. All rights reserved. Reproduction of this document
         is authorized on the condition that the foregoing copyright notice is included.

         This nokia-yang-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision 2019-04-09;

    // Deviations

    deviation /yang:key {
        description
            "key attribute is not supported.";
        deviate not-supported;
    }
}
