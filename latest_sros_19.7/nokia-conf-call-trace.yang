submodule nokia-conf-call-trace {

    yang-version "1.1";

    belongs-to nokia-conf { prefix "conf"; }

    import nokia-sros-yang-extensions     { prefix "sros-ext"; }
    import nokia-types-nat                { prefix "types-nat"; }
    import nokia-types-sros               { prefix "types-sros"; }


    sros-ext:sros-major-release "rel19";

    organization "Nokia";

    contact
        "Nokia SR OS Support
         Web: <http://www.nokia.com>";

    description
        "Nokia YANG Data model to configure call-trace parameters on SR OS based routers.

         Copyright 2016 Nokia. All rights reserved. Reproduction of this document
         is authorized on the condition that the foregoing copyright notice is included.

         This nokia-conf-call-trace YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-06-06";

    grouping conf-call-trace {
        container call-trace {
            description "Enter the call-trace context";

            leaf max-files-number {
                type uint32 {
                    range "1..1024";
                }
                default "200";
                description "Maximum number of all call trace log files stored on all compact flash cards";
            }

            leaf primary-cf {
                type enumeration {
                    enum "cf1"                          { value 1; }
                    enum "cf2"                          { value 2; }
                }
                default "cf1";
                description "Compact flash card to be used as primary local storage location to save the call trace log files";
            }

            list location {
                key "location-type";
                description "Enter the location list instance";

                leaf location-type {
                    type enumeration {
                        enum "cf1"                          { value 1; }
                        enum "cf2"                          { value 2; }
                    }
                    description "ID of the compact flash card to be used";
                }

                leaf admin-state {
                    type types-sros:admin-state;
                    default "enable";
                    description "Administrative state of compact flash for log storage";
                }

                leaf size-limit {
                    type union {
                        type uint32 {
                            range "1..65536";
                        }
                        type enumeration {
                            enum "unlimited"                    { value 0; }
                        }
                    }
                    default "1000";
                    description "Maximum cumulative size of all local call trace log files stored on the given compact flash card";
                }

            } // list location

            list trace-profile {
                key "name";
                description "Enter the trace-profile list instance";

                leaf name {
                    type types-sros:named-item;
                    description "Unique name for the call trace profile";
                }

                leaf description {
                    type types-sros:description;
                    description "Text description";
                }

                leaf size-limit {
                    type uint32 {
                        range "1..1000";
                    }
                    units "megabytes";
                    default "10";
                    description "Maximum data volume generated by a single call trace job to the output";
                }

                leaf time-limit {
                    type types-sros:time-duration {
                        range "1..604800";
                    }
                    default "86400";
                    description "Maximum time for a single call trace job";
                }

                leaf events {
                    type enumeration {
                        enum "public-only"                  { value 2; }
                        enum "all"                          { value 3; }
                    }
                    description "Events to include in the captured trace";
                }

                container applications {
                    description "Enter the applications context";

                    leaf connectivity-management {
                        type boolean;
                        default "true";
                        description "Allow tracing for connectivity protocols";
                    }

                    leaf radius-auth {
                        type boolean;
                        default "true";
                        description "Allow tracing for messages and events related to RADIUS authentication";
                    }

                    leaf radius-acct {
                        type boolean;
                        default "true";
                        description "Allow tracing for messages and events related to RADIUS-based accounting";
                    }

                    leaf python {
                        type boolean;
                        default "true";
                        description "Allow tracing for Python script execution";
                    }

                    leaf ludb {
                        type boolean;
                        default "true";
                        description "Allow tracing for local user database lookups";
                    }

                    leaf msap {
                        type boolean;
                        default "true";
                        description "Allow tracing for MSAP creation events";
                    }

                } // container applications

                container output {
                    description "Enter the output context";

                    choice destination {
                        default "local-storage";
                        case local-storage {

                            leaf local-storage {
                                type empty;
                                description "Default destination for output";
                            }

                        }
                        case debug {

                            leaf debug {
                                type empty;
                                description "Trace log generated by a call trace job to be decoded as test and sent to debug logging";
                            }

                        }
                        case live {

                            container live {
                                presence "Live output";
                                description "Enter the live context";

                                leaf port {
                                    type types-nat:port-number;
                                    default "29770";
                                    description "TCP IP port";
                                }

                                leaf router-instance {
                                    type string;
                                    default "Base";
                                    description "Router instance or VPRN service name";
                                }

                                choice live {
                                    mandatory true;
                                    case ip-address {

                                        leaf ip-address {
                                            type types-sros:ip-address;
                                            description "IP address of the live output destination";
                                        }

                                    }
                                    case fqdn {

                                        leaf fqdn {
                                            type string {
                                                length "1..255";
                                            }
                                            description "Fully qualified domain name of the live output destination";
                                        }

                                    }
                                }
                            } // container live

                        }
                    }
                } // container output

            } // list trace-profile

        } // container call-trace

    } // grouping conf-call-trace

}
