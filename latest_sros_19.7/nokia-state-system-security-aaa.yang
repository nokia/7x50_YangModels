submodule nokia-state-system-security-aaa {

    yang-version "1.1";

    belongs-to nokia-state { prefix "state"; }

    import nokia-sros-yang-extensions     { prefix "sros-ext"; }
    import nokia-types-sros               { prefix "types-sros"; }


    sros-ext:sros-major-release "rel19";

    organization "Nokia";

    contact
        "Nokia SR OS Support
         Web: <http://www.nokia.com>";

    description
        "Nokia YANG Data model with operational state for system security aaa parameters. on SR OS based routers.

         Copyright 2016 Nokia. All rights reserved. Reproduction of this document
         is authorized on the condition that the foregoing copyright notice is included.

         This nokia-state-system-security-aaa YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-06-10";

    grouping state-system-security-aaa {
        container aaa {
            description "Enter the aaa context";

            container remote-servers {
                description "Enter the remote-servers context";

                container radius {
                    description "Enter the radius context";

                    leaf oper-state {
                        type types-sros:up-down-status;
                        description "Current status of aaa server. Is it up if one server is up.";
                    }

                    list server {
                        key "index";
                        description "Enter the server list instance";

                        leaf index {
                            type uint32 {
                                range "1..5";
                            }
                            description "Unique number which identifies a specific RADIUS server.";
                        }

                        leaf oper-state {
                            type types-sros:up-down-status;
                            description "Current status of RADIUS server.";
                        }

                    } // list server

                } // container radius

                container ldap {
                    description "Enter the ldap context";

                    leaf oper-state {
                        type types-sros:up-down-status;
                        description "Current status of aaa server. Is it up if one server is up.";
                    }

                    list server {
                        key "index";
                        description "Enter the server list instance";

                        leaf index {
                            type uint32 {
                                range "1..5";
                            }
                            description "Unique value which identifies a specific LDAP server.";
                        }

                        leaf oper-state {
                            type types-sros:up-down-status;
                            description "Operational status of LDAP server.";
                        }

                    } // list server

                } // container ldap

                container tacplus {
                    description "Enter the tacplus context";

                    leaf oper-state {
                        type types-sros:up-down-status;
                        description "Current status of aaa server. Is it up if one server is up.";
                    }

                    list server {
                        key "index";
                        description "Enter the server list instance";

                        leaf index {
                            type uint32 {
                                range "1..5";
                            }
                            description "Identifies a specific TACACS+ server.";
                        }

                        leaf oper-state {
                            type types-sros:up-down-status;
                            description "Operational status of TACACS+ server.";
                        }

                    } // list server

                } // container tacplus

                container statistics {
                    description "Statistics for aaa remote-servers.";

                    container authentication {
                        description "Statistics for aaa remote-servers authentication.";

                        container radius {
                            description "Statistics for radius.";

                            list server {
                                key "index";
                                description "Statistics for radius servers.";

                                leaf index {
                                    type uint32 {
                                        range "1..5";
                                    }
                                    description "Unique number which identifies a specific RADIUS server.";
                                }

                                leaf connection-errors {
                                    type uint32;
                                    description "Indicates the number of connection errors.";
                                }

                                leaf accepted-logins {
                                    type uint32;
                                    description "Indicates the number of accepted logins.";
                                }

                                leaf rejected-logins {
                                    type uint32;
                                    description "Indicates the number of rejected logins.";
                                }

                            } // list server

                        } // container radius

                        container tacplus {
                            description "Statistics for tacplus.";

                            list server {
                                key "index";
                                description "Statistics for tacplus servers.";

                                leaf index {
                                    type uint32 {
                                        range "1..5";
                                    }
                                    description "Identifies a specific TACACS+ server.";
                                }

                                leaf connection-errors {
                                    type uint32;
                                    description "Indicates the number of connection errors.";
                                }

                                leaf accepted-logins {
                                    type uint32;
                                    description "Indicates the number of accepted logins.";
                                }

                                leaf rejected-logins {
                                    type uint32;
                                    description "Indicates the number of rejected logins.";
                                }

                            } // list server

                        } // container tacplus

                        container ldap {
                            description "Statistics for ldap.";

                            list server {
                                key "index";
                                description "Statistics for ldap servers.";

                                leaf index {
                                    type uint32 {
                                        range "1..5";
                                    }
                                    description "Unique value which identifies a specific LDAP server.";
                                }

                                leaf connection-errors {
                                    type uint32;
                                    description "Indicates the number of connection errors.";
                                }

                                leaf accepted-logins {
                                    type uint32;
                                    description "Indicates the number of accepted logins.";
                                }

                                leaf rejected-logins {
                                    type uint32;
                                    description "Indicates the number of rejected logins.";
                                }

                            } // list server

                        } // container ldap

                        container local {
                            description "Statistics for local.";

                            leaf accepted-logins {
                                type uint32;
                                description "Indicates the number of accepted logins.";
                            }

                            leaf rejected-logins {
                                type uint32;
                                description "Indicates the number of rejected logins.";
                            }

                        } // container local

                    } // container authentication

                    container authorization {
                        description "Statistics for aaa remote-servers authorization.";

                        container tacplus {
                            description "Statistics for tacplus.";

                            list server {
                                key "index";
                                description "Statistics for tacplus servers.";

                                leaf index {
                                    type uint32 {
                                        range "1..5";
                                    }
                                    description "Identifies a specific TACACS+ server.";
                                }

                                leaf connection-errors {
                                    type uint32;
                                    description "Indicates the number of connection errors.";
                                }

                                leaf sent-requests {
                                    type uint32;
                                    description "Indicates the number of sent requests.";
                                }

                                leaf rejected-requests {
                                    type uint32;
                                    description "Indicates the number of rejected requests.";
                                }

                            } // list server

                        } // container tacplus

                    } // container authorization

                    container accounting {
                        description "Statistics for aaa remote-servers accounting.";

                        container tacplus {
                            description "Statistics for tacplus.";

                            list server {
                                key "index";
                                description "Statistics for tacplus servers.";

                                leaf index {
                                    type uint32 {
                                        range "1..5";
                                    }
                                    description "Identifies a specific TACACS+ server.";
                                }

                                leaf connection-errors {
                                    type uint32;
                                    description "Indicates the number of connection errors.";
                                }

                                leaf sent-messages {
                                    type uint32;
                                    description "Indicates the number of sent messages.";
                                }

                                leaf rejected-messages {
                                    type uint32;
                                    description "Indicates the number of rejected messages.";
                                }

                            } // list server

                        } // container tacplus

                        container radius {
                            description "Statistics for radius.";

                            list server {
                                key "index";
                                description "Statistics for radius servers.";

                                leaf index {
                                    type uint32 {
                                        range "1..5";
                                    }
                                    description "Unique number which identifies a specific RADIUS server.";
                                }

                                leaf connection-errors {
                                    type uint32;
                                    description "Indicates the number of connection errors.";
                                }

                                leaf sent-messages {
                                    type uint32;
                                    description "Indicates the number of sent messages.";
                                }

                                leaf rejected-messages {
                                    type uint32;
                                    description "Indicates the number of rejected messages.";
                                }

                            } // list server

                        } // container radius

                    } // container accounting

                } // container statistics

            } // container remote-servers

        } // container aaa

    } // grouping state-system-security-aaa

}
