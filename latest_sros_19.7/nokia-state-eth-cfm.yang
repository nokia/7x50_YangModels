submodule nokia-state-eth-cfm {

    yang-version "1.1";

    belongs-to nokia-state { prefix "state"; }

    import ietf-yang-types                { prefix "yang"; }
    import nokia-sros-yang-extensions     { prefix "sros-ext"; }
    import nokia-types-eth-cfm            { prefix "types-eth-cfm"; }


    sros-ext:sros-major-release "rel19";

    organization "Nokia";

    contact
        "Nokia SR OS Support
         Web: <http://www.nokia.com>";

    description
        "Nokia YANG Data model with operational state for eth-cfm on SR OS based routers.

         Copyright 2016 Nokia. All rights reserved. Reproduction of this document
         is authorized on the condition that the foregoing copyright notice is included.

         This nokia-state-eth-cfm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-04-17";

    grouping state-eth-cfm {
        container eth-cfm {
            description "Enter the eth-cfm context";

            list domain {
                key "md-admin-name";
                description "Enter the domain list instance";

                leaf md-admin-name {
                    type types-eth-cfm:admin-name;
                    description "Unique domain name";
                }

                list association {
                    key "ma-admin-name";
                    description "Enter the association list instance";

                    leaf ma-admin-name {
                        type types-eth-cfm:admin-name;
                        description "Unique domain association name";
                    }

                } // list association

            } // list domain

        } // container eth-cfm

    } // grouping state-eth-cfm

}
