submodule nokia-state-port-sonet {

    yang-version "1.1";

    belongs-to nokia-state { prefix "state"; }

    import ietf-yang-types                { prefix "yang"; }
    import nokia-sros-yang-extensions     { prefix "sros-ext"; }
    import nokia-types-port               { prefix "types-port"; }
    import nokia-types-sros               { prefix "types-sros"; }


    sros-ext:sros-major-release "rel19";

    organization "Nokia";

    contact
        "Nokia SR OS Support
         Web: <http://www.nokia.com>";

    description
        "Nokia YANG Data model with operational state for SONET/SDH ports on SR OS based routers.

         Copyright 2016 Nokia. All rights reserved. Reproduction of this document
         is authorized on the condition that the foregoing copyright notice is included.

         This nokia-state-port-sonet YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-06-05";

    grouping state-port-sonet-sonet-sdh {
        container sonet-sdh {
            description "Enter the sonet-sdh context";

            leaf current-alarms {
                type types-port:sonet-report-alarms;
                description "Indicates the current alarms on the SONET port.";
            }

            leaf received-j0-string {
                type string {
                    length "0..32";
                }
                description "Indicates the contents of the j0 byte in the SONET Section Header.";
            }

            leaf received-k1-byte {
                type uint32 {
                    range "0..255";
                }
                description
                    "Indicates the Automatic Protection Switching(APS) signalling status from
                     the K1 byte in the SONET Line Overhead Header.";
            }

            leaf received-k2-byte {
                type uint32 {
                    range "0..255";
                }
                description
                    "Indicates the Automatic Protection Switching(APS) signalling status from
                     the K2 byte in the SONET Line Overhead Header.";
            }

            leaf received-s1-byte {
                type uint32 {
                    range "0..255";
                }
                description
                    "Indicates the Synchronization Status Message from the S1 byte in
                     the Line Overhead Header. A value of 0x00 indicates unknown quality.
                     A value of 0xF0 indicates `Do not use for synchronization`. Other
                     values are documented in Telcordia GR253 and ITU G.707.";
            }

            leaf transmitted-s1-byte {
                type uint32;
                description "Indicates the transmitted S1 Byte.";
            }

        } // container sonet-sdh

    } // grouping state-port-sonet-sonet-sdh

}
