submodule nokia-conf-routing-options {

    yang-version "1.1";

    belongs-to nokia-conf { prefix "conf"; }

    import nokia-sros-yang-extensions     { prefix "sros-ext"; }
    import nokia-types-sros               { prefix "types-sros"; }


    sros-ext:sros-major-release "rel19";

    organization "Nokia";

    contact
        "Nokia SR OS Support
         Web: <http://www.nokia.com>";

    description
        "Nokia YANG Data model to configure routing options attributes on SR OS based routers.

         Copyright 2016 Nokia. All rights reserved. Reproduction of this document
         is authorized on the condition that the foregoing copyright notice is included.

         This nokia-conf-routing-options YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-06-27";

    grouping conf-routing-options {
        container routing-options {
            description "Enter the routing-options context";

            leaf ip-fast-reroute {
                type boolean;
                default "false";
                description "Enable IP fast reroute capability";
            }

            container if-attribute {
                description "Enter the if-attribute context";

                list admin-group {
                    key "group-name";
                    max-elements 32;
                    description "Enter the admin-group list instance";

                    leaf group-name {
                        type types-sros:named-item;
                        description "Specifies interface admin group name.";
                    }

                    leaf value {
                        type uint32 {
                            range "0..31";
                        }
                        sros-ext:immutable;
                        mandatory true;
                        description "Specifies the group value associated with this administrative group.";
                    }

                } // list admin-group

                list srlg-group {
                    key "name";
                    max-elements 1024;
                    description "Enter the srlg-group list instance";

                    leaf name {
                        type types-sros:named-item;
                        description "Specifies a name defined for the Shared Risk Link Group (SRLG).";
                    }

                    leaf value {
                        type int64 {
                            range "0..4294967295";
                        }
                        sros-ext:immutable;
                        mandatory true;
                        description "Specifies the group value associated with this SRLG.";
                    }

                    leaf penalty-weight {
                        type uint32 {
                            range "0..65535";
                        }
                        default "0";
                        description "Specifies the penalty weight associated with this SRLG group.";
                    }

                } // list srlg-group

            } // container if-attribute

            container admin-tags {
                description "Enter the admin-tags context";

                list admin-tag {
                    key "tag";
                    max-elements 256;
                    description "Add a list entry for admin-tag";

                    leaf tag {
                        type string {
                            length "1..32";
                        }
                        description "Specifies admin-tag.";
                    }

                } // list admin-tag

                list route-admin-tag-policy {
                    key "policy-name";
                    max-elements 2048;
                    description "Enter the route-admin-tag-policy list instance";

                    leaf policy-name {
                        type string {
                            length "1..64";
                        }
                        description "Policy name";
                    }

                    list exclude {
                        key "tag";
                        max-elements 8;
                        description "Add a list entry for exclude";

                        leaf tag {
                            type leafref {
                                path "../../../admin-tag/tag";
                            }
                            description "Specifies admin-tag.";
                        }

                    } // list exclude

                    list include {
                        key "tag";
                        max-elements 8;
                        description "Add a list entry for include";

                        leaf tag {
                            type leafref {
                                path "../../../admin-tag/tag";
                            }
                            description "Specifies admin-tag.";
                        }

                    } // list include

                } // list route-admin-tag-policy

            } // container admin-tags

            container route-next-hop-policy {
                description "Enter the route-next-hop-policy context";

                list template {
                    key "template-name";
                    description "Enter the template list instance";

                    leaf template-name {
                        type types-sros:named-item;
                        description "Template name";
                    }

                    leaf description {
                        type types-sros:description;
                        description "Text description";
                    }

                    leaf srlg {
                        type boolean;
                        default "false";
                        description "Select next hops from the SRLG";
                    }

                    leaf nh-type {
                        type enumeration {
                            enum "ip"                           { value 1; }
                            enum "tunnel"                       { value 2; }
                        }
                        default "ip";
                        description "Preferred next hop";
                    }

                    leaf protection-type {
                        type enumeration {
                            enum "link"                         { value 1; }
                            enum "node"                         { value 2; }
                        }
                        default "node";
                        description "Protection type used";
                    }

                    list exclude-group {
                        key "group-name";
                        max-elements 32;
                        description "Add a list entry for exclude-group";

                        leaf group-name {
                            type leafref {
                                path "../../../../if-attribute/admin-group/group-name";
                            }
                            description "Group name out of which the next-hop link is selected";
                        }

                    } // list exclude-group

                    list include-group {
                        key "group-name";
                        max-elements 32;
                        description "Enter the include-group list instance";

                        leaf group-name {
                            type leafref {
                                path "../../../../if-attribute/admin-group/group-name";
                            }
                            description "Group name out of which the next-hop link is selected";
                        }

                        leaf preference {
                            type int32 {
                                range "1..255";
                            }
                            default "255";
                            description "Preference number for configured admin-group.";
                        }

                    } // list include-group

                } // list template

            } // container route-next-hop-policy

        } // container routing-options

    } // grouping conf-routing-options

}
