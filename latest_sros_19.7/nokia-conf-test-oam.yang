submodule nokia-conf-test-oam {

    yang-version "1.1";

    belongs-to nokia-conf { prefix "conf"; }

    import nokia-sros-yang-extensions     { prefix "sros-ext"; }
    import nokia-types-oam                { prefix "types-oam"; }
    import nokia-types-sros               { prefix "types-sros"; }


    sros-ext:sros-major-release "rel19";

    organization "Nokia";

    contact
        "Nokia SR OS Support
         Web: <http://www.nokia.com>";

    description
        "Nokia YANG Data model to configure OAM test parameters configuration on SR OS based routers.

         Copyright 2016 Nokia. All rights reserved. Reproduction of this document
         is authorized on the condition that the foregoing copyright notice is included.

         This nokia-conf-test-oam YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-03-22";

    grouping conf-test-oam {
        container test-oam {
            description "Enter the test-oam context";

            container mpls-dm {
                description "Enter the mpls-dm context";

                leaf admin-state {
                    type types-sros:admin-state;
                    default "disable";
                    description "Administrative state of MPLS DM packet processing";
                }

            } // container mpls-dm

            container twamp {
                description "Enter the twamp context";

                container server {
                    description "Enter the server context";

                    leaf admin-state {
                        type types-sros:admin-state;
                        default "disable";
                        description "Administrative state of the TWAMP server";
                    }

                    leaf inactivity-timeout {
                        type uint32 {
                            range "60..3600";
                        }
                        units "seconds";
                        sros-ext:auto-restart-to-modify;
                        default "900";
                        description "System wide inactivity timeout for each TWAMP server control connection";
                    }

                    leaf max-connections {
                        type types-oam:twamp-server-connection-count;
                        sros-ext:auto-restart-to-modify;
                        default "32";
                        description "System wide maximum number of concurrent TWAMP server control connections";
                    }

                    leaf max-sessions {
                        type types-oam:twamp-server-session-count;
                        sros-ext:auto-restart-to-modify;
                        default "32";
                        description "System wide maximum number of concurrent TWAMP server test sessions";
                    }

                    leaf ref-inactivity-timeout {
                        type uint32 {
                            range "60..3600";
                        }
                        units "seconds";
                        sros-ext:auto-restart-to-modify;
                        default "900";
                        description "System wide reflector inactivity timeout for TWAMP";
                    }

                    list prefix {
                        key "ip-prefix";
                        max-elements 100;
                        description "Enter the prefix list instance";

                        leaf ip-prefix {
                            type types-sros:ip-unicast-prefix;
                            description "Prefix to be matched against a TWAMP client address Best-fit is used when matching a TWAMP client's IP address against the set of configured prefixes. For example, suppose the first row of this table has the prefix 138.120.0.0/16, and the second row has the prefix 138.120.214.0/24. The TWAMP client address 138.120.214.52 matches the second row.";
                        }

                        leaf description {
                            type types-sros:description;
                            description "Text description";
                        }

                        leaf max-connections {
                            type types-oam:twamp-server-connection-count;
                            default "32";
                            description "Maximum number of concurrent TWAMP control connections allowed for the TWAMP prefix identified by the index values In addition, the number of concurrent TWAMP control connections for this prefix is limited by the system maximum '/configure test-oam twamp server max-connections'.";
                        }

                        leaf max-sessions {
                            type types-oam:twamp-server-session-count;
                            default "32";
                            description "Maximum number of concurrent TWAMP test sessions allowed for the TWAMP prefix identified by the key value In addition, the number of concurrent TWAMP test sessions for this prefix is limited by the system maximum '/configure test-oam twamp server max-sessions'.";
                        }

                    } // list prefix

                } // container server

                container twamp-light {
                    description "Enter the twamp-light context";

                    leaf inactivity-timeout {
                        type uint32 {
                            range "10..100";
                        }
                        units "seconds";
                        default "100";
                        description "System inactivity timeout for TWAMP-Light reflectors A TWAMP-Light reflector replies to TWAMP-Test PDUs. When a reflector sees a TWAMP-Test PDU for a new session (i.e. a {source IP address, source UDP port, destination IP address} triple which is not known to the reflector), the reflector allocates a record for the session. The record is used to ensure that reply PDUs sent for the session have consecutive sequence numbers. When a reflector sees 'inactivity-timeout' seconds pass without receiving a TWAMP-Test PDU for a particular session, an inactivity timeout has occurred, so the record allocated to the session is freed.";
                    }

                } // container twamp-light

            } // container twamp

        } // container test-oam

    } // grouping conf-test-oam

}
