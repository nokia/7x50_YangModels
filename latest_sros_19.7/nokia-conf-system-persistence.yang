submodule nokia-conf-system-persistence {

    yang-version "1.1";

    belongs-to nokia-conf { prefix "conf"; }

    import nokia-sros-yang-extensions     { prefix "sros-ext"; }
    import nokia-types-sros               { prefix "types-sros"; }
    import nokia-types-system             { prefix "types-system"; }

    include nokia-conf-groups;

    sros-ext:sros-major-release "rel19";

    organization "Nokia";

    contact
        "Nokia SR OS Support
         Web: <http://www.nokia.com>";

    description
        "Nokia YANG Data model to configure system persistence parameters. on SR OS based routers.

         Copyright 2016 Nokia. All rights reserved. Reproduction of this document
         is authorized on the condition that the foregoing copyright notice is included.

         This nokia-conf-system-persistence YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-05-03";

    grouping conf-system-persistence {
        container persistence {
            description "Enter the persistence context";

            container ancp {
                description "Enter the ancp context";

                leaf location {
                    type types-system:cpm-flash-id;
                    description "CPM flash card where the information is stored";
                }

                leaf description {
                    type types-sros:description;
                    description "Text description";
                }

            } // container ancp

            container application-assurance {
                description "Enter the application-assurance context";

                leaf location {
                    type types-system:cpm-flash-id;
                    description "CPM flash card where the information is stored";
                }

                leaf description {
                    type types-sros:description;
                    description "Text description";
                }

            } // container application-assurance

            container dhcp-server {
                description "Enter the dhcp-server context";

                leaf location {
                    type types-system:cpm-flash-id;
                    description "CPM flash card where the information is stored";
                }

                leaf description {
                    type types-sros:description;
                    description "Text description";
                }

            } // container dhcp-server

            container nat-port-forwarding {
                description "Enter the nat-port-forwarding context";

                leaf location {
                    type types-system:cpm-flash-id;
                    description "CPM flash card where the information is stored";
                }

                leaf description {
                    type types-sros:description;
                    description "Text description";
                }

            } // container nat-port-forwarding

            container python-policy-cache {
                description "Enter the python-policy-cache context";

                leaf location {
                    type types-system:cpm-flash-id;
                    description "CPM flash card where the information is stored";
                }

                leaf description {
                    type types-sros:description;
                    description "Text description";
                }

            } // container python-policy-cache

            container subscriber-mgmt {
                description "Enter the subscriber-mgmt context";

                leaf location {
                    type types-system:cpm-flash-id;
                    description "CPM flash card where the information is stored";
                }

                leaf description {
                    type types-sros:description;
                    description "Text description";
                }

            } // container subscriber-mgmt

            container options {
                description "Enter the options context";

                leaf dhcp-leasetime-threshold {
                    type types-sros:time-duration {
                        range "1..631152000";
                    }
                    description "Threshold time for DHCP leases to be eligible for persistence";
                }

            } // container options

        } // container persistence

    } // grouping conf-system-persistence

}
