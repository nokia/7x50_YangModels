submodule nokia-state-svc-ies-grp-if-wlangw {

    yang-version "1.1";

    belongs-to nokia-state { prefix "state"; }

    import ietf-yang-types                { prefix "yang"; }
    import nokia-sros-yang-extensions     { prefix "sros-ext"; }
    import nokia-types-sros               { prefix "types-sros"; }


    sros-ext:sros-major-release "rel19";

    organization "Nokia";

    contact
        "Nokia SR OS Support
         Web: <http://www.nokia.com>";

    description
        "Nokia YANG Data model with operational state for ies service group interface WLAN Gateway on SR OS based routers.

         Copyright 2016 Nokia. All rights reserved. Reproduction of this document
         is authorized on the condition that the foregoing copyright notice is included.

         This nokia-state-svc-ies-grp-if-wlangw YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-03-20";

    grouping state-svc-ies-grp-if-wlangw-wlan-gw {
        container wlan-gw {
            description "Enter the wlan-gw context";

            leaf num-tunnels {
                type yang:gauge32;
                description
                    "The number of tunnels with ESM hosts terminated on this group
                     interface.";
            }

            container l2-ap {
                description "Enter the l2-ap context";

                list access-point {
                    key "sap-id";
                    description "Enter the access-point list instance";

                    leaf sap-id {
                        type types-sros:sap;
                        description "SAP ID for the Layer 2 access point";
                    }

                    leaf id {
                        type uint32;
                        description "The unique index of this access point";
                    }

                } // list access-point

            } // container l2-ap

        } // container wlan-gw

    } // grouping state-svc-ies-grp-if-wlangw-wlan-gw

}
