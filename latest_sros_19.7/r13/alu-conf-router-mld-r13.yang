module alu-conf-router-mld-r13 {
  yang-version "1";

  namespace "urn:alcatel-lucent.com:sros:ns:yang:conf-router-mld-r13";

  prefix "conf-router-mld-r13";

  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure MLD on SR OS based routers. 
       
       Copyright 2014-2015 Alcatel-Lucent, 2016 Nokia. All rights reserved. 
       Reproduction of this document is authorized on the condition that the 
       foregoing copyright notice is included. 
       
       This alu-conf-router-mld-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2017-10-03";

  grouping alu-conf-router-mld-r13 {
    container mld {
      presence
          "Configure MLD";
      container grp-if-query-src-ip {
        description
            "Configure the IP source address used in MLD queries for all group-interfaces";
        leaf ipv6-address {
          type inet:ipv6-address;
        } //ipv6-address

      } //container grp-if-query-src-ip

      container query-interval {
        description
            "Configure the frequency at which Host-Query packets are transmitted";
        leaf seconds {
          type uint32 {
            range "2..1024";
          }
        } //seconds

      } //container query-interval

      container query-last-listener-interval {
        description
            "Configure the frequency at which Group-Specific-Query packets are transmitted";
        leaf seconds {
          type uint32 {
            range "1..1023";
          }
        } //seconds

      } //container query-last-listener-interval

      container query-response-interval {
        description
            "Configure the time to wait to receive a response to the Host-Query message 
             from the host";
        leaf seconds {
          type uint32 {
            range "1..1023";
          }
        } //seconds

      } //container query-response-interval

      container robust-count {
        description
            "Configure the robust count";
        leaf robust-count {
          type uint32 {
            range "2..10";
          }
        } //robust-count

      } //container robust-count

      leaf shutdown {
        type boolean;
        description
            "Administratively enable or disable the operation of MLD";
      }

      list group-interface {
        key "ip-int-name";
        description
            "Configure MLD group-interface";
        leaf ip-int-name {
          type string {
            length "1..32";
          }
        } //ip-int-name

        leaf disable-router-alert-check {
          type boolean;
          description
              "Enable/disable the MLD router alert check option";
        }

        container import {
          description
              "Import a policy to filter MLD packets";
          leaf policy-name {
            type string {
              length "1..32";
            }
          } //policy-name

        } //container import

        container max-groups {
          description
              "Configure the maximum number of groups for this group-interface";
          leaf max-groups-id {
            type uint16 {
              range "1..16000";
            }
          } //max-groups-id

        } //container max-groups

        container max-grp-sources {
          description
              "Configure the maximum number of group sources for this group-interface";
          leaf max-grp-sources-id {
            type uint16 {
              range "1..32000";
            }
          } //max-grp-sources-id

        } //container max-grp-sources

        container max-sources {
          description
              "Configure the maximum number of sources for this group-interface";
          leaf max-sources-id {
            type uint16 {
              range "1..1000";
            }
          } //max-sources-id

        } //container max-sources

        container query-interval {
          description
              "Configure the frequency at which Host-Query packets are transmitted";
          leaf seconds {
            type uint32 {
              range "2..1024";
            }
          } //seconds

        } //container query-interval

        container query-last-listener-interval {
          description
              "Configure the frequency at which Group-Specific-Query packets are transmitted";
          leaf seconds {
            type uint32 {
              range "1..1023";
            }
          } //seconds

        } //container query-last-listener-interval

        container query-response-interval {
          description
              "Configure the time to wait to receive a response to the Host-Query message 
               from the host";
          leaf seconds {
            type uint32 {
              range "1..1023";
            }
          } //seconds

        } //container query-response-interval

        container query-src-ip {
          description
              "Configure the IP source address used in MLD queries for this group-interface";
          leaf ipv6-address {
            type inet:ipv6-address;
          } //ipv6-address

        } //container query-src-ip

        leaf shutdown {
          type boolean;
          description
              "Administratively enable/disable the group interface";
        }

        leaf sub-hosts-only {
          type boolean;
          description
              "Enable/disable the MLD traffic from known hosts only";
        }

        leaf subnet-check {
          type boolean;
          description
              "Enable/disable local subnet checking for MLD";
        }

        container version {
          description
              "Configure the version of MLD";
          leaf version {
            type uint32 {
              range "1..2";
            }
            description
                "[1 or 2]";
          } //version

        } //container version

        container mcac {
          description
              "Configure multicast CAC policy and constraints for this group interface";
          container if-policy {
            description
                "Configure multicast CAC if-policy for this interface";
            leaf if-policy-name {
              type string {
                length "1..32";
              }
            } //if-policy-name

          } //container if-policy

          container policy {
            description
                "Configure multicast CAC policy for this interface";
            leaf policy-name {
              type string {
                length "1..32";
              }
              description
                  "max 32 chars";
            } //policy-name

          } //container policy

          container unconstrained-bw {
            description
                "Configure unconstrained-bw for multicast cac policy on this interface";
            leaf bandwidth {
              type int32 {
                range "0..2147483647";
              }
            } //bandwidth

            leaf mandatory-bw {
              type int32 {
                range "0..2147483647";
              }
            } //mandatory-bw

          } //container unconstrained-bw

          container mc-constraints {
            description
                "Configure multicast CAC constraints";
            leaf shutdown {
              type boolean;
              description
                  "Administratively enable/disable constraint for multicast cac policy";
            }

          } //container mc-constraints

        } //container mcac

      } //list group-interface

      list interface {
        key "ip-int-name";
        description
            "Configure MLD interface";
        leaf ip-int-name {
          type string {
            length "1..32";
          }
        } //ip-int-name

        leaf disable-router-alert-check {
          type boolean;
          description
              "Enable/disable the MLD router alert check option";
        }

        container import {
          description
              "Import a policy to filter MLD packets";
          leaf policy-name {
            type string {
              length "1..32";
            }
          } //policy-name

        } //container import

        container max-groups {
          description
              "Configure the maximum number of groups for this interface";
          leaf max-groups-id {
            type uint16 {
              range "1..16000";
            }
          } //max-groups-id

        } //container max-groups

        container max-grp-sources {
          description
              "Configure the maximum number of group sources for this group-interface";
          leaf max-grp-sources-id {
            type uint16 {
              range "1..32000";
            }
          } //max-grp-sources-id

        } //container max-grp-sources

        container max-sources {
          description
              "Configure the maximum number of sources for this group-interface";
          leaf max-sources-id {
            type uint16 {
              range "1..1000";
            }
          } //max-sources-id

        } //container max-sources

        container query-interval {
          description
              "Configure the frequency at which Host-Query packets are transmitted on this 
               interface";
          leaf seconds {
            type uint32 {
              range "2..1024";
            }
          } //seconds

        } //container query-interval

        container query-last-listener-interval {
          description
              "Configure the frequency at which Group-Specific-Query packets are transmitted 
               on this interface";
          leaf seconds {
            type uint32 {
              range "1..1023";
            }
          } //seconds

        } //container query-last-listener-interval

        container query-response-interval {
          description
              "Configure the time to wait to receive a response to the Host-Query message 
               from the host on this interface";
          leaf seconds {
            type uint32 {
              range "1..1023";
            }
          } //seconds

        } //container query-response-interval

        leaf shutdown {
          type boolean;
          description
              "Administratively enable/disable the interface";
        }

        container version {
          description
              "Configure the version of MLD";
          leaf version {
            type uint32 {
              range "1..2";
            }
            description
                "[1 or 2]";
          } //version

        } //container version

        container mcac {
          description
              "Configure multicast CAC policy and constraints for this interface";
          container if-policy {
            description
                "Configure multicast CAC if-policy for this interface";
            leaf if-policy-name {
              type string {
                length "1..32";
              }
            } //if-policy-name

          } //container if-policy

          container policy {
            description
                "Configure multicast CAC policy for this interface";
            leaf policy-name {
              type string {
                length "1..32";
              }
              description
                  "max 32 chars";
            } //policy-name

          } //container policy

          container unconstrained-bw {
            description
                "Configure unconstrained-bw for multicast cac policy on this interface";
            leaf bandwidth {
              type int32 {
                range "0..2147483647";
              }
            } //bandwidth

            leaf mandatory-bw {
              type int32 {
                range "0..2147483647";
              }
            } //mandatory-bw

          } //container unconstrained-bw

          container mc-constraints {
            description
                "Configure multicast CAC constraints";
            list level {
              key "level-id";
              description
                  "Configure levels and their associated bandwidth for multicast cac policy on 
                   this interface";
              leaf level-id {
                type uint32 {
                  range "1..8";
                }
              } //level-id

              leaf bw {
                type uint32;
                description
                    "[0..2147483647] kbps";
              } //bw

            } //list level

            list number-down {
              key "number-lag-port-down";
              description
                  "Configure number of ports down along with level for multicast cac policy on 
                   this interface";
              leaf number-lag-port-down {
                type string;
                description
                    "Attribute number-lag-port-down for number-down";
              } //number-lag-port-down

              leaf level {
                type uint32 {
                  range "1..8";
                }
              } //level

            } //list number-down

            leaf shutdown {
              type boolean;
              description
                  "Administratively enable/disable constraint for multicast cac policy";
            }

            leaf use-lag-port-weight {
              type boolean;
              description
                  "Enable/disable using the LAG port weight while calculating Multicast CAC 
                   constraints";
            }

          } //container mc-constraints

        } //container mcac

        container ssm-translate {
          description
              "Context to add/remove ssm-translate group ranges";
          list grp-range {
            key "start end";
            description
                "Add/remove SSM translate group range entry";
            leaf start {
              type inet:ipv6-address;
              description
                  "Attribute start for grp-range";
            } //start

            leaf end {
              type inet:ipv6-address;
              description
                  "Attribute end for grp-range";
            } //end

            list source {
              key "src-ipv6-address";
              description
                  "Add/remove source address for the SSM translate group range";
              leaf src-ipv6-address {
                type inet:ipv6-address;
                description
                    "Attribute src-ipv6-address for source";
              } //src-ipv6-address

            } //list source

          } //list grp-range

        } //container ssm-translate

        container static {
          description
              "Add/remove MLD static group membership";
          container group {
            description
                "Add/remove a static multicast group";
            leaf grp-ipv6-address {
              type inet:ipv6-address;
              description
                  "Attribute grp-ipv6-address for group";
            } //grp-ipv6-address

            leaf start {
              type inet:ipv6-address;
              description
                  "grp-ipv6-address";
            } //start

            leaf end {
              type inet:ipv6-address;
              description
                  "grp-ipv6-address";
            } //end

            leaf step {
              type inet:ipv6-address;
            } //step

            container source {
              description
                  "Add/remove a static multicast source";
              leaf src-ipv6-address {
                type inet:ipv6-address;
                description
                    "Attribute src-ipv6-address for source";
              } //src-ipv6-address

              leaf source-id {
                type inet:ipv6-address;
                description
                    "src-ipv6-address";
              } //source-id

            } //container source

            leaf starg {
              type boolean;
              description
                  "Add/remove a static starg entry";
            }

          } //container group

        } //container static

      } //list interface

      container ssm-translate {
        description
            "Context to add/remove ssm-translate group ranges";
        list grp-range {
          key "start end";
          description
              "Add/remove SSM translate group range entry";
          leaf start {
            type inet:ipv6-address;
            description
                "Attribute start for grp-range";
          } //start

          leaf end {
            type inet:ipv6-address;
            description
                "Attribute end for grp-range";
          } //end

          list source {
            key "src-ipv6-address";
            description
                "Add/remove source address for the SSM translate group range";
            leaf src-ipv6-address {
              type inet:ipv6-address;
              description
                  "Attribute src-ipv6-address for source";
            } //src-ipv6-address

          } //list source

        } //list grp-range

      } //container ssm-translate

    } //container mld

  } //grouping alu-conf-router-mld-r13

} //module  alu-conf-router-mld-r13
