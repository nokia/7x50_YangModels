module alu-conf-mda-cellular-r13 {
  yang-version "1";

  namespace "urn:alcatel-lucent.com:sros:ns:yang:conf-mda-cellular-r13";

  prefix "conf-mda-cellular-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure cellular MDA parameters on SR OS 
       based routers. 
       
       Copyright 2014-2015 Alcatel-Lucent, 2016 Nokia. All rights reserved. 
       Reproduction of this document is authorized on the condition that the 
       foregoing copyright notice is included. 
       
       This alu-conf-mda-cellular-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-04-26";

  grouping alu-conf-mda-cellular-r13 {
    container cellular {
      description
          "Configure cellular MDA parameters";
      container active-sim {
        description
            "Configure the active SIM for the MDA";
        leaf sim-card {
          type enumeration {
            enum 1;
            enum 2;
            enum auto;
          }
        } //sim-card

      } //container active-sim

      container down-recovery-criteria {
        description
            "Configure the criteria to reset the system if the cellular interface is 
             inoperational";
        leaf-list criterion {
          type enumeration {
            enum port;
            enum bgp;
          }
          max-elements 2;
        } //criterion

      } //container down-recovery-criteria

      container down-recovery-interval {
        description
            "Configure the interval to reset the system if the cellular interface is 
             inoperational";
        leaf interval {
          type uint32 {
            range "1..240";
          }
          description
              "[1..240] in minutes";
        } //interval

      } //container down-recovery-interval

      container preferred-sim {
        description
            "Configure the preferred SIM for the MDA to use at startup when active-sim is 
             auto";
        leaf sim-card {
          type enumeration {
            enum 1;
            enum 2;
          }
        } //sim-card

      } //container preferred-sim

      container sim {
        description
            "Configure SIM cards for the cellular MDA";
        leaf sim-card-number {
          type uint32 {
            range "1..2";
          }
        } //sim-card-number

        container description {
          description
              "Configure a description for the SIM card";
          leaf description-string {
            type string {
              length "1..80";
            }
          } //description-string

        } //container description

        container pin {
          description
              "Configure the PIN for the SIM card";
          leaf pin-string {
            type string {
              length "1..500";
            }
          } //pin-string

          leaf hash-hash2-custom {
            type enumeration {
              enum hash;
              enum hash2;
              enum custom;
            }
          } //hash-hash2-custom

        } //container pin

        container failover-criteria {
          description
              "Configure the failover criteria for the SIM card";
          leaf bgp-neighbor-state {
            type boolean;
            description
                "Control whether the system will switch SIM cards based on BGP neighbor state";
          }

          container failure-duration {
            description
                "Controls the amount of time before the system will switch SIM cards";
            leaf duration {
              type uint32 {
                range "1..60";
              }
              default 5;
              description
                  "[1..60] minutes - Default: 5";
            } //duration

          } //container failure-duration

          leaf port-oper-state {
            type boolean;
            description
                "Control whether the system will switch SIM cards based on the port operational 
                 state";
          }

        } //container failover-criteria

      } //container sim

    } //container cellular

  } //grouping alu-conf-mda-cellular-r13

} //module  alu-conf-mda-cellular-r13
