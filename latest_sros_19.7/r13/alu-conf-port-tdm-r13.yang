module alu-conf-port-tdm-r13 {
  yang-version "1";

  namespace "urn:alcatel-lucent.com:sros:ns:yang:conf-port-tdm-r13";

  prefix "conf-port-tdm-r13";

  import alu-conf-port-tdm-ds1-r13 {
    prefix "conf-port-tdm-ds1-r13";
  }
  import alu-conf-port-tdm-ds3-r13 {
    prefix "conf-port-tdm-ds3-r13";
  }
  import alu-conf-port-tdm-e1-r13 {
    prefix "conf-port-tdm-e1-r13";
  }
  import alu-conf-port-tdm-e3-r13 {
    prefix "conf-port-tdm-e3-r13";
  }
  import alu-types {
    prefix "alu";
  }

  alu:alu-major-release "rel19";

  organization "Alcatel-Lucent";

  contact
      "Alcatel-Lucent SR OS Support 
       Web: <http://www.alcatel-lucent.com>";

  description
      "Alcatel-Lucent YANG Data model to configure TDM parameters for a port on SR OS 
       based routers. 
       
       Copyright 2014-2015 Alcatel-Lucent, 2016 Nokia. All rights reserved. 
       Reproduction of this document is authorized on the condition that the 
       foregoing copyright notice is included. 
       
       This alu-conf-port-tdm-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2014-10-20";

  grouping alu-conf-port-tdm-r13 {
    container tdm {
      description
          "Configure TDM parameters for a port";
      container buildout {
        description
            "Configure the line buildout for a physical DS1/DS3 port";
        leaf long-short {
          type enumeration {
            enum long;
            enum short;
          }
          description
              "keywords";
        } //long-short

      } //container buildout

      container hold-time {
        description
            "Configure the line dampening timers";
        leaf up {
          type uint32 {
            range "0..100";
          }
          description
              "[0..100] in 100s of milliseconds";
        } //up

        leaf down {
          type uint32 {
            range "0..100";
          }
          description
              "[0..100] in 100s of milliseconds";
        } //down

      } //container hold-time

      container lbo {
        description
            "Configure the transmitter attenuation for a long buildout on a physical DS1 
             port";
        leaf t0dB--7.5dB--15.0dB--22.5dB {
          type string;
          description
              "keywords";
        } //t0dB--7.5dB--15.0dB--22.5dB

      } //container lbo

      container length {
        description
            "Configure the cable length for a short buildout on a physical DS1 port";
        leaf t133-266-399-533-655 {
          type enumeration {
            enum 133;
            enum 266;
            enum 399;
            enum 533;
            enum 655;
          }
          description
              "keywords";
        } //t133-266-399-533-655

      } //container length

      uses "conf-port-tdm-ds1-r13:alu-conf-port-tdm-ds1-r13";
      uses "conf-port-tdm-ds3-r13:alu-conf-port-tdm-ds3-r13";
      uses "conf-port-tdm-e1-r13:alu-conf-port-tdm-e1-r13";
      uses "conf-port-tdm-e3-r13:alu-conf-port-tdm-e3-r13";
    } //container tdm

  } //grouping alu-conf-port-tdm-r13

} //module  alu-conf-port-tdm-r13
