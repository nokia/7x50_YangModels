module alu-conf-router-bier-r13 {
  yang-version "1";

  namespace "urn:alcatel-lucent.com:sros:ns:yang:conf-router-bier-r13";

  prefix "conf-router-bier-r13";

  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure BIER on SR OS based routers. 
       
       Copyright 2014-2015 Alcatel-Lucent, 2016 Nokia. All rights reserved. 
       Reproduction of this document is authorized on the condition that the 
       foregoing copyright notice is included. 
       
       This alu-conf-router-bier-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2018-09-21";

  grouping alu-conf-router-bier-r13 {
    container bier {
      presence
          "Configure BIER";
      leaf shutdown {
        type boolean;
        description
            "Configure BIER admin state";
      }

      list template {
        key "template-string";
        description
            "Configure BIER template";
        leaf template-string {
          type string {
            length "1..32";
          }
        } //template-string

        leaf shutdown {
          type boolean;
          description
              "Configure BIER template admin state";
        }

        container sub-domain {
          description
              "Configure BIER sub domain";
          leaf start {
            type uint32 {
              range "0..255";
            }
          } //start

          leaf end {
            type uint32 {
              range "0..255";
            }
          } //end

          leaf sub-domain-id {
            type uint32 {
              range "0..255";
            }
          } //sub-domain-id

          container bfr-id {
            description
                "Configure BIER sub domain BFR ID";
            leaf bfr-id-id {
              type uint32 {
                range "1..4096";
              }
            } //bfr-id-id

          } //container bfr-id

          container mt {
            description
                "Configure BIER sub domain ISIS multi topology";
            leaf mt-id {
              type enumeration {
                enum ipv4-unicast;
                enum ipv4-multicast;
                enum ipv6-unicast;
                enum ipv6-multicast;
              }
            } //mt-id

          } //container mt

          container prefix {
            description
                "Configure BIER sub domain prefix";
            leaf prefix-id {
              type inet:ip-address;
            } //prefix-id

          } //container prefix

        } //container sub-domain

      } //list template

    } //container bier

  } //grouping alu-conf-router-bier-r13

} //module  alu-conf-router-bier-r13
