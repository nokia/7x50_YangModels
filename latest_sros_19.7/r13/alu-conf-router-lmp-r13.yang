module alu-conf-router-lmp-r13 {
  yang-version "1";

  namespace "urn:alcatel-lucent.com:sros:ns:yang:conf-router-lmp-r13";

  prefix "conf-router-lmp-r13";

  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure Link Management Protocol on SR OS 
       based routers. 
       
       Copyright 2014-2015 Alcatel-Lucent, 2016 Nokia. All rights reserved. 
       Reproduction of this document is authorized on the condition that the 
       foregoing copyright notice is included. 
       
       This alu-conf-router-lmp-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2017-01-27";

  grouping alu-conf-router-lmp-r13 {
    container lmp {
      presence
          "Configure Link Management Protocol";
      container gmpls-loopback-address {
        description
            "Configure the GMPLS loopback address";
        leaf ip-address {
          type inet:ip-address;
        } //ip-address

      } //container gmpls-loopback-address

      leaf shutdown {
        type boolean;
        description
            "Administratively enable/disable LMP";
      }

      list peer {
        key "peer-node-id";
        description
            "Configure LMP peer information";
        leaf peer-node-id {
          type string {
            length "1..15";
          }
          description
              "a.b.c.d|<1..4294967295>";
        } //peer-node-id

        container control-channel-router {
          description
              "Configure the router instance and GMPLS loopback address used by the peer's 
               control channels";
          leaf router-instance {
            type string {
              length "1..32";
            }
            default "Base";
            description
                "Attribute router-instance for control-channel-router";
          } //router-instance

          leaf gmpls-loopback-address {
            type inet:ip-address;
          } //gmpls-loopback-address

        } //container control-channel-router

        container peer-loopback-address {
          description
              "Configure the loopback address of the peer";
          leaf ip-address {
            type string;
            description
                "Attribute ip-address for peer-loopback-address";
          } //ip-address

        } //container peer-loopback-address

        container retransmission-interval {
          description
              "Configure the retransmission interval of the peer";
          leaf milliseconds {
            type uint32 {
              range "10..60000";
            }
            default 500;
            description
                "[10..60000] - Default: 500";
          } //milliseconds

        } //container retransmission-interval

        container retry-limit {
          description
              "Configure the retry limit of the peer";
          leaf limit {
            type uint32 {
              range "1..4294967295";
            }
            description
                "[1..4294967295]";
          } //limit

        } //container retry-limit

        leaf shutdown {
          type boolean;
          description
              "Administratively enable/disable the peer";
        }

        list te-link {
          key "te-link-id";
          description
              "Configure the TE link to the peer";
          leaf te-link-id {
            type string {
            }
            description
                "[1..4294967295]|<te-link-name>";
          } //te-link-id

        } //list te-link

        list control-channel {
          key "lmp-cc-id";
          description
              "Configure LMP peer control channel information";
          leaf lmp-cc-id {
            type uint32 {
              range "1..4294967295";
            }
          } //lmp-cc-id

          container hello {
            description
                "Configure the hello parameters of the control channel";
            leaf interval {
              type uint32 {
                range "1000..65535";
              }
              default 1000;
              description
                  "[1000..65535] - Default: 1000 milliseconds";
            } //interval

            leaf dead-interval {
              type uint32 {
                range "3000..65535";
              }
              default 4000;
              description
                  "[3000..65535] - Default: 4000 milliseconds";
            } //dead-interval

          } //container hello

          container peer-interface-address {
            description
                "Configure the peer interface address of the control channel";
            leaf ip-address {
              type string;
              description
                  "Attribute ip-address for peer-interface-address";
            } //ip-address

          } //container peer-interface-address

          container setup-role {
            description
                "Configure the setup role of the control channel";
            leaf active-passive {
              type enumeration {
                enum active;
                enum passive;
              }
              default "active";
              description
                  "keywords - Default: active";
            } //active-passive

          } //container setup-role

          leaf shutdown {
            type boolean;
            description
                "Administratively enable/disable the control channel";
          }

          container ttl {
            description
                "Configure the Time-To-Live (TTL) value used in the LMP and RSVP control packet 
                 IP header";
            leaf hops {
              type uint32 {
                range "1..255";
              }
              default 1;
              description
                  "[1..255] - Default: 1";
            } //hops

          } //container ttl

        } //list control-channel

      } //list peer

      list te-link {
        key "te-link-id";
        description
            "Configure LMP Traffic Engineering (TE) link information";
        leaf te-link-id {
          type string {
            length "1..32";
          }
          description
              "[1..4294967295]|<te-link-name>";
        } //te-link-id

        container link-name {
          description
              "Configure the name of the TE link";
          leaf te-link-name {
            type string {
              length "1..32";
            }
          } //te-link-name

        } //container link-name

        container remote-id {
          description
              "Configure the remote ID of the TE link";
          leaf id {
            type uint32 {
              range "1..4294967295";
            }
          } //id

        } //container remote-id

        leaf shutdown {
          type boolean;
          description
              "Administratively enable/disable the TE link";
        }

        list data-bearer {
          key "data-bearer-id";
          description
              "Configure Data Bearer (DB) link information";
          leaf data-bearer-id {
            type uint32 {
              range "1..4294967295";
            }
          } //data-bearer-id

          container port {
            description
                "Configure the port of the DB link";
            leaf port-id {
              type string;
              description
                  "slot/mda/port";
            } //port-id

          } //container port

          container remote-id {
            description
                "Configure the remote ID of the DB link";
            leaf id {
              type uint32 {
                range "1..4294967295";
              }
            } //id

          } //container remote-id

          leaf shutdown {
            type boolean;
            description
                "Administratively enable/disable the DB link";
          }

        } //list data-bearer

      } //list te-link

    } //container lmp

  } //grouping alu-conf-router-lmp-r13

} //module  alu-conf-router-lmp-r13
