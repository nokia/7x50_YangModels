module alu-conf-ip-except-r13 {
  yang-version "1";

  namespace "urn:alcatel-lucent.com:sros:ns:yang:conf-ip-except-r13";

  prefix "conf-ip-except-r13";

  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure an IP exception filter on SR OS 
       based routers. 
       
       Copyright 2014-2015 Alcatel-Lucent, 2016 Nokia. All rights reserved. 
       Reproduction of this document is authorized on the condition that the 
       foregoing copyright notice is included. 
       
       This alu-conf-ip-except-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2018-03-01";

  grouping alu-conf-ip-except-r13 {
    list ip-exception {
      key "filter-id";
      description
          "Configure an IP exception filter";
      leaf filter-id {
        type string;
        description
            "Attribute filter-id for ip-exception";
      } //filter-id

      container description {
        description
            "Description for this ip-exception";
        leaf description-string {
          type string {
            length "1..80";
          }
        } //description-string

      } //container description

      container filter-name {
        description
            "Configure a name for the exception";
        leaf filter-name {
          type string;
        } //filter-name

      } //container filter-name

      container renum {
        description
            "Renumber an entry";
        leaf old-entry-id {
          type uint32 {
            range "1..2097151";
          }
        } //old-entry-id

        leaf new-entry-id {
          type uint32 {
            range "1..2097151";
          }
        } //new-entry-id

      } //container renum

      container scope {
        description
            "Configure scope for this exception";
        leaf scope-id {
          type enumeration {
            enum exclusive;
            enum template;
            enum embedded;
          }
        } //scope-id

      } //container scope

      list entry {
        key "entry-id";
        description
            "Configure ip-exception entry";
        leaf entry-id {
          type uint32 {
            range "1..2097151";
          }
        } //entry-id

        container description {
          description
              "Description for this entry";
          leaf description-string {
            type string {
              length "1..80";
            }
          } //description-string

        } //container description

        container match {
          description
              "Configure match criteria for this ip exception entry";
          leaf protocol {
            type string;
            description
                "Attribute protocol-id for match";
          } //protocol

          container dst-ip {
            description
                "Configure destination IP match condition";
            leaf ip-address-mask {
              type inet:ip-prefix;
              description
                  "<ip-address>/<mask>";
            } //ip-address-mask

            leaf ip-address {
              type inet:ip-address;
              description
                  "Attribute ip-address for dst-ip";
            } //ip-address

            leaf ipv4-address-mask {
              type string;
              description
                  "a.b.c.d any address mask expressed as dotted quad [0..255]";
            } //ipv4-address-mask

          } //container dst-ip

          container dst-port {
            description
                "Configure destination port match condition";
            leaf lt-gt-eq {
              type enumeration {
                enum lt;
                enum gt;
                enum eq;
              }
              description
                  "operators";
            } //lt-gt-eq

            leaf dst-port-number {
              type string;
              description
                  "Attribute dst-port-number for dst-port";
            } //dst-port-number

            leaf-list range {
              type string;
              max-elements 2;
              description
                  "dst-port-number";
            } //range

          } //container dst-port

          container icmp-code {
            description
                "Configure ICMP code match condition";
            leaf icmp-code {
              type string;
              description
                  "Attribute icmp-code for icmp-code";
            } //icmp-code

          } //container icmp-code

          container icmp-type {
            description
                "Configure ICMP type match condition";
            leaf icmp-type {
              type string;
              description
                  "Attribute icmp-type for icmp-type";
            } //icmp-type

          } //container icmp-type

          container src-ip {
            description
                "Configure source ip match condition";
            leaf ip-address-mask {
              type inet:ip-prefix;
              description
                  "<ip-address>/<mask>";
            } //ip-address-mask

            leaf ip-address {
              type inet:ip-address;
              description
                  "Attribute ip-address for src-ip";
            } //ip-address

            leaf ipv4-address-netmask {
              type string;
              description
                  "a.b.c.d any address mask expressed as a dotted quad [0..255]";
            } //ipv4-address-netmask

          } //container src-ip

          container src-port {
            description
                "Configure source port match condition";
            leaf lt-gt-eq {
              type enumeration {
                enum lt;
                enum gt;
                enum eq;
              }
              description
                  "operators";
            } //lt-gt-eq

            leaf src-port-number {
              type string;
              description
                  "Attribute src-port-number for src-port";
            } //src-port-number

            leaf-list range {
              type string;
              max-elements 2;
              description
                  "src-port-number";
            } //range

          } //container src-port

        } //container match

      } //list entry

    } //list ip-exception

  } //grouping alu-conf-ip-except-r13

} //module  alu-conf-ip-except-r13
