module alu-conf-svc-template-r13 {
  yang-version "1";

  namespace "urn:alcatel-lucent.com:sros:ns:yang:conf-svc-template-r13";

  prefix "conf-svc-template-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure service templates on SR OS based 
       routers. 
       
       Copyright 2014-2015 Alcatel-Lucent, 2016 Nokia. All rights reserved. 
       Reproduction of this document is authorized on the condition that the 
       foregoing copyright notice is included. 
       
       This alu-conf-svc-template-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-05-30";

  grouping alu-conf-svc-template-r13 {
    container template {
      description
          "Configure service templates";
      list epipe-sap-template {
        key "name";
        description
            "Configure a template for Ether-Pipe Service SAP's";
        leaf name {
          type string;
        } //name

        container egress {
          description
              "Configuration for the egress direction";
          container qos {
            description
                "Configure the Quality of Service policy";
            leaf sap-egress-policy-id {
              type uint32 {
                range "1..65535";
              }
            } //sap-egress-policy-id

            leaf name {
              type string;
            } //name

          } //container qos

          container filter {
            presence
                "Configure filters";
            container ip {
              description
                  "Configure the IPv4 filter";
              leaf filter-id {
                type uint32 {
                  range "1..65535";
                }
              } //filter-id

            } //container ip

            container ipv6 {
              description
                  "Configure the IPv6 filter";
              leaf filter-id {
                type uint32 {
                  range "1..65535";
                }
              } //filter-id

            } //container ipv6

            container mac {
              description
                  "Configure the MAC filter";
              leaf filter-id {
                type uint32 {
                  range "1..65535";
                }
              } //filter-id

            } //container mac

          } //container filter

          container filter-name {
            presence
                "Apply egress filter names";
            container ip {
              description
                  "Configure the IPv4 filter";
              leaf name {
                type string;
              } //name

            } //container ip

            container ipv6 {
              description
                  "Configure the IPv6 filter";
              leaf name {
                type string;
              } //name

            } //container ipv6

            container mac {
              description
                  "Configure the MAC filter";
              leaf name {
                type string;
              } //name

            } //container mac

          } //container filter-name

        } //container egress

        container ingress {
          description
              "Configuration for the ingress direction";
          container qos {
            description
                "Configure the Quality of Service policy";
            leaf sap-ingress-policy-id {
              type uint32 {
                range "1..65535";
              }
            } //sap-ingress-policy-id

            leaf name {
              type string;
            } //name

            leaf shared-queuing {
              type enumeration {
                enum shared-queuing;
                enum multipoint-shared;
              }
            } //shared-queuing

          } //container qos

          container filter {
            presence
                "Configure filters";
            container ip {
              description
                  "Configure the IPv4 filter";
              leaf filter-id {
                type uint32 {
                  range "1..65535";
                }
              } //filter-id

            } //container ip

            container ipv6 {
              description
                  "Configure the IPv6 filter";
              leaf filter-id {
                type uint32 {
                  range "1..65535";
                }
              } //filter-id

            } //container ipv6

            container mac {
              description
                  "Configure the MAC filter";
              leaf filter-id {
                type uint32 {
                  range "1..65535";
                }
              } //filter-id

            } //container mac

          } //container filter

          container filter-name {
            presence
                "Apply ingress filter names";
            container ip {
              description
                  "Configure the IPv4 filter";
              leaf name {
                type string;
              } //name

            } //container ip

            container ipv6 {
              description
                  "Configure the IPv6 filter";
              leaf name {
                type string;
              } //name

            } //container ipv6

            container mac {
              description
                  "Configure the MAC filter";
              leaf name {
                type string;
              } //name

            } //container mac

          } //container filter-name

        } //container ingress

      } //list epipe-sap-template

      list vpls-sap-template {
        key "name";
        description
            "Provision a SAP template";
        leaf name {
          type string;
        } //name

        container bpdu-translation {
          description
              "Configure the bpdu translation on this SAP template";
          leaf bpdu-translation-id {
            type enumeration {
              enum auto;
              enum auto-rw;
              enum pvst;
              enum pvst-rw;
              enum stp;
            }
          } //bpdu-translation-id

        } //container bpdu-translation

        leaf collect-stats {
          type boolean;
          description
              "Enable/disable statistics collection";
        }

        container cpu-protection {
          description
              "Configure CPU protection";
          leaf policy-id {
            type uint32 {
              range "1..255";
            }
          } //policy-id

          leaf mac-monitoring {
            type boolean;
            description
                "keyword - enable MAC monitoring";
          } //mac-monitoring

          leaf eth-cfm-monitoring {
            type boolean;
            description
                "keyword - enable Ethernet Connectivity Fault Management monitoring";
          } //eth-cfm-monitoring

          leaf aggregate {
            type boolean;
            description
                "keyword - apply the rate limit to the sum of the per peer packet rates";
          } //aggregate

          leaf car {
            type boolean;
            description
                "keyword - Committed Access Rate - ignore Eth-CFM packets when enforcing 
                 overall-rate";
          } //car

        } //container cpu-protection

        leaf disable-aging {
          type boolean;
          description
              "Enable/disable aging of MAC addresses";
        }

        leaf disable-learning {
          type boolean;
          description
              "Enable/disable learning of new MAC addresses";
        }

        leaf discard-unknown-source {
          type boolean;
          description
              "Enable/disable discarding of frames with unknown source MAC address";
        }

        container dist-cpu-protection {
          description
              "Configure Distributed CPU protection";
          leaf policy-name {
            type string;
          } //policy-name

        } //container dist-cpu-protection

        container l2pt-termination {
          description
              "Configure L2PT termination on this SAP template";
          leaf cdp {
            type boolean;
            description
                "keyword - cisco discovery protocol";
          } //cdp

          leaf dtp {
            type boolean;
            description
                "keyword - dynamic trunking protocol";
          } //dtp

          leaf pagp {
            type boolean;
            description
                "keyword - port aggregation protocol";
          } //pagp

          leaf stp {
            type boolean;
            description
                "keyword - all spanning tree protocols: stp, rstp, mstp, pvst (default)";
          } //stp

          leaf udld {
            type boolean;
            description
                "keyword - unidirectional link detection";
          } //udld

          leaf vtp {
            type boolean;
            description
                "keyword - virtual trunk protocol";
          } //vtp

        } //container l2pt-termination

        container limit-mac-move {
          description
              "Configure limit mac move";
          leaf blockable-non-blockable {
            type enumeration {
              enum blockable;
              enum non-blockable;
            }
          } //blockable-non-blockable

        } //container limit-mac-move

        container mac-move-level {
          description
              "Configure limit-mac-move level";
          leaf mac-move-level-id {
            type enumeration {
              enum primary;
              enum secondary;
              enum tertiary;
            }
          } //mac-move-level-id

        } //container mac-move-level

        container max-nbr-mac-addr {
          description
              "Configure the maximum number of MAC entries in the FDB from this SAP";
          leaf table-size {
            type uint32 {
              range "1..511999";
            }
          } //table-size

        } //container max-nbr-mac-addr

        container egress {
          description
              "Configure egress policies";
          container filter {
            description
                "Apply egress filter";
            leaf ip {
              type uint32 {
                range "1..65535";
              }
            } //ip

            leaf mac {
              type uint32 {
                range "1..65535";
              }
              description
                  "filter-id";
            } //mac

            leaf ipv6 {
              type uint32 {
                range "1..65535";
              }
              description
                  "filter-id";
            } //ipv6

          } //container filter

          container policer-control-policy {
            description
                "Specify policer control policy";
            leaf policy-name {
              type string {
                length "1..32";
              }
            } //policy-name

          } //container policer-control-policy

          leaf qinq-mark-top-only {
            type boolean;
            description
                "Mark p-bits on top q-tag only";
          }

          container qos {
            description
                "Apply egress qos policy";
            leaf sap-egress-policy-id {
              type uint32 {
                range "1..65535";
              }
            } //sap-egress-policy-id

            leaf name {
              type string;
            } //name

          } //container qos

          container scheduler-policy {
            description
                "Specify a scheduler-policy";
            leaf scheduler-policy-name {
              type string {
                length "1..32";
              }
            } //scheduler-policy-name

          } //container scheduler-policy

          container agg-rate {
            presence
                "Configure aggregate rate limit";
            leaf limit-unused-bandwidth {
              type boolean;
              description
                  "Specify whether to enable limit unused bandwidth";
            }

            leaf queue-frame-based-accounting {
              type boolean;
              description
                  "Specify whether to enable queue frame based accounting";
            }

            container rate {
              description
                  "Specify rate limit for agg-rate";
              leaf kilobits-per-second {
                type string;
                description
                    "[1..6400000000|max] Kbps";
              } //kilobits-per-second

            } //container rate

          } //container agg-rate

          container filter-name {
            presence
                "Apply egress filter names";
            container ip {
              description
                  "Configure the IPv4 filter";
              leaf name {
                type string;
              } //name

            } //container ip

            container ipv6 {
              description
                  "Configure the IPv6 filter";
              leaf name {
                type string;
              } //name

            } //container ipv6

            container mac {
              description
                  "Configure the MAC filter";
              leaf name {
                type string;
              } //name

            } //container mac

          } //container filter-name

        } //container egress

        container eth-cfm {
          description
              "Configure CFM parameters";
          leaf mip {
            type boolean;
            description
                "Enable/Disable Maintenance Intermediate Points";
          }

          container squelch-ingress-levels {
            description
                "Configure the level(s) of the ETH-CFM PDUs that will be silently discarded";
            leaf t0 {
              type boolean;
              description
                  "[0..7]";
            } //t0

            leaf t1 {
              type boolean;
            } //t1

            leaf t2 {
              type boolean;
            } //t2

            leaf t3 {
              type boolean;
            } //t3

            leaf t4 {
              type boolean;
            } //t4

            leaf t5 {
              type boolean;
            } //t5

            leaf t6 {
              type boolean;
            } //t6

            leaf t7 {
              type boolean;
            } //t7

          } //container squelch-ingress-levels

        } //container eth-cfm

        container ingress {
          description
              "Configure ingress policies";
          container filter {
            description
                "Apply ingress filter";
            leaf ip {
              type uint32 {
                range "1..65535";
              }
            } //ip

            leaf mac {
              type uint32 {
                range "1..65535";
              }
              description
                  "filter-id";
            } //mac

            leaf ipv6 {
              type uint32 {
                range "1..65535";
              }
              description
                  "filter-id";
            } //ipv6

          } //container filter

          container match-qinq-dot1p {
            description
                "Define 802.1P bits to match in QinQ SAP's";
            leaf top-bottom {
              type enumeration {
                enum top;
                enum bottom;
              }
            } //top-bottom

          } //container match-qinq-dot1p

          container policer-control-policy {
            description
                "Specify policer control policy";
            leaf policy-name {
              type string {
                length "1..32";
              }
            } //policy-name

          } //container policer-control-policy

          container qos {
            description
                "Apply ingress qos policy";
            leaf policy-id {
              type uint32 {
                range "1..65535";
              }
            } //policy-id

            leaf name {
              type string;
            } //name

            leaf shared-queuing-multipoint-shared {
              type enumeration {
                enum shared-queuing;
                enum multipoint-shared;
              }
              description
                  "keywords";
            } //shared-queuing-multipoint-shared

          } //container qos

          container scheduler-policy {
            description
                "Specify a scheduler-policy";
            leaf scheduler-policy-name {
              type string {
                length "1..32";
              }
            } //scheduler-policy-name

          } //container scheduler-policy

          container filter-name {
            presence
                "Apply ingress filter names";
            container ip {
              description
                  "Configure the IPv4 filter";
              leaf name {
                type string;
              } //name

            } //container ip

            container ipv6 {
              description
                  "Configure the IPv6 filter";
              leaf name {
                type string;
              } //name

            } //container ipv6

            container mac {
              description
                  "Configure the MAC filter";
              leaf name {
                type string;
              } //name

            } //container mac

          } //container filter-name

        } //container ingress

        container stp {
          description
              "Configure spanning tree protocol parameters";
          leaf auto-edge {
            type boolean;
            description
                "Enable/disable automatic detection of edge port";
          }

          leaf edge-port {
            type boolean;
            description
                "Configure sap as edge or non-edge port";
          }

          list link-type {
            key "pt-pt-shared";
            description
                "Configure link type of the sap";
            leaf pt-pt-shared {
              type enumeration {
                enum pt-pt;
                enum shared;
              }
              description
                  "link type";
            } //pt-pt-shared

          } //list link-type

          list path-cost {
            key "sap-path-cost";
            description
                "Configure path-cost";
            leaf sap-path-cost {
              type uint32 {
                range "1..200000000";
              }
            } //sap-path-cost

          } //list path-cost

          list priority {
            key "stp-priority";
            description
                "Configure stp priority";
            leaf stp-priority {
              type uint32 {
                range "0..255";
              }
            } //stp-priority

          } //list priority

          leaf root-guard {
            type boolean;
            description
                "Enable/disable STP root-guard";
          }

          leaf shutdown {
            type boolean;
            description
                "Enable/disable spanning tree protocol";
          }

        } //container stp

      } //list vpls-sap-template

      list vpls-template {
        key "name";
        description
            "Provision a Virtual Private LAN Service template";
        leaf name {
          type string;
        } //name

        container customer {
          description
              "Configure customer identifier";
          leaf customer-id {
            type uint32 {
              range "1..2147483647";
            }
          } //customer-id

        } //container customer

        leaf disable-aging {
          type boolean;
          description
              "Enable/disable aging of MAC addresses";
        }

        leaf disable-learning {
          type boolean;
          description
              "Enable/disable learning of new MAC addresses";
        }

        leaf discard-unknown {
          type boolean;
          description
              "Enable/disable discarding of packets with unknown destination mac addresses";
        }

        list fdb-table-high-wmark {
          key "high-water-mark";
          description
              "Configure the high watermark for the FDB table";
          leaf high-water-mark {
            type uint32 {
              range "0..100";
            }
          } //high-water-mark

        } //list fdb-table-high-wmark

        list fdb-table-low-wmark {
          key "low-water-mark";
          description
              "Configure the low watermark for the FDB table";
          leaf low-water-mark {
            type uint32 {
              range "0..100";
            }
          } //low-water-mark

        } //list fdb-table-low-wmark

        list fdb-table-size {
          key "table-size";
          description
              "Configure the maximum number of MAC entries in the FDB";
          leaf table-size {
            type uint32 {
              range "1..511999";
            }
          } //table-size

        } //list fdb-table-size

        list local-age {
          key "aging-timer";
          description
              "Configure aging time for locally learned mac addresses";
          leaf aging-timer {
            type uint32 {
              range "60..86400";
            }
          } //aging-timer

        } //list local-age

        list remote-age {
          key "aging-timer";
          description
              "Configure aging time for remotely learned mac addresses";
          leaf aging-timer {
            type uint32 {
              range "60..86400";
            }
          } //aging-timer

        } //list remote-age

        container service-mtu {
          description
              "Configure service MTU";
          leaf octets {
            type uint32 {
              range "1..9782";
            }
          } //octets

        } //container service-mtu

        container temp-flooding {
          description
              "Configure temporary flooding";
          leaf temp-flooding-id {
            type uint32 {
              range "3..600";
            }
          } //temp-flooding-id

        } //container temp-flooding

        container load-balancing {
          description
              "Configure load balancing information";
          leaf per-service-hashing {
            type boolean;
            description
                "Enable/disable per service hashing";
          }

          leaf spi-load-balancing {
            type boolean;
            description
                "Enable/disable SPI load balancing";
          }

          leaf teid-load-balancing {
            type boolean;
            description
                "Enable/disable TEID load balancing";
          }

        } //container load-balancing

        container mac-move {
          presence
              "Configure Mac Move and its attributes";
          container move-frequency {
            description
                "Configure move frequency to be used";
            leaf frequency {
              type uint64 {
                range "1..10";
              }
            } //frequency

          } //container move-frequency

          container number-retries {
            description
                "Configure number of retries for reenabling";
            leaf number-retries {
              type uint32 {
                range "0..255";
              }
              description
                  "[0..255] - 0 for unlimited";
            } //number-retries

          } //container number-retries

          container retry-timeout {
            description
                "Configure retry timeout to be used";
            leaf timeout {
              type uint64 {
                range "0..600";
              }
            } //timeout

          } //container retry-timeout

          leaf shutdown {
            type boolean;
            description
                "Administratively enable/disable mac-move";
          }

          container primary-ports {
            description
                "Configure primary-ports for this service";
            container cumulative-factor {
              description
                  "mac-relearn periods to be used for mac-relearn rate";
              leaf cumulative-factor {
                type int32 {
                  range "3..10";
                }
              } //cumulative-factor

            } //container cumulative-factor

          } //container primary-ports

          container secondary-ports {
            description
                "Configure secondary-ports for this service";
            container cumulative-factor {
              description
                  "mac-relearn periods to be used for mac-relearn rate";
              leaf cumulative-factor {
                type int32 {
                  range "2..9";
                }
              } //cumulative-factor

            } //container cumulative-factor

          } //container secondary-ports

        } //container mac-move

        container stp {
          description
              "Configure STP parameters";
          list forward-delay {
            key "forward-delay";
            description
                "Configure forward-delay";
            leaf forward-delay {
              type uint32 {
                range "4..30";
              }
            } //forward-delay

          } //list forward-delay

          list hello-time {
            key "hello-time";
            description
                "Configure hello-time";
            leaf hello-time {
              type uint32 {
                range "1..10";
              }
            } //hello-time

          } //list hello-time

          container hold-count {
            description
                "Configure BPDU txmit hold count";
            leaf BPDU-tx-hold-count {
              type uint32 {
                range "1..20";
              }
            } //BPDU-tx-hold-count

          } //container hold-count

          list max-age {
            key "max-age";
            description
                "Configure maximum info age for the stp";
            leaf max-age {
              type uint32 {
                range "6..40";
              }
            } //max-age

          } //list max-age

          container mode {
            description
                "Configure protocol version";
            leaf rstp-comp-dot1w-dot1w-mstp-pmstp {
              type enumeration {
                enum rstp;
                enum comp-dot1w;
                enum dot1w;
                enum mstp;
                enum pmstp;
              }
              description
                  "protocol version";
            } //rstp-comp-dot1w-dot1w-mstp-pmstp

          } //container mode

          list priority {
            key "bridge-priority";
            description
                "Configure bridge priority for the stp";
            leaf bridge-priority {
              type uint32 {
                range "0..65535";
              }
            } //bridge-priority

          } //list priority

          leaf shutdown {
            type boolean;
            description
                "Enable/disable spanning tree protocol";
          }

        } //container stp

      } //list vpls-template

    } //container template

  } //grouping alu-conf-svc-template-r13

} //module  alu-conf-svc-template-r13
