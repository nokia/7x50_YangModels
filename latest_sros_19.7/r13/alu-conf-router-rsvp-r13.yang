module alu-conf-router-rsvp-r13 {
  yang-version "1";

  namespace "urn:alcatel-lucent.com:sros:ns:yang:conf-router-rsvp-r13";

  prefix "conf-router-rsvp-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure RSVP on SR OS based routers. 
       
       Copyright 2014-2015 Alcatel-Lucent, 2016 Nokia. All rights reserved. 
       Reproduction of this document is authorized on the condition that the 
       foregoing copyright notice is included. 
       
       This alu-conf-router-rsvp-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2018-11-06";

  grouping alu-conf-router-rsvp-r13 {
    container rsvp {
      presence
          "Configure RSVP";
      leaf entropy-label-capability {
        type boolean;
        description
            "Enable/disable the entropy label capability on RSVP instance";
      }

      container gr-helper-time {
        description
            "Configure restart and recovery interval";
        leaf max-recovery {
          type uint32 {
            range "1..1800";
          }
          default 300;
          description
              "[1..1800] seconds";
        } //max-recovery

        leaf max-restart {
          type uint32 {
            range "1..300";
          }
          default 120;
          description
              "[1..300] seconds";
        } //max-restart

      } //container gr-helper-time

      leaf graceful-shutdown {
        type boolean;
        description
            "Enable/disable the graceful shutdown on RSVP instance";
      }

      leaf implicit-null-label {
        type boolean;
        description
            "Enable/disable signalling of implicit null values for all LSPs";
      }

      container keep-multiplier {
        description
            "Keep-multiplier used to declare a reservation or neighbor as down";
        leaf number {
          type uint16 {
            range "1..255";
          }
        } //number

      } //container keep-multiplier

      container node-id-in-rro {
        description
            "Include/Exclude node-id sub-object in RRO on RSVP instance";
        leaf node-id-in-rro-id {
          type enumeration {
            enum include;
            enum exclude;
          }
        } //node-id-in-rro-id

      } //container node-id-in-rro

      container p2mp-merge-point-abort-timer {
        description
            "Configure merge pointer timer for P2MP S2L paths";
        leaf seconds {
          type uint32 {
            range "1..65535";
          }
        } //seconds

      } //container p2mp-merge-point-abort-timer

      container p2p-merge-point-abort-timer {
        description
            "Configure merge pointer timer for P2P paths";
        leaf seconds {
          type uint32 {
            range "1..65535";
          }
        } //seconds

      } //container p2p-merge-point-abort-timer

      container preemption-timer {
        description
            "Configure the preemption timer for the MPLS instance";
        leaf seconds {
          type uint32 {
            range "0..1800";
          }
        } //seconds

      } //container preemption-timer

      container rapid-retransmit-time {
        description
            "Configure rapid retransmission interval for reliable delivery of RSVP messages";
        leaf hundred-milliseconds {
          type uint32 {
            range "1..100";
          }
        } //hundred-milliseconds

      } //container rapid-retransmit-time

      container rapid-retry-limit {
        description
            "Configure rapid retry limit for reliable delivery of RSVP messages";
        leaf limit {
          type uint32 {
            range "1..6";
          }
        } //limit

      } //container rapid-retry-limit

      container refresh-reduction-over-bypass {
        description
            "Enable/Disable refresh reduction capabilities over all bypass tunnels";
        leaf enable-disable {
          type enumeration {
            enum enable;
            enum disable;
          }
          description
              "keywords";
        } //enable-disable

      } //container refresh-reduction-over-bypass

      container refresh-time {
        description
            "Interval between successive Path refresh Resv refresh and Srefresh messages";
        leaf seconds {
          type uint32 {
            range "1..65535";
          }
        } //seconds

      } //container refresh-time

      leaf shutdown {
        type boolean;
        description
            "Administratively enable/disable the RSVP instance";
      }

      container te-down-threshold {
        description
            "Configure down threshold levels for IGP TE update";
        leaf-list threshold-level {
          type int32 {
            range "0..100";
          }
          max-elements 16;
          description
              "percent";
        } //threshold-level

      } //container te-down-threshold

      container te-up-threshold {
        description
            "Configure up threshold levels for IGP TE update";
        leaf-list threshold-level {
          type int32 {
            range "0..100";
          }
          max-elements 16;
          description
              "percent";
        } //threshold-level

      } //container te-up-threshold

      container dbw-accounting {
        presence
            "Enable/Disable Dark Bandwidth accounting for RSVP.";
        container dbw-multiplier {
          description
              "Configure the Dark Bandwidth multiplier.";
          leaf percent {
            type uint32 {
              range "0..1000";
            }
            description
                "[0..1000]";
          } //percent

        } //container dbw-multiplier

        container down-threshold {
          description
              "Configure down threshold for Dark Bandwidth.";
          leaf percent {
            type uint32 {
              range "0..100";
            }
            description
                "[0..100]";
          } //percent

          leaf bw {
            type uint32 {
              range "0..1000000";
            }
            description
                "[0..1000000]";
          } //bw

        } //container down-threshold

        container sample-interval {
          description
              "Configure the Dark Bandwidth sample interval.";
          leaf seconds {
            type uint32 {
              range "10..600";
            }
          } //seconds

        } //container sample-interval

        container sample-multiplier {
          description
              "Configure the Dark Bandwidth sample multiplier.";
          leaf sample-multiplier {
            type uint32 {
              range "1..10";
            }
            default 3;
          } //sample-multiplier

        } //container sample-multiplier

        container up-threshold {
          description
              "Configure up threshold for Dark Bandwidth.";
          leaf percent {
            type uint32 {
              range "0..100";
            }
            description
                "[0..100]";
          } //percent

          leaf bw {
            type uint32 {
              range "0..1000000";
            }
            description
                "[0..1000000]";
          } //bw

        } //container up-threshold

      } //container dbw-accounting

      container diffserv-te {
        description
            "Configure parameters for Diffserv TE";
        leaf mam---rdm {
          type enumeration {
            enum mam;
            enum rdm;
          }
          description
              "keywords";
        } //mam---rdm

        container class-type-bw {
          description
              "Configure bandwidth percent for class type";
          leaf ct0 {
            type uint32 {
              range "0..100";
            }
          } //ct0

          leaf ct1 {
            type uint32 {
              range "0..100";
            }
          } //ct1

          leaf ct2 {
            type uint32 {
              range "0..100";
            }
          } //ct2

          leaf ct3 {
            type uint32 {
              range "0..100";
            }
          } //ct3

          leaf ct4 {
            type uint32 {
              range "0..100";
            }
          } //ct4

          leaf ct5 {
            type uint32 {
              range "0..100";
            }
          } //ct5

          leaf ct6 {
            type uint32 {
              range "0..100";
            }
          } //ct6

          leaf ct7 {
            type uint32 {
              range "0..100";
            }
          } //ct7

        } //container class-type-bw

        list fc {
          key "fc-name";
          description
              "Configure fc name to ct-number mapping";
          leaf fc-name {
            type enumeration {
              enum be;
              enum l2;
              enum af;
              enum l1;
              enum h2;
              enum ef;
              enum h1;
              enum nc;
            }
          } //fc-name

          leaf class-type {
            type uint16 {
              range "0..7";
            }
          } //class-type

        } //list fc

        list te-class {
          key "te-class-number";
          description
              "Configure TE Class";
          leaf te-class-number {
            type uint16;
            description
                "[0..7]";
          } //te-class-number

          leaf class-type {
            type uint16 {
              range "0..7";
            }
          } //class-type

          leaf priority {
            type uint16;
            description
                "[0..7]";
          } //priority

        } //list te-class

      } //container diffserv-te

      list interface {
        key "ip-int-name";
        description
            "Configure RSVP on an IP interface";
        leaf ip-int-name {
          type string {
            length "1..32";
          }
        } //ip-int-name

        container auth-keychain {
          description
              "Configure TCP authentication keychain to use for the session";
          leaf name {
            type string {
              length "1..32";
            }
            description
                "keychain-name (32 char max)";
          } //name

        } //container auth-keychain

        container authentication-key {
          description
              "Configure the authentication key used between RSVP neighbours to authenticate 
               RSVP messages";
          leaf authentication-key-hash-key {
            type string {
              length "1..500";
            }
            description
                "authentication-key - [16 chars max] 
                 hash-key 
                 hash2-key 
                 custom-key";
          } //authentication-key-hash-key

          leaf hash-hash2-custom {
            type enumeration {
              enum hash;
              enum hash2;
              enum custom;
            }
            description
                "keywords - specify hashing scheme";
          } //hash-hash2-custom

        } //container authentication-key

        leaf bfd-enable {
          type boolean;
          description
              "Enable BFD";
        }

        container class-type-bw {
          description
              "Configure bandwidth percent for class type";
          leaf ct0 {
            type uint32 {
              range "0..100";
            }
          } //ct0

          leaf ct1 {
            type uint32 {
              range "0..100";
            }
          } //ct1

          leaf ct2 {
            type uint32 {
              range "0..100";
            }
          } //ct2

          leaf ct3 {
            type uint32 {
              range "0..100";
            }
          } //ct3

          leaf ct4 {
            type uint32 {
              range "0..100";
            }
          } //ct4

          leaf ct5 {
            type uint32 {
              range "0..100";
            }
          } //ct5

          leaf ct6 {
            type uint32 {
              range "0..100";
            }
          } //ct6

          leaf ct7 {
            type uint32 {
              range "0..100";
            }
          } //ct7

        } //container class-type-bw

        container dbw-down-threshold {
          description
              "Configure Dark Bandwidth down change threshold for RSVP Interface.";
          leaf percent {
            type uint32 {
              range "0..100";
            }
          } //percent

          leaf bw {
            type uint32 {
              range "0..1000000";
            }
          } //bw

        } //container dbw-down-threshold

        container dbw-multiplier {
          description
              "Configure the Dark Bandwidth multiplier.";
          leaf percent {
            type uint32 {
              range "0..1000";
            }
          } //percent

        } //container dbw-multiplier

        container dbw-up-threshold {
          description
              "Configure Dark Bandwidth up change threshold for RSVP Interface.";
          leaf percent {
            type uint32 {
              range "0..100";
            }
          } //percent

          leaf bw {
            type uint32 {
              range "0..1000000";
            }
          } //bw

        } //container dbw-up-threshold

        container gr-helper {
          description
              "Enable/Disable gr-helper";
          leaf enable-disable {
            type enumeration {
              enum enable;
              enum disable;
            }
            description
                "keywords";
          } //enable-disable

        } //container gr-helper

        leaf graceful-shutdown {
          type boolean;
          description
              "Enable/disable the graceful shutdown on RSVP interface";
        }

        container hello-interval {
          description
              "Configure time interval between RSVP hello messages";
          leaf milli-seconds {
            type uint32 {
              range "0..60000";
            }
            description
                "[0..60000] - only multiples of 1000 allowed";
          } //milli-seconds

        } //container hello-interval

        container implicit-null-label {
          description
              "Enable/disable signalling of implicit null label to all LSPs";
          leaf enable-disable {
            type enumeration {
              enum enable;
              enum disable;
            }
            description
                "keyword";
          } //enable-disable

        } //container implicit-null-label

        leaf shutdown {
          type boolean;
          description
              "Administratively enable/disable RSVP on the interface";
        }

        container subscription {
          description
              "Configure the percentage of the link bandwidth to use for reservation";
          leaf percentage {
            type uint32 {
              range "0..1000";
            }
          } //percentage

        } //container subscription

        container te-down-threshold {
          description
              "Configure down threshold levels for IGP TE update";
          leaf-list threshold-level {
            type int32 {
              range "0..100";
            }
            max-elements 16;
            description
                "percent";
          } //threshold-level

        } //container te-down-threshold

        container te-up-threshold {
          description
              "Configure up threshold levels for IGP TE update";
          leaf-list threshold-level {
            type int32 {
              range "0..100";
            }
            max-elements 16;
            description
                "percent";
          } //threshold-level

        } //container te-up-threshold

        container refresh-reduction {
          presence
              "Enable/Disable RSVP overhead refresh reduction capabilities on this interface";
          leaf reliable-delivery {
            type boolean;
            description
                "Enable/Disable reliable delivery of RSVP messages over the RSVP interface";
          }

        } //container refresh-reduction

      } //list interface

      container msg-pacing {
        presence
            "Enable/disable RSVP message pacing";
        container max-burst {
          description
              "Configure max number of RSVP messages that can be sent over a specified period 
               when message pacing is enabled";
          leaf number {
            type string;
            description
                "[100..1000] - only multiples of 10 allowed";
          } //number

        } //container max-burst

        container period {
          description
              "Configure period for RSVP message pacing";
          leaf milli-seconds {
            type string;
            description
                "[100..1000] - only multiples of 10 allowed";
          } //milli-seconds

        } //container period

      } //container msg-pacing

      container te-threshold-update {
        presence
            "Enable or disable threshold based IGP TE updates";
        leaf on-cac-failure {
          type boolean;
          description
              "Enable or disable connection admission control failure triggered IGP update";
        }

        container update-timer {
          description
              "Configure timer based IGP updates";
          leaf seconds {
            type uint32 {
              range "0..300";
            }
            default 0;
            description
                "[0..300]";
          } //seconds

        } //container update-timer

      } //container te-threshold-update

    } //container rsvp

  } //grouping alu-conf-router-rsvp-r13

} //module  alu-conf-router-rsvp-r13
