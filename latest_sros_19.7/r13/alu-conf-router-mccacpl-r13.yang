module alu-conf-router-mccacpl-r13 {
  yang-version "1";

  namespace "urn:alcatel-lucent.com:sros:ns:yang:conf-router-mccacpl-r13";

  prefix "conf-router-mccacpl-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure Multicast CAC on SR OS based 
       routers. 
       
       Copyright 2014-2015 Alcatel-Lucent, 2016 Nokia. All rights reserved. 
       Reproduction of this document is authorized on the condition that the 
       foregoing copyright notice is included. 
       
       This alu-conf-router-mccacpl-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2017-10-03";

  grouping alu-conf-router-mccacpl-r13 {
    container mcac {
      description
          "Configure Multicast CAC";
      list if-policy {
        key "if-policy-name";
        description
            "Enable/disable multicast CAC interface-policy";
        leaf if-policy-name {
          type string {
            length "1..32";
          }
        } //if-policy-name

        container description {
          description
              "Add/remove description for MCAC interface-policy";
          leaf description-string {
            type string {
              length "1..80";
            }
          } //description-string

        } //container description

        leaf shutdown {
          type boolean;
          description
              "Administratively enable/disable the MCAC interface-policy";
        }

        container unconstrained-bw {
          description
              "Configure unconstrained-bw for MCAC interface-policy";
          leaf bandwidth-in-kbps {
            type int32 {
              range "0..2147483647";
            }
          } //bandwidth-in-kbps

          leaf mandatory-bw {
            type int32 {
              range "0..2147483647";
            }
          } //mandatory-bw

        } //container unconstrained-bw

      } //list if-policy

      list policy {
        key "policy-name";
        description
            "Enable/disable multicast CAC policy";
        leaf policy-name {
          type string {
            length "1..32";
          }
          description
              "max 32 chars";
        } //policy-name

        container default-action {
          description
              "Accept/discard default-action for mcac-policy";
          leaf default-action-id {
            type enumeration {
              enum accept;
              enum discard;
            }
          } //default-action-id

        } //container default-action

        container description {
          description
              "Add/remove description for mcac policy";
          leaf description {
            type string {
              length "1..80";
            }
            description
                "max 80 chars";
          } //description

        } //container description

        list bundle {
          key "bundle-name";
          description
              "Add/remove bundle for mcac policy (maximum of 64 unique bundles can be 
               specified)";
          leaf bundle-name {
            type string {
              length "1..32";
            }
            description
                "max 32 chars";
          } //bundle-name

          container bandwidth {
            description
                "Configure mcac policy bundle maximum bandwidth";
            leaf bandwidth-in-kbps {
              type uint32 {
                range "1..4294967295";
              }
            } //bandwidth-in-kbps

          } //container bandwidth

          list channel {
            key "start-address end-address source";
            description
                "Add/remove mc-group address as a channel within a bundle";
            leaf start-address {
              type string;
              description
                  "Attribute start-address for channel";
            } //start-address

            leaf end-address {
              type string;
              description
                  "Attribute end-address for channel";
            } //end-address

            leaf bw {
              type uint32 {
                range "10..10000000";
              }
            } //bw

            leaf class {
              type enumeration {
                enum high;
                enum low;
              }
            } //class

            leaf type {
              type enumeration {
                enum mandatory;
                enum optional;
              }
            } //type

            leaf source {
              type string {
                length "1..64";
              }
              description
                  "Attribute prefix/prefix-length for channel";
            } //source

          } //list channel

          container description {
            description
                "Add/remove description for bundle";
            leaf description {
              type string {
                length "1..80";
              }
              description
                  "max 80 chars";
            } //description

          } //container description

          leaf shutdown {
            type boolean;
            description
                "Administratively enable/disable bundle";
          }

          container mc-constraints {
            description
                "Create context that allows for the configuration of the different levels and 
                 their associated bandwidth for either a bundle or a logical interface";
            list lag-port-down {
              key "lag-id number-down";
              description
                  "enable/disable lag port down";
              leaf lag-id {
                type string;
                description
                    "Attribute lag-id for lag-port-down";
              } //lag-id

              leaf number-down {
                type string;
                description
                    "Attribute number-lag-port-down for lag-port-down";
              } //number-down

              leaf level {
                type uint32 {
                  range "1..8";
                }
              } //level

            } //list lag-port-down

            list level {
              key "level";
              description
                  "set or reset amount of BW available within a given bundle for MC traffic for a 
                   specified level";
              leaf level {
                type uint32 {
                  range "1..8";
                }
              } //level

              leaf bw {
                type uint32 {
                  range "0..2147483647";
                }
              } //bw

            } //list level

            leaf use-lag-port-weight {
              type boolean;
              description
                  "Enable/disable using the LAG port weight while calculating Multicast CAC 
                   constraints";
            }

          } //container mc-constraints

        } //list bundle

      } //list policy

    } //container mcac

  } //grouping alu-conf-router-mccacpl-r13

} //module  alu-conf-router-mccacpl-r13
