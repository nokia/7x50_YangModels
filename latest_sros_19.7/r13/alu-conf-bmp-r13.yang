module alu-conf-bmp-r13 {
  yang-version "1";

  namespace "urn:alcatel-lucent.com:sros:ns:yang:conf-bmp-r13";

  prefix "conf-bmp-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure BGP Monitoring Protocol (BMP) 
       Parameters on SR OS based routers. 
       
       Copyright 2014-2015 Alcatel-Lucent, 2016 Nokia. All rights reserved. 
       Reproduction of this document is authorized on the condition that the 
       foregoing copyright notice is included. 
       
       This alu-conf-bmp-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-05-13";

  grouping alu-conf-bmp-r13 {
    container bmp {
      description
          "Configure BGP Monitoring Protocol (BMP) Parameters";
      leaf shutdown {
        type boolean;
        description
            "Administratively enable/disable BMP";
      }

      list station {
        key "station-name";
        description
            "Configure a BMP monitoring station";
        leaf station-name {
          type string {
            length "1..32";
          }
        } //station-name

        container description {
          description
              "Description for the BMP station";
          leaf description-string {
            type string {
              length "1..80";
            }
          } //description-string

        } //container description

        container family {
          description
              "Which address families are reported";
          leaf ipv4 {
            type boolean;
          } //ipv4

          leaf ipv6 {
            type boolean;
          } //ipv6

          leaf label-ipv4 {
            type boolean;
          } //label-ipv4

          leaf label-ipv6 {
            type boolean;
          } //label-ipv6

          leaf mcast-ipv4 {
            type boolean;
          } //mcast-ipv4

          leaf mcast-ipv6 {
            type boolean;
          } //mcast-ipv6

          leaf vpn-ipv4 {
            type boolean;
          } //vpn-ipv4

          leaf vpn-ipv6 {
            type boolean;
          } //vpn-ipv6

          leaf mcast-vpn-ipv4 {
            type boolean;
          } //mcast-vpn-ipv4

          leaf mcast-vpn-ipv6 {
            type boolean;
          } //mcast-vpn-ipv6

          leaf evpn {
            type boolean;
          } //evpn

          leaf l2-vpn {
            type boolean;
          } //l2-vpn

        } //container family

        container initiation-message {
          description
              "Human-readable text included in initiation message";
          leaf initiation-message {
            type string {
            }
          } //initiation-message

        } //container initiation-message

        leaf report-local-routes {
          type boolean;
          description
              "Report imported and leaked routes";
        }

        container routes-report-interval {
          status "obsolete";
          description
              "How often BMP looks at the RIB to find new routes and send those to the BMP 
               station";
          leaf seconds {
            type uint32 {
              range "1..30";
            }
          } //seconds

        } //container routes-report-interval

        leaf shutdown {
          type boolean;
          description
              "Shutdown the BMP station";
        }

        container stats-report-interval {
          description
              "How often statistics reports are sent to the BMP station";
          leaf seconds {
            type uint32 {
              range "15..65535";
            }
          } //seconds

        } //container stats-report-interval

        container connection {
          description
              "Connection parameters for the BMP station";
          container connect-retry {
            description
                "Maximum interval between 2 connection attempts";
            leaf seconds {
              type uint32 {
                range "1..65535";
              }
            } //seconds

          } //container connect-retry

          container local-address {
            description
                "Local IP address of the TCP connection to the BMP station";
            leaf ip-address-ipv6-address {
              type string;
            } //ip-address-ipv6-address

          } //container local-address

          container router {
            description
                "Router instance used to reach the BMP station";
            leaf router-instance {
              type string {
                length "1..32";
              }
              default "Base";
              description
                  "Attribute router-instance for router";
            } //router-instance

            leaf service-name {
              type string;
            } //service-name

          } //container router

          container station-address {
            description
                "IP address and TCP port of the BMP station";
            leaf ip-address-ipv6-address {
              type string;
            } //ip-address-ipv6-address

            leaf port {
              type uint16 {
                range "1..65535";
              }
            } //port

          } //container station-address

          container tcp-keepalive {
            description
                "Parameters for TCP keep-alives";
            container keep-count {
              description
                  "Number of missed keep-alives before the TCP connection is declared down";
              leaf count {
                type uint32 {
                  range "3..100";
                }
                default 4;
              } //count

            } //container keep-count

            container keep-idle {
              description
                  "Number of seconds until the first TCP keep-alive is sent";
              leaf idle {
                type uint32 {
                  range "1..100000";
                }
                default 600;
              } //idle

            } //container keep-idle

            container keep-interval {
              description
                  "Number of seconds between two TCP keep-alives";
              leaf interval {
                type uint32 {
                  range "1..100000";
                }
                default 15;
              } //interval

            } //container keep-interval

            leaf shutdown {
              type boolean;
              description
                  "Enable/disable TCP keep-alives";
            }

          } //container tcp-keepalive

        } //container connection

      } //list station

    } //container bmp

  } //grouping alu-conf-bmp-r13

} //module  alu-conf-bmp-r13
