module alu-conf-router-mpls-tp-r13 {
  yang-version "1";

  namespace "urn:alcatel-lucent.com:sros:ns:yang:conf-router-mpls-tp-r13";

  prefix "conf-router-mpls-tp-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure MPLS Transport Profile parameters 
       on SR OS based routers. 
       
       Copyright 2014-2015 Alcatel-Lucent, 2016 Nokia. All rights reserved. 
       Reproduction of this document is authorized on the condition that the 
       foregoing copyright notice is included. 
       
       This alu-conf-router-mpls-tp-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2018-05-08";

  grouping alu-conf-router-mpls-tp-r13 {
    container mpls-tp {
      presence
          "Configure MPLS Transport Profile parameters";
      container global-id {
        description
            "Global id for MPLS-TP";
        leaf global-id {
          type uint32;
        } //global-id

      } //container global-id

      container node-id {
        description
            "Node id for MPLS-TP local router";
        leaf node-id {
          type string {
            length "1..15";
          }
          description
              "a.b.c.d|<1..4294967295>";
        } //node-id

      } //container node-id

      leaf shutdown {
        type boolean;
        description
            "Administratively enable/disable the MPLS-TP";
      }

      container tp-tunnel-id-range {
        description
            "Configure MPLS-TP tunnel id range on the ingress router";
        leaf min {
          type uint32 {
            range "1..61440";
          }
          description
              "[1..61440]";
        } //min

        leaf max {
          type uint32 {
            range "1..61440";
          }
          description
              "[1..61440]";
        } //max

      } //container tp-tunnel-id-range

      list oam-template {
        key "template-name";
        description
            "Configure a MPLS-TP OAM Template";
        leaf template-name {
          type string {
            length "1..32";
          }
        } //template-name

        container bfd-template {
          description
              "Configure the Bidirectional Forwarding Detection (BFD) template";
          leaf template-name {
            type string {
              length "1..32";
            }
          } //template-name

        } //container bfd-template

        container hold-time-down {
          description
              "Configure hold-down dampening timer";
          leaf timer {
            type uint32 {
              range "0..5000";
            }
            default 0;
            description
                "0..5000 centiseconds - Default: 0 centiseconds";
          } //timer

        } //container hold-time-down

        container hold-time-up {
          description
              "Configure the hold-up dampening timer";
          leaf timer {
            type uint32 {
              range "0..500";
            }
            default 20;
            description
                "0..500 deciseconds - Default: 20 deciseconds.";
          } //timer

        } //container hold-time-up

      } //list oam-template

      list protection-template {
        key "protection-template-string";
        description
            "Configure a MPLS-TP Protection Template";
        leaf protection-template-string {
          type string {
            length "1..32";
          }
        } //protection-template-string

        container rapid-psc-timer {
          description
              "Configure the rapid Protection Switch Coordination (PSC) timer";
          leaf timer {
            type enumeration {
              enum 1000;
              enum 100;
              enum 10;
            }
            description
                "1000|100|10 - Default: 10 milliseconds.";
          } //timer

        } //container rapid-psc-timer

        leaf revertive {
          type boolean;
          description
              "Enable/Disable the template's revertive mode";
        }

        container slow-psc-timer {
          description
              "Configure the slow Protection Switch Coordination (PSC) timer";
          leaf timer {
            type uint32 {
              range "5..60";
            }
            default 5;
            description
                "5..60 seconds - Default: 5 seconds.";
          } //timer

        } //container slow-psc-timer

        container wait-to-restore {
          description
              "Configure the WTR timer for the template";
          leaf timer {
            type uint32 {
              range "0..720";
            }
            default 300;
            description
                "0..720 seconds - Default: 300 seconds.";
          } //timer

        } //container wait-to-restore

      } //list protection-template

      list transit-path {
        key "path-name";
        description
            "Configure a MPLS-TP Transit Path";
        leaf path-name {
          type string {
            length "1..32";
          }
        } //path-name

        container path-id {
          description
              "Configure the MPLS-TP Path-id parameters";
          leaf src-global-id {
            type uint32;
          } //src-global-id

          leaf src-node-id {
            type string;
            description
                "a.b.c.d|<1..4294967295>";
          } //src-node-id

          leaf src-tunnel-num {
            type uint32 {
              range "1..61440";
            }
            description
                "[1..61440]";
          } //src-tunnel-num

          leaf dest-global-id {
            type uint32;
          } //dest-global-id

          leaf dest-node-id {
            type string;
          } //dest-node-id

          leaf dest-tunnel-num {
            type uint32 {
              range "1..61440";
            }
          } //dest-tunnel-num

          leaf lsp-num {
            type uint32 {
              range "1..65535";
            }
          } //lsp-num

        } //container path-id

        leaf shutdown {
          type boolean;
          description
              "Administratively enable/disable the MPLS-TP Transit Path";
        }

        container forward-path {
          presence
              "Configure MPLS-TP Transit Path Forward Path";
          container in-label {
            description
                "Configure MPLS-TP Transit Path Forward Path In-label";
            leaf in-label {
              type string;
              description
                  "Attribute in-label for in-label";
            } //in-label

            leaf out-label {
              type uint32 {
                range "16..1048575";
              }
            } //out-label

            leaf out-link {
              type string {
                length "1..32";
              }
            } //out-link

            leaf next-hop {
              type string;
              description
                  "[a.b.c.d]";
            } //next-hop

          } //container in-label

          container mip {
            presence
                "Configure a MPLS-TP Maintenance Intermediate Point (MIP)";
            container dsmap {
              description
                  "Configure the DSMAP for the MIP";
              leaf if-num {
                type string;
                description
                    "<in-if-num>[:<out-if-num>] 
                     <in-if-num> - [0..4294967295] - Default: 0 
                     <out-if-num> - [0..4294967295] - Default: 0";
              } //if-num

            } //container dsmap

          } //container mip

        } //container forward-path

        container reverse-path {
          presence
              "Configure MPLS-TP Transit Path Reverse Path";
          container in-label {
            description
                "Configure MPLS-TP Transit Path Reverse Path In Label";
            leaf in-label {
              type string;
              description
                  "Attribute in-label for in-label";
            } //in-label

            leaf out-label {
              type uint32 {
                range "16..1048575";
              }
            } //out-label

            leaf out-link {
              type string {
                length "1..32";
              }
            } //out-link

            leaf next-hop {
              type string;
              description
                  "[a.b.c.d]";
            } //next-hop

          } //container in-label

          container mip {
            presence
                "Configure a MPLS-TP Maintenance Intermediate Point (MIP)";
            container dsmap {
              description
                  "Configure the DSMAP for the MIP";
              leaf if-num {
                type string;
                description
                    "<in-if-num>[:<out-if-num>] 
                     <in-if-num> - [0..4294967295] - Default: 0 
                     <out-if-num> - [0..4294967295] - Default: 0";
              } //if-num

            } //container dsmap

          } //container mip

        } //container reverse-path

      } //list transit-path

    } //container mpls-tp

  } //grouping alu-conf-router-mpls-tp-r13

} //module  alu-conf-router-mpls-tp-r13
