module alu-conf-sys-ptp-r13 {
  yang-version "1";

  namespace "urn:alcatel-lucent.com:sros:ns:yang:conf-sys-ptp-r13";

  prefix "conf-sys-ptp-r13";

  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure the Precision Timing Protocol on 
       SR OS based routers. 
       
       Copyright 2014-2015 Alcatel-Lucent, 2016 Nokia. All rights reserved. 
       Reproduction of this document is authorized on the condition that the 
       foregoing copyright notice is included. 
       
       This alu-conf-sys-ptp-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-03-05";

  grouping alu-conf-sys-ptp-r13 {
    container ptp {
      description
          "Configure the Precision Timing Protocol";
      container anno-rx-timeout {
        description
            "Configure the PTP Announce Receipt Timeout, in Announce Intervals";
        leaf count {
          type uint16 {
            range "2..10";
          }
          description
              "[2..10] - Default 3";
        } //count

      } //container anno-rx-timeout

      container clock-type {
        description
            "Configure the PTP Clock Type";
        leaf boundary {
          type boolean;
        } //boundary

        leaf ordinary {
          type enumeration {
            enum master;
            enum slave;
          }
        } //ordinary

      } //container clock-type

      container domain {
        description
            "Configure the PTP Domain";
        leaf domain-value {
          type uint32 {
            range "0..255";
          }
          description
              "Attribute domain-value for domain";
        } //domain-value

      } //container domain

      container local-priority {
        description
            "Configure the PTP clock's G.8275.1 Local Priority";
        leaf priority {
          type uint32 {
            range "1..255";
          }
          default 128;
          description
              "[1..255] - Default: 128";
        } //priority

      } //container local-priority

      container log-anno-interval {
        description
            "Configure the PTP Announce Interval (specified as the logarithm to the base 2 
             in seconds)";
        leaf log-interval {
          type int32 {
            range "-3..4";
          }
          description
              "Attribute log-interval for log-anno-interval";
        } //log-interval

      } //container log-anno-interval

      container network-type {
        description
            "Configure the PTP Network Type";
        leaf network-type-id {
          type enumeration {
            enum sdh;
            enum sonet;
          }
        } //network-type-id

      } //container network-type

      container peer-limit {
        description
            "Configure the maximum number of PTP slave peers that may be dynamically 
             created on the Base router";
        leaf limit {
          type string;
          description
              "Attribute limit for peer-limit";
        } //limit

      } //container peer-limit

      container priority1 {
        description
            "Configure PTP Priority1";
        leaf priority-value {
          type uint32 {
            range "0..255";
          }
          default 128;
          description
              "[0..255] - Default: 128";
        } //priority-value

      } //container priority1

      container priority2 {
        description
            "Configure PTP Priority2";
        leaf priority-value {
          type uint32 {
            range "0..255";
          }
          default 128;
          description
              "[0..255] - Default: 128";
        } //priority-value

      } //container priority2

      container profile {
        description
            "Configure the PTP Profile";
        leaf profile-id {
          type enumeration {
            enum g8265dot1-2010;
            enum ieee1588-2008;
            enum g8275dot1-2014;
          }
        } //profile-id

      } //container profile

      leaf shutdown {
        type boolean;
        description
            "Administratively enable or disable PTP on the system";
      }

      list peer {
        key "peer-id";
        description
            "Configure a PTP master Peer";
        leaf peer-id {
          type inet:ip-address;
        } //peer-id

        container local-priority {
          description
              "Configure the PTP peer local priority";
          leaf local-priority {
            type uint32 {
              range "1..255";
            }
            default 128;
            description
                "[1..255] - Default: 128";
          } //local-priority

        } //container local-priority

        container log-sync-interval {
          description
              "Configure the PTP peer sync message interval (specified as the logarithm to 
               the base 2 in seconds)";
          leaf log-interval {
            type int32 {
              range "-6..0";
            }
            description
                "Attribute log-interval for log-sync-interval";
          } //log-interval

        } //container log-sync-interval

        leaf shutdown {
          type boolean;
          description
              "Administratively shutdown the PTP peer";
        }

      } //list peer

      list port {
        key "port-id";
        description
            "Configure a PTP Port";
        leaf port-id {
          type string;
          description
              "slot/mda/port";
        } //port-id

        container address {
          description
              "Configure the PTP port multicast address";
          leaf address-id {
            type enumeration {
              enum 01:1b:19:00:00:00;
              enum 01:80:c2:00:00:0e;
            }
          } //address-id

        } //container address

        container local-priority {
          description
              "Configure the PTP port's G.8275.1 local priority";
          leaf priority {
            type uint32 {
              range "1..255";
            }
            default 128;
            description
                "[1..255] - Default: 128";
          } //priority

        } //container local-priority

        container log-delay-interval {
          description
              "Configure the PTP port delay message interval (specified as the logarithm to 
               the base 2 in seconds)";
          leaf log-interval {
            type int32 {
              range "-6..0";
            }
            description
                "Attribute log-interval for log-delay-interval";
          } //log-interval

        } //container log-delay-interval

        container log-sync-interval {
          description
              "Configure the PTP port sync message interval (specified as the logarithm to 
               the base 2 in seconds)";
          leaf log-interval {
            type int32 {
              range "-6..0";
            }
            description
                "Attribute log-interval for log-sync-interval";
          } //log-interval

        } //container log-sync-interval

        container master-only {
          description
              "Enable/disable the master-only parameter of the PTP port";
          leaf true {
            type boolean;
          } //true

          leaf false {
            type boolean;
          } //false

        } //container master-only

        leaf shutdown {
          type boolean;
          description
              "Administratively enable/disable the PTP port";
        }

      } //list port

    } //container ptp

  } //grouping alu-conf-sys-ptp-r13

} //module  alu-conf-sys-ptp-r13
