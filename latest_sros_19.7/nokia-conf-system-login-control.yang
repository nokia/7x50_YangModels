submodule nokia-conf-system-login-control {

    yang-version "1.1";

    belongs-to nokia-conf { prefix "conf"; }

    import nokia-sros-yang-extensions     { prefix "sros-ext"; }
    import nokia-types-sros               { prefix "types-sros"; }

    include nokia-conf-groups;

    sros-ext:sros-major-release "rel19";

    organization "Nokia";

    contact
        "Nokia SR OS Support
         Web: <http://www.nokia.com>";

    description
        "Nokia YANG Data model to configure system login-control parameters on SR OS based routers.

         Copyright 2016 Nokia. All rights reserved. Reproduction of this document
         is authorized on the condition that the foregoing copyright notice is included.

         This nokia-conf-system-login-control YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-04-01";

    grouping conf-system-login-control {
        container login-control {
            description "Enter the login-control context";

            leaf exponential-backoff {
                type boolean;
                default "false";
                description "Login exponential-backoff to deter brute force attack";
            }

            leaf idle-timeout {
                type union {
                    type enumeration {
                        enum "none"                         { value 9999; }
                    }
                    type int64 {
                        range "1..1440";
                    }
                }
                units "minutes";
                default "30";
                description "Idle timeout for FTP, console, or Telnet sessions before the system terminate the session";
            }

            leaf login-banner {
                type boolean;
                default "false";
                description "Display login banner";
            }

            container login-scripts {
                description "Enter the login-scripts context";

                leaf global-script {
                    type types-sros:string-not-all-spaces {
                        length "1..180";
                    }
                    description "URL of the global login script";
                }

                container per-user-script {
                    description "Enter the per-user-script context";

                    leaf user-directory {
                        type types-sros:string-not-all-spaces {
                            length "1..180";
                        }
                        description "Users to define their own login scripts that can be executed when they first log in to CLI";
                    }

                    leaf file-name {
                        type types-sros:filename;
                        description "File name of the per-user login script";
                    }

                } // container per-user-script

            } // container login-scripts

            container motd {
                description "Enter the motd context";

                choice motd {
                    case url {

                        leaf url {
                            type types-sros:string-not-all-spaces {
                                length "1..180";
                            }
                            description "URL from where a message of the day is fetched";
                        }

                    }
                    case text {

                        leaf text {
                            type types-sros:string-not-all-spaces {
                                length "1..900";
                            }
                            description "Message to display in text format";
                        }

                    }
                }
            } // container motd

            container pre-login-message {
                description "Enter the pre-login-message context";

                leaf message {
                    type types-sros:string-not-all-spaces {
                        length "1..900";
                    }
                    description "Message to display prior to the login prompt of an inbound FTP, Telnet, or SSH session";
                }

                leaf name {
                    type boolean;
                    default "false";
                    description "Pre login message included in the system name";
                }

            } // container pre-login-message

            container ftp {
                description "Enter the ftp context";

                leaf inbound-max-sessions {
                    type uint32 {
                        range "0..5";
                    }
                    default "3";
                    description "Maximum number of concurrent inbound FTP sessions";
                }

            } // container ftp

            container ssh {
                description "Enter the ssh context";

                leaf graceful-shutdown {
                    type boolean;
                    default "true";
                    description "Allow graceful shutdown of SSH sessions";
                }

                leaf inbound-max-sessions {
                    type uint32 {
                        range "0..50";
                    }
                    default "5";
                    description "Maximum number of concurrent inbound sessions";
                }

                leaf outbound-max-sessions {
                    type uint32 {
                        range "0..15";
                    }
                    default "5";
                    description "Maximum number of concurrent outbound sessions";
                }

                leaf ttl-security {
                    type uint32 {
                        range "1..255";
                    }
                    description "Minimum TTL value for incoming BGP packet";
                }

            } // container ssh

            container telnet {
                description "Enter the telnet context";

                leaf graceful-shutdown {
                    type boolean;
                    default "false";
                    description "Allow graceful shutdown of Telnet sessions";
                }

                leaf inbound-max-sessions {
                    type uint32 {
                        range "0..50";
                    }
                    default "5";
                    description "Maximum number of concurrent inbound sessions";
                }

                leaf outbound-max-sessions {
                    type uint32 {
                        range "0..15";
                    }
                    default "5";
                    description "Maximum number of concurrent outbound sessions";
                }

                leaf ttl-security {
                    type uint32 {
                        range "1..255";
                    }
                    description "Minimum TTL value for incoming BGP packet";
                }

            } // container telnet

        } // container login-control

    } // grouping conf-system-login-control

}
