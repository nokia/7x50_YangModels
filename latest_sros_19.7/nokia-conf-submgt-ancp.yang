submodule nokia-conf-submgt-ancp {

    yang-version "1.1";

    belongs-to nokia-conf { prefix "conf"; }

    import nokia-sros-yang-extensions     { prefix "sros-ext"; }
    import nokia-types-sros               { prefix "types-sros"; }
    import nokia-types-subscriber-mgmt    { prefix "types-submgt"; }

    include nokia-conf-groups;
    include nokia-conf-service;

    sros-ext:sros-major-release "rel19";

    organization "Nokia";

    contact
        "Nokia SR OS Support
         Web: <http://www.nokia.com>";

    description
        "Nokia YANG Data model to configure subscriber management ancp on SR OS based routers.

         Copyright 2016 Nokia. All rights reserved. Reproduction of this document
         is authorized on the condition that the foregoing copyright notice is included.

         This nokia-conf-submgt-ancp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-05-02";

    grouping conf-submgt-ancp {
        container ancp {
            description "Enter the ancp context";

            list ancp-policy {
                key "name";
                description "Enter the ancp-policy list instance";

                leaf name {
                    type types-sros:named-item;
                    description "Policy name";
                }

                container egress {
                    description "Enter the egress context";

                    leaf rate-adjustment {
                        type uint32 {
                            range "1..200";
                        }
                        units "percent";
                        default "100";
                        description "Rate adjustment";
                    }

                    leaf rate-reduction {
                        type uint32 {
                            range "1..4294967295";
                        }
                        units "kilobps";
                        description "Rate reduction";
                    }

                    container rate-modify {
                        description "Enter the rate-modify context";

                        choice rate-modify {
                            case agg-rate {

                                leaf agg-rate {
                                    type empty;
                                    description "Aggregate rate that applies for modification";
                                }

                            }
                            case scheduler {

                                leaf scheduler {
                                    type types-sros:named-item;
                                    description "Scheduler to be applied for rate modification";
                                }

                            }
                        }
                    } // container rate-modify

                    container rate-monitor {
                        description "Enter the rate-monitor context";

                        leaf rate {
                            type uint32 {
                                range "1..4294967295";
                            }
                            units "kilobps";
                            description "Rate below which the system generates an event";
                        }

                        leaf alarm {
                            type boolean;
                            default "false";
                            description "Generate SNMP notification when monitor event is raised";
                        }

                    } // container rate-monitor

                } // container egress

                container ingress {
                    description "Enter the ingress context";

                    leaf rate-adjustment {
                        type uint32 {
                            range "1..200";
                        }
                        units "percent";
                        default "100";
                        description "Rate adjustment";
                    }

                    leaf rate-reduction {
                        type uint32 {
                            range "1..4294967295";
                        }
                        units "kilobps";
                        description "Rate reduction";
                    }

                    container rate-modify {
                        description "Enter the rate-modify context";

                        leaf scheduler {
                            type types-sros:named-item;
                            description "Scheduler to be applied for rate modification";
                        }

                    } // container rate-modify

                    container rate-monitor {
                        description "Enter the rate-monitor context";

                        leaf rate {
                            type uint32 {
                                range "1..4294967295";
                            }
                            units "kilobps";
                            description "Rate below which the system generates an event";
                        }

                        leaf alarm {
                            type boolean;
                            default "false";
                            description "Generate SNMP notification when monitor event is raised";
                        }

                    } // container rate-monitor

                } // container ingress

                container port-down {
                    description "Enter the port-down context";

                    container suspend-shcv {
                        presence "Disable subscriber host connectivity verification.";
                        description "Enter the suspend-shcv context";

                        leaf alarm {
                            type boolean;
                            default "false";
                            description "Enables/disables whether the system should generate a notification before suspending SHCV.";
                        }

                        leaf hold-time {
                            type types-sros:time-duration {
                                range "1..7200";
                            }
                            units "seconds";
                            description "Configures how long SHCV is suspended.";
                        }

                    } // container suspend-shcv

                } // container port-down

            } // list ancp-policy

            container ancp-static-map {
                description "Enter the ancp-static-map context";

                list sap-entry {
                    key "ancp-string sap-id";
                    description "Enter the sap-entry list instance";

                    leaf ancp-string {
                        type types-submgt:ancp-string;
                        description "ANCP string";
                    }

                    leaf sap-id {
                        type types-sros:sap;
                        description "SAP";
                    }

                    leaf ancp-policy {
                        type leafref {
                            path "../../../ancp-policy/name";
                        }
                        mandatory true;
                        description "ANCP policy name";
                    }

                } // list sap-entry

                list multi-service-site-entry {
                    key "ancp-string customer-name customer-site-name";
                    description "Enter the multi-service-site-entry list instance";

                    leaf ancp-string {
                        type types-submgt:ancp-string;
                        description "ANCP string";
                    }

                    leaf customer-name {
                        type leafref {
                            path "../../../../../service/customer/customer-name";
                        }
                        description "Service customer identifier";
                    }

                    leaf customer-site-name {
                        type leafref {
                            path "../../../../../service/customer[customer-name=current()/../customer-name]/multi-service-site/multi-service-site-name";
                        }
                        description "Service customer multi-service site name";
                    }

                    leaf ancp-policy {
                        type leafref {
                            path "../../../ancp-policy/name";
                        }
                        mandatory true;
                        description "The ANCP policy.";
                    }

                } // list multi-service-site-entry

            } // container ancp-static-map

        } // container ancp

    } // grouping conf-submgt-ancp

}
