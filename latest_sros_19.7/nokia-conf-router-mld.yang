submodule nokia-conf-router-mld {

    yang-version "1.1";

    belongs-to nokia-conf { prefix "conf"; }

    import nokia-sros-yang-extensions     { prefix "sros-ext"; }
    import nokia-types-igmp               { prefix "types-igmp"; }
    import nokia-types-mcast-cac          { prefix "types-mcast-cac"; }
    import nokia-types-sros               { prefix "types-sros"; }

    include nokia-conf-groups;
    include nokia-conf-mcast-cac;
    include nokia-conf-policy-options;
    include nokia-conf-service;
    include nokia-conf-svc-ies;
    include nokia-conf-svc-ies-sub-if;

    sros-ext:sros-major-release "rel19";

    organization "Nokia";

    contact
        "Nokia SR OS Support
         Web: <http://www.nokia.com>";

    description
        "Nokia YANG Data model to configure mld protocol on SR OS based routers.

         Copyright 2016 Nokia. All rights reserved. Reproduction of this document
         is authorized on the condition that the foregoing copyright notice is included.

         This nokia-conf-router-mld YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-03-21";

    grouping conf-router-mld {
        container mld {
            presence "Enables MLD functionality on this router.";
            description "Enter the mld context";

            leaf group-if-query-source-address {
                type types-sros:ipv6-unicast-or-linklocal-address;
                description "Source address in queries for group interfaces when not configured at group interface level";
            }

            leaf query-interval {
                type uint32 {
                    range "2..1024";
                }
                units "seconds";
                default "125";
                description "Time between two consecutive host-query messages";
            }

            leaf query-last-member-interval {
                type uint32 {
                    range "1..1023";
                }
                units "seconds";
                default "1";
                description "Time between group-specific query messages";
            }

            leaf query-response-interval {
                type uint32 {
                    range "1..1023";
                }
                units "seconds";
                default "10";
                description "Time to wait for a response to the host-query messages";
            }

            leaf robust-count {
                type uint32 {
                    range "2..10";
                }
                default "2";
                description "Robust count to tune for the expected packet loss on a subnet";
            }

            leaf admin-state {
                type types-sros:admin-state;
                default "enable";
                description "Administrative state of MLD operation";
            }

            container ssm-translate {
                description "Enter the ssm-translate context";

                list group-range {
                    key "start end";
                    description "Enter the group-range list instance";

                    leaf start {
                        type types-sros:ipv6-multicast-address;
                        description "Start of group range";
                    }

                    leaf end {
                        type types-sros:ipv6-multicast-address;
                        description "End of group range";
                    }

                    list source {
                        key "source-address";
                        min-elements 1;
                        description "Add a list entry for source";

                        leaf source-address {
                            type types-sros:ipv6-unicast-address;
                            description "Source address of multicast channel.";
                        }

                    } // list source

                } // list group-range

            } // container ssm-translate

            list interface {
                key "ip-interface-name";
                description "Enter the interface list instance";

                leaf ip-interface-name {
                    type types-sros:interface-name;
                    description "Interface name.";
                }

                leaf router-alert-check {
                    type boolean;
                    default "true";
                    description "Enable router alert checking for IGMP or MLD messages";
                }

                leaf maximum-number-groups {
                    type uint32 {
                        range "1..16000";
                    }
                    description "Maximum number of groups for this interface";
                }

                leaf maximum-number-group-sources {
                    type uint32 {
                        range "1..32000";
                    }
                    description "Maximum number of group sources for this interface";
                }

                leaf maximum-number-sources {
                    type uint32 {
                        range "1..1000";
                    }
                    description "Maximum number of sources that are allowed per group";
                }

                leaf query-interval {
                    type uint32 {
                        range "2..1024";
                    }
                    description "Time between two consecutive host-query messages";
                }

                leaf query-response-interval {
                    type uint32 {
                        range "1..1023";
                    }
                    description "Time to wait for a response to the host-query messages";
                }

                leaf query-last-member-interval {
                    type uint32 {
                        range "1..1023";
                    }
                    description "Time between group-specific query messages";
                }

                leaf import-policy {
                    type leafref {
                        path "../../../../policy-options/policy-statement/name";
                    }
                    description "Import policy to filter MLD packets";
                }

                leaf admin-state {
                    type types-sros:admin-state;
                    default "enable";
                    description "Administrative state of this interface";
                }

                leaf version {
                    type types-igmp:mld-version;
                    default "2";
                    description "MLD protocol version";
                }

                container mcac {
                    description "Enter the mcac context";

                    leaf interface-policy {
                        type leafref {
                            path "../../../../../mcac/interface-policy/policy-name";
                        }
                        description "Name of multicast CAC interface policy";
                    }

                    leaf policy {
                        type leafref {
                            path "../../../../../mcac/policy/policy-name";
                        }
                        description "Multicast CAC policy name";
                    }

                    container mc-constraints {
                        description "Enter the mc-constraints context";

                        leaf use-lag-port-weight {
                            type boolean;
                            default "false";
                            description "Use LAG port weight in calculating MCAC constraints";
                        }

                        list level {
                            key "level-id";
                            description "Enter the level list instance";

                            leaf level-id {
                                type types-mcast-cac:constraints-level;
                                description "Bandwidth level ID for a multicast CAC constraint";
                            }

                            leaf bandwidth {
                                type types-mcast-cac:bandwidth {
                                    range "0..2147483647";
                                }
                                mandatory true;
                                description "Bandwidth available for this level";
                            }

                        } // list level

                        list number-down {
                            key "number-lag-port-down";
                            description "Enter the number-down list instance";

                            leaf number-lag-port-down {
                                type uint32 {
                                    range "1..64";
                                }
                                description "Number of ports that are down in this LAG link";
                            }

                            leaf level {
                                type types-mcast-cac:constraints-level;
                                mandatory true;
                                description "Level ID to associate with number of down LAG ports";
                            }

                        } // list number-down

                    } // container mc-constraints

                    container bandwidth {
                        description "Enter the bandwidth context";

                        leaf total {
                            type types-mcast-cac:bandwidth-limit;
                            description "Maximum allowed bandwidth";
                        }

                        leaf mandatory {
                            type types-mcast-cac:bandwidth-limit;
                            description "Pre-reserved bandwidth for all mandatory channels";
                        }

                    } // container bandwidth

                } // container mcac

                container ssm-translate {
                    description "Enter the ssm-translate context";

                    list group-range {
                        key "start end";
                        description "Enter the group-range list instance";

                        leaf start {
                            type types-sros:ipv6-multicast-address;
                            description "Start of group range";
                        }

                        leaf end {
                            type types-sros:ipv6-multicast-address;
                            description "End of group range";
                        }

                        list source {
                            key "source-address";
                            min-elements 1;
                            description "Add a list entry for source";

                            leaf source-address {
                                type types-sros:ipv6-unicast-address;
                                description "Source address of multicast channel.";
                            }

                        } // list source

                    } // list group-range

                } // container ssm-translate

                container static {
                    description "Enter the static context";

                    list group {
                        key "group-address";
                        description "Enter the group list instance";

                        leaf group-address {
                            type types-sros:ipv6-multicast-address;
                            description "Group address of multicast channel";
                        }

                        choice source-or-starg {
                            mandatory true;
                            case source {

                                list source {
                                    key "source-address";
                                    description "Add a list entry for source";

                                    leaf source-address {
                                        type types-sros:ipv6-unicast-address;
                                        description "Source address of multicast channel.";
                                    }

                                } // list source

                            }
                            case starg {

                                leaf starg {
                                    type empty;
                                    description "any source address (*,G)";
                                }

                            }
                        }
                    } // list group

                    list group-range {
                        key "start end step";
                        description "Enter the group-range list instance";

                        leaf start {
                            type types-sros:ipv6-multicast-address;
                            description "Start of group range of multicast channel";
                        }

                        leaf end {
                            type types-sros:ipv6-multicast-address;
                            description "End of group range for multicast channel";
                        }

                        leaf step {
                            type types-sros:ipv6-address;
                            description "Step interval for the group-range addresses";
                        }

                        choice source-or-starg {
                            mandatory true;
                            case source {

                                list source {
                                    key "source-address";
                                    description "Add a list entry for source";

                                    leaf source-address {
                                        type types-sros:ipv6-unicast-address;
                                        description "Source address of multicast channel.";
                                    }

                                } // list source

                            }
                            case starg {

                                leaf starg {
                                    type empty;
                                    description "any source address (*,G)";
                                }

                            }
                        }
                    } // list group-range

                } // container static

            } // list interface

            list group-interface {
                key "group-interface-name";
                description "Enter the group-interface list instance";

                leaf group-interface-name {
                    type leafref {
                        path "../../../../service/ies/subscriber-interface/group-interface/group-interface-name";
                    }
                    description "Group interface name";
                }

                leaf router-alert-check {
                    type boolean;
                    default "true";
                    description "Enable router alert checking for IGMP or MLD messages";
                }

                leaf maximum-number-groups {
                    type uint32 {
                        range "1..16000";
                    }
                    description "Maximum number of groups for this interface";
                }

                leaf maximum-number-group-sources {
                    type uint32 {
                        range "1..32000";
                    }
                    description "Maximum number of group sources for this interface";
                }

                leaf maximum-number-sources {
                    type uint32 {
                        range "1..1000";
                    }
                    description "Maximum number of sources that are allowed per group";
                }

                leaf query-interval {
                    type uint32 {
                        range "2..1024";
                    }
                    description "Time between two consecutive host-query messages";
                }

                leaf query-response-interval {
                    type uint32 {
                        range "1..1023";
                    }
                    description "Time to wait for a response to the host-query messages";
                }

                leaf query-last-member-interval {
                    type uint32 {
                        range "1..1023";
                    }
                    description "Time between group-specific query messages";
                }

                leaf import-policy {
                    type leafref {
                        path "../../../../policy-options/policy-statement/name";
                    }
                    description "Import policy to filter MLD packets";
                }

                leaf admin-state {
                    type types-sros:admin-state;
                    default "enable";
                    description "Administrative state of this interface";
                }

                leaf version {
                    type types-igmp:mld-version;
                    default "2";
                    description "MLD protocol version";
                }

                leaf subnet-check {
                    type boolean;
                    default "true";
                    description "Enable subnet checking";
                }

                leaf sub-hosts-only {
                    type boolean;
                    default "true";
                    description "Allow MLD traffic from known hosts only";
                }

                leaf query-source-address {
                    type types-sros:ipv6-unicast-or-linklocal-address;
                    description "Source address for MLD queries";
                }

                container mcac {
                    description "Enter the mcac context";

                    leaf interface-policy {
                        type leafref {
                            path "../../../../../mcac/interface-policy/policy-name";
                        }
                        description "Name of multicast CAC interface policy";
                    }

                    leaf policy {
                        type leafref {
                            path "../../../../../mcac/policy/policy-name";
                        }
                        description "Multicast CAC policy name";
                    }

                    container bandwidth {
                        description "Enter the bandwidth context";

                        leaf total {
                            type types-mcast-cac:bandwidth-limit;
                            description "Maximum allowed bandwidth";
                        }

                        leaf mandatory {
                            type types-mcast-cac:bandwidth-limit;
                            description "Pre-reserved bandwidth for all mandatory channels";
                        }

                    } // container bandwidth

                } // container mcac

            } // list group-interface

        } // container mld

    } // grouping conf-router-mld

}
