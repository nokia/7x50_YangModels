submodule nokia-conf-port {

    yang-version "1.1";

    belongs-to nokia-conf { prefix "conf"; }

    import nokia-sros-yang-extensions     { prefix "sros-ext"; }
    import nokia-types-sros               { prefix "types-sros"; }

    include nokia-conf-groups;
    include nokia-conf-port-access;
    include nokia-conf-port-cellular;
    include nokia-conf-port-connector;
    include nokia-conf-port-dwdm;
    include nokia-conf-port-ethernet;
    include nokia-conf-port-network;
    include nokia-conf-port-otu;
    include nokia-conf-port-sonet;
    include nokia-conf-port-tdm;
    include nokia-conf-port-wlan;

    sros-ext:sros-major-release "rel19";

    organization "Nokia";

    contact
        "Nokia SR OS Support
         Web: <http://www.nokia.com>";

    description
        "Nokia YANG Data model to configure physical ports on SR OS based routers.

         Copyright 2016 Nokia. All rights reserved. Reproduction of this document
         is authorized on the condition that the foregoing copyright notice is included.

         This nokia-conf-port YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-06-20";

    grouping conf-port {
        list port {
            key "port-id";
            description "Enter the port list instance";

            leaf port-id {
                type types-sros:port;
                description "Unique port ID";
            }

            leaf admin-state {
                type types-sros:admin-state;
                description "Administrative state of this port";
            }

            leaf description {
                type types-sros:long-description;
                description "Text description";
            }

            leaf ddm-events {
                type boolean;
                default "true";
                description "Enable Digital Diagnostic Monitoring (DDM) events";
            }

            leaf monitor-agg-egress-queue-stats {
                type boolean;
                default "false";
                description "Monitor aggregate queue statistics";
            }

            leaf-list apply-groups {
                type leafref {
                    path "../../groups/group/name";
                }
                max-elements 8;
                ordered-by user;
                description "Apply a configuration group at this level";
            }

            container hybrid-buffer-allocation {
                description "Enter the hybrid-buffer-allocation context";

                container egress-weight {
                    description "Enter the egress-weight context";

                    leaf access {
                        type uint32 {
                            range "0..100";
                        }
                        default "50";
                        description "Access weight for hybrid port";
                    }

                    leaf network {
                        type uint32 {
                            range "0..100";
                        }
                        default "50";
                        description "Access weight for hybrid port";
                    }

                } // container egress-weight

                container ingress-weight {
                    description "Enter the ingress-weight context";

                    leaf access {
                        type uint32 {
                            range "0..100";
                        }
                        default "50";
                        description "Access weight for hybrid port";
                    }

                    leaf network {
                        type uint32 {
                            range "0..100";
                        }
                        default "50";
                        description "Access weight for hybrid port";
                    }

                } // container ingress-weight

            } // container hybrid-buffer-allocation

            container modify-buffer-allocation {
                description "Enter the modify-buffer-allocation context";

                container percentage-of-rate {
                    description "Enter the percentage-of-rate context";

                    leaf egress {
                        type uint32 {
                            range "1..1000";
                        }
                        default "100";
                        description "Egress rate percentage";
                    }

                    leaf ingress {
                        type uint32 {
                            range "1..1000";
                        }
                        default "100";
                        description "Ingress rate percentage";
                    }

                } // container percentage-of-rate

            } // container modify-buffer-allocation

            container transceiver {
                description "Enter the transceiver context";

                leaf digital-coherent-optics {
                    type boolean;
                    default "false";
                    description "Enable/disable digital coherent optics on the transceiver.";
                }

            } // container transceiver

            uses conf-port-access;
            uses conf-port-cellular;
            uses conf-port-connector;
            uses conf-port-dwdm;
            uses conf-port-ethernet;
            uses conf-port-network;
            uses conf-port-otu;
            uses conf-port-sonet-sonet-sdh;
            uses conf-port-tdm;
            uses conf-port-wlan;
        } // list port

    } // grouping conf-port

}
