submodule nokia-conf-router-isis {

    yang-version "1.1";

    belongs-to nokia-conf { prefix "conf"; }

    import ietf-yang-types                { prefix "yang"; }
    import nokia-sros-yang-extensions     { prefix "sros-ext"; }
    import nokia-types-igp                { prefix "types-igp"; }
    import nokia-types-isis               { prefix "types-isis"; }
    import nokia-types-router             { prefix "types-router"; }
    import nokia-types-sros               { prefix "types-sros"; }

    include nokia-conf-groups;
    include nokia-conf-policy-options;
    include nokia-conf-router;
    include nokia-conf-router-bier;
    include nokia-conf-routing-options;
    include nokia-conf-system;
    include nokia-conf-system-security;

    sros-ext:sros-major-release "rel19";

    organization "Nokia";

    contact
        "Nokia SR OS Support
         Web: <http://www.nokia.com>";

    description
        "Nokia YANG Data model to configure router isis protocol attributes on SR OS based routers.

         Copyright 2016 Nokia. All rights reserved. Reproduction of this document
         is authorized on the condition that the foregoing copyright notice is included.

         This nokia-conf-router-isis YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-04-26";

    grouping conf-router-isis {
        list isis {
            key "isis-instance";
            description "Enter the isis list instance";

            leaf isis-instance {
                type int32 {
                    range "0..31";
                }
                description "Instance ID for IS-IS instance";
            }

            leaf authentication-keychain {
                type leafref {
                    path "../../../system/security/keychains/keychain/keychain-name";
                }
                description "The keychain used to sign and/or authenticate.";
            }

            leaf authentication-key {
                type types-sros:encrypted-leaf {
                    length "1..366";
                }
                description "Authentication key to verify PDUs sent by neighboring routers";
            }

            leaf authentication-type {
                type types-isis:auth-type;
                description "Authentication type";
            }

            leaf csnp-authentication {
                type boolean;
                default "true";
                description "Authenticate individual IS-IS protocol packets of complete sequence number PDU (CSNP) type";
            }

            leaf psnp-authentication {
                type boolean;
                default "true";
                description "Authenticate individual IS-IS protocol packets of partial sequence number PDU (PSNP) type";
            }

            leaf admin-state {
                type types-sros:admin-state;
                default "disable";
                description "Administrative state of IS-IS instance";
            }

            leaf advertise-passive-only {
                type boolean;
                default "false";
                description "Advertise prefixes that belong to passive interfaces";
            }

            leaf advertise-router-capability {
                type enumeration {
                    enum "area"                         { value 2; }
                    enum "as"                           { value 3; }
                }
                description "Advertise router capabilities to neighbors";
            }

            leaf advertise-tunnel-link {
                type boolean;
                default "false";
                description "Allow use of forwarding adjacency";
            }

            leaf all-l1isis {
                type yang:mac-address;
                default "01:80:C2:00:00:14";
                description "Destination MAC address for all L1 IS-IS routers";
            }

            leaf all-l2isis {
                type yang:mac-address;
                default "01:80:C2:00:00:15";
                description "Destination MAC address for all L2 IS-IS routers";
            }

            leaf authentication-check {
                type boolean;
                default "true";
                description "Perform authentication check to reject PDUs that do not match the type or key requirements";
            }

            leaf default-route-tag {
                type uint32 {
                    range "1..max";
                }
                description "Route tag for default route";
            }

            leaf ldp-sync {
                type boolean;
                default "true";
                description "Use IGP-LDP synchronization feature on all interfaces participating in IS-IS routing protocol";
            }

            leaf hello-authentication {
                type boolean;
                default "true";
                description "Authenticate individual IS-IS protocol packets of Hello type";
            }

            leaf ignore-attached-bit {
                type boolean;
                default "false";
                description "Ignore attached bit on received L1 LSPs to disable installation of default routes";
            }

            leaf ignore-lsp-errors {
                type boolean;
                default "false";
                description "Ignore LSP packets with errors";
            }

            leaf ignore-narrow-metric {
                type boolean;
                default "false";
                description "Ignore links with narrow metrics when wide-metrics support is enabled";
            }

            leaf iid-tlv {
                type boolean;
                default "false";
                description "Use IID TLVs with IS-IS multi-instance (MI)";
            }

            leaf ipv4-multicast-routing {
                type types-isis:routing-topology;
                default "native";
                description "IS-IS topology for IPv4 multicast routing";
            }

            leaf ipv4-routing {
                type boolean;
                default "true";
                description "Support IPv4 routing for IS-IS instance";
            }

            leaf ipv6-multicast-routing {
                type types-isis:routing-topology;
                description "Topology to populate the IPv6 multicast RTM";
            }

            leaf ipv6-routing {
                type types-isis:routing-topology;
                default "false";
                description "Routing topology for IPv6";
            }

            leaf hello-padding {
                type types-isis:hello-padding-type;
                description "Padding on IS-IS Hello packets";
            }

            leaf ldp-over-rsvp {
                type boolean;
                default "false";
                description "Allow LDP over RSVP processing";
            }

            leaf level-capability {
                type types-isis:level;
                description "Routing level for instance";
            }

            leaf lsp-lifetime {
                type uint32 {
                    range "350..65535";
                }
                units "seconds";
                sros-ext:manual-restart-to-modify;
                default "1200";
                description "Amount of time during which an LSP is considered valid";
            }

            leaf lsp-minimum-remaining-lifetime {
                type uint32 {
                    range "350..65535";
                }
                units "seconds";
                description "Minimum value for the Remaining Lifetime of an LSP";
            }

            leaf lsp-mtu-size {
                type types-isis:lsp-buffer-ext-size;
                units "bytes";
                sros-ext:manual-restart-to-modify;
                default "1492";
                description "LSP MTU size";
            }

            leaf overload-export-interlevel {
                type boolean;
                default "false";
                description "Advertise the inter-level routes when router is overloaded";
            }

            leaf overload-export-external {
                type boolean;
                default "false";
                description "Advertise the external routes when router is in overloaded";
            }

            leaf poi-tlv {
                type boolean;
                default "false";
                description "Purge Originator Identification TLV";
            }

            leaf prefix-attributes-tlv {
                type boolean;
                default "false";
                description "Use IS-IS Prefix Attributes TLV to exchange extended IPv4 and IPv6 reachability information";
            }

            leaf reference-bandwidth {
                type types-sros:reference-bandwidth-ext;
                units "kilobps";
                description "Reference bandwidth for bandwidth relative costing";
            }

            leaf router-id {
                type types-igp:router-id;
                sros-ext:auto-restart-to-modify;
                description "Unique router ID for the ISIS instance";
            }

            leaf standard-multi-instance {
                type boolean;
                default "false";
                description "Enable RFC standards compliant multi-instance behavior";
            }

            leaf strict-adjacency-check {
                type boolean;
                default "false";
                description "Enable strict checking of address families for IS-IS adjacencies";
            }

            leaf suppress-attached-bit {
                type boolean;
                default "false";
                description "Allow IS-IS to suppress setting the attached bit on LSPs";
            }

            leaf system-id {
                type types-igp:system-id;
                sros-ext:manual-restart-to-modify;
                description "System ID";
            }

            leaf traffic-engineering {
                type boolean;
                default "false";
                description "Traffic engineering for router";
            }

            leaf-list export-policy {
                type leafref {
                    path "../../../policy-options/policy-statement/name";
                }
                max-elements 5;
                ordered-by user;
                description "Configure names of export policies to be used for determining which routes are exported from the routing table to this IGP.";
            }

            leaf-list import-policy {
                type leafref {
                    path "../../../policy-options/policy-statement/name";
                }
                max-elements 5;
                ordered-by user;
                description "Configure names of import policies to be used for determining which routes are imported from this IGP to the routing table.";
            }

            leaf-list area-address {
                type types-isis:area-address;
                max-elements 3;
                description "Area address portion of NSAP address";
            }

            leaf-list apply-groups {
                type leafref {
                    path "../../../groups/group/name";
                }
                max-elements 8;
                ordered-by user;
                description "Apply a configuration group at this level";
            }

            container export-limit {
                presence "Maximum number of routes (prefixes) that can be exported into IS-IS from the route table.";
                description "Enter the export-limit context";

                leaf number {
                    type uint32 {
                        range "1..max";
                    }
                    mandatory true;
                    description "Maximum number of routes or prefixes to be exported into IGP instance from route table";
                }

                leaf log-percent {
                    type uint32 {
                        range "1..100";
                    }
                    description "Export limit at which warning a log message and SNMP notification are sent";
                }

            } // container export-limit

            container graceful-restart {
                presence "Enables/disables graceful restart for ISIS.";
                description "Enter the graceful-restart context";

                leaf helper-mode {
                    type boolean;
                    default "true";
                    description "Enable graceful restart helper for IS-IS";
                }

            } // container graceful-restart

            container entropy-label {
                description "Enter the entropy-label context";

                leaf override-tunnel-elc {
                    type boolean;
                    default "false";
                    description "Received entropy label capability advertisement to override";
                }

            } // container entropy-label

            container multi-topology {
                presence "Configure multi-topologies support in this ISIS instance.";
                description "Enter the multi-topology context";

                leaf ipv6-unicast {
                    type boolean;
                    default "false";
                    description "Support multi-topology TLVs";
                }

                leaf ipv4-multicast {
                    type boolean;
                    default "false";
                    description "Support IPv4 topology (MT3)";
                }

                leaf ipv6-multicast {
                    type boolean;
                    default "false";
                    description "Support IPv6 topology (MT4)";
                }

            } // container multi-topology

            container multicast-import {
                description "Enter the multicast-import context";

                leaf ipv4 {
                    type boolean;
                    default "false";
                    description "Submit IPv4 routes into the multicast RPF of the RTM";
                }

                leaf ipv6 {
                    type boolean;
                    default "false";
                    description "Submit IPv6 routes into the multicast RPF of the RTM";
                }

            } // container multicast-import

            container overload {
                presence "Configure the local router so that it appears to be overload.";
                description "Enter the overload context";

                leaf max-metric {
                    type boolean;
                    default "false";
                    description "Advertise transit links with maximum metric instead of setting overload bit";
                }

            } // container overload

            container overload-on-boot {
                presence "Configure the local router so that it appears to be overloaded at boot up.";
                description "Enter the overload-on-boot context";

                leaf timeout {
                    type uint32 {
                        range "60..1800";
                    }
                    units "seconds";
                    description "Time during which the router operates in overload state after reboot";
                }

                leaf max-metric {
                    type boolean;
                    default "false";
                    description "Advertise transit links with maximum metric instead of setting overload bit";
                }

            } // container overload-on-boot

            container prefix-limit {
                presence "Configure the limit for maximum number of prefixes IS-IS can support.";
                description "Enter the prefix-limit context";

                leaf limit {
                    type uint32 {
                        range "1..max";
                    }
                    mandatory true;
                    description "Maximum number of prefixes for IS-IS instance";
                }

                leaf log-only {
                    type boolean;
                    default "false";
                    description "Send warning message at specified threshold or when limit is reached, without going into overload";
                }

                leaf warning-threshold {
                    type uint32 {
                        range "0..100";
                    }
                    units "percent";
                    default "0";
                    description "Specifies the percentage of the value defined by prefix-limit, at which a warning log message and SNMP notification would be sent. This would only be a warning and additional prefixes will be learned up to 100% of prefix-limit. A value of 0 indicates that the threshold is disabled and no log message or SNMP notification will be sent.";
                }

                leaf overload-timeout {
                    type types-igp:overload-timeout;
                    default "forever";
                    description "Time router remains in overload after prefix limit is exceeded before restarting";
                }

            } // container prefix-limit

            container lsp-refresh {
                description "Enter the lsp-refresh context";

                leaf interval {
                    type uint32 {
                        range "150..65535";
                    }
                    units "seconds";
                    default "600";
                    description "Refresh timer interval";
                }

                leaf half-lifetime {
                    type boolean;
                    default "true";
                    description "Set the refresh interval to always be half the LSP lifetime";
                }

            } // container lsp-refresh

            container rib-priority {
                description "Enter the rib-priority context";

                container high {
                    description "Enter the high context";

                    choice type {
                        case prefix-list {

                            leaf prefix-list {
                                type leafref {
                                    path "../../../../../policy-options/prefix-list/name";
                                }
                                description "List used to select routes processed at higher priority through OSPF route calculation process";
                            }

                        }
                        case tag {

                            leaf tag {
                                type uint32 {
                                    range "1..max";
                                }
                                description "Value that matches IS-IS routes processed at higher priority through route calculation process";
                            }

                        }
                    }
                } // container high

            } // container rib-priority

            container timers {
                description "Enter the timers context";

                container spf-wait {
                    description "Enter the spf-wait context";

                    leaf spf-max-wait {
                        type uint32 {
                            range "10..120000";
                        }
                        units "milliseconds";
                        default "10000";
                        description "Maximum interval between two consecutive SPF calculations";
                    }

                    leaf spf-initial-wait {
                        type uint32 {
                            range "10..100000";
                        }
                        units "milliseconds";
                        default "1000";
                        description "Initial SPF calculation delay after topology change";
                    }

                    leaf spf-second-wait {
                        type uint32 {
                            range "10..100000";
                        }
                        units "milliseconds";
                        default "1000";
                        description "Hold time between first and second SPF calculations";
                    }

                } // container spf-wait

                container lsp-wait {
                    description "Enter the lsp-wait context";

                    leaf lsp-max-wait {
                        type uint32 {
                            range "10..120000";
                        }
                        units "milliseconds";
                        default "5000";
                        description "Maximum time between two consecutive occurrences of LSP generation";
                    }

                    leaf lsp-initial-wait {
                        type uint32 {
                            range "10..100000";
                        }
                        units "milliseconds";
                        default "10";
                        description "Initial LSP generation delay";
                    }

                    leaf lsp-second-wait {
                        type uint32 {
                            range "10..100000";
                        }
                        units "milliseconds";
                        default "1000";
                        description "Delay between first and second LSP generation";
                    }

                } // container lsp-wait

            } // container timers

            container unicast-import {
                description "Enter the unicast-import context";

                leaf ipv4 {
                    type boolean;
                    default "true";
                    description "Submit IPv4 routes into unicast RTM";
                }

                leaf ipv6 {
                    type boolean;
                    default "true";
                    description "Submit IPv6 routes into unicast RTM";
                }

            } // container unicast-import

            container loopfree-alternate {
                presence "Enable/disable fast re-route capability for ISIS";
                description "Enter the loopfree-alternate context";

                container exclude {
                    description "Enter the exclude context";

                    leaf-list prefix-policy {
                        type leafref {
                            path "../../../../../policy-options/policy-statement/name";
                        }
                        max-elements 5;
                        ordered-by user;
                        description "Loopfree Alternative (LFA) exclude policies from which prefixes are excluded. Prefixes excluded from LFA this way will not be used in the LFA calculation, regardless of their priority.";
                    }

                } // container exclude

                container remote-lfa {
                    presence "Enable/disable Remote LFA";
                    description "Enter the remote-lfa context";

                    leaf max-pq-cost {
                        type uint32;
                        default "4261412864";
                        description "Maximum cost of destination node during reverse SPF calculation";
                    }

                    container node-protect {
                        presence "Configure node-protection support in this ISIS instance.";
                        description "Enter the node-protect context";

                        leaf max-pq-nodes {
                            type uint32 {
                                range "1..32";
                            }
                            default "16";
                            description "Specifies the maximum number of PQ nodes.";
                        }

                    } // container node-protect

                } // container remote-lfa

                container ti-lfa {
                    presence "Enable/disable topology Independent LFA";
                    description "Enter the ti-lfa context";

                    leaf max-sr-frr-labels {
                        type uint32 {
                            range "0..3";
                        }
                        default "2";
                        description "Maximum number of labels that TI-LFA backup next hop can use";
                    }

                    container node-protect {
                        presence "Configure node-protection support in this ISIS instance.";
                        description "Enter the node-protect context";

                    } // container node-protect

                } // container ti-lfa

            } // container loopfree-alternate

            container database-export {
                presence "Enable/disable database export.";
                description "Enter the database-export context";

                leaf igp-identifier {
                    type uint64;
                    description "Unique identifier of the IGP instance in the BGP-LS NLRI";
                }

                container bgp-ls-identifier {
                    presence "Enable/disable BGP-LS instance-identifier.";
                    description "Enter the bgp-ls-identifier context";

                    leaf value {
                        type uint32;
                        default "0";
                        description "BGP-LS identifier that is sent in the BGP-LS NLRI";
                    }

                } // container bgp-ls-identifier

            } // container database-export

            container segment-routing {
                description "Enter the segment-routing context";

                leaf admin-state {
                    type types-sros:admin-state;
                    default "disable";
                    description "Administrative state of segment routing";
                }

                leaf adj-sid-hold {
                    type types-igp:adj-sid-hold-type;
                    units "seconds";
                    default "15";
                    description "Adjacency SID hold time";
                }

                leaf entropy-label {
                    type boolean;
                    default "true";
                    description "Entropy label capability";
                }

                leaf export-tunnel-table {
                    type enumeration {
                        enum "ldp"                          { value 1; }
                    }
                    description "Tunnel table export policies to export tunneled routes";
                }

                leaf srlb {
                    type leafref {
                        path "../../../mpls-labels/reserved-label-block/label-block-name";
                    }
                    description "Segment routing local block";
                }

                leaf tunnel-mtu {
                    type types-router:ip-mtu-ext;
                    description "Tunnel MTU size";
                }

                leaf tunnel-table-pref {
                    type uint32 {
                        range "1..255";
                    }
                    default "11";
                    description "Preference of SR tunnels created by the IGP instance";
                }

                leaf-list apply-groups {
                    type leafref {
                        path "../../../../groups/group/name";
                    }
                    max-elements 8;
                    ordered-by user;
                    description "Apply a configuration group at this level";
                }

                container prefix-sid-range {
                    presence "Configure prefix-sid-range";
                    description "Enter the prefix-sid-range context";

                    choice type {
                        case global {

                            leaf global {
                                type empty;
                                description "Use global SR range";
                            }

                        }
                        case local {

                            leaf start-label {
                                type uint32 {
                                    range "0..524287";
                                }
                                sros-ext:auto-restart-to-modify;
                                default "0";
                                description "Value for the local label starting offset";
                            }

                            leaf max-index {
                                type uint32 {
                                    range "1..524287";
                                }
                                sros-ext:auto-restart-to-modify;
                                default "1";
                                description "Maximum local SID index";
                            }

                        }
                    }
                } // container prefix-sid-range

                list adjacency-set {
                    key "id";
                    description "Enter the adjacency-set list instance";

                    leaf id {
                        type uint32 {
                            range "1..max";
                        }
                        description "Identifier for specified adjacency set";
                    }

                    leaf family {
                        type types-sros:adjacency-set-family-type;
                        default "ipv4";
                        description "Address family for the adjacency set";
                    }

                    leaf parallel {
                        type boolean;
                        default "true";
                        description "Require all members of the adjacency set to terminate on the same neighboring node";
                    }

                    leaf advertise {
                        type boolean;
                        default "true";
                        description "Advertise the adjacency set when all links terminate on the same neighboring node";
                    }

                    leaf-list apply-groups {
                        type leafref {
                            path "../../../../../groups/group/name";
                        }
                        max-elements 8;
                        ordered-by user;
                        description "Apply a configuration group at this level";
                    }

                    container sid {
                        presence "Assign a static SID value to this adj-set";
                        description "Enter the sid context";

                        choice type {
                            case label {

                                leaf label {
                                    type int64 {
                                        range "1..1048575";
                                    }
                                    description "Adjacency SID";
                                }

                            }
                        }
                    } // container sid

                } // list adjacency-set

                container mapping-server {
                    description "Enter the mapping-server context";

                    leaf admin-state {
                        type types-sros:admin-state;
                        default "disable";
                        description "Administrative state of ISIS segment routing mapping server";
                    }

                    list node-sid-map {
                        key "sid-index";
                        description "Enter the node-sid-map list instance";

                        leaf sid-index {
                            type uint32;
                            description "SID index of a mapping server Prefix-SID";
                        }

                        leaf ip-prefix {
                            type types-sros:ipv4-unicast-prefix;
                            mandatory true;
                            description "Prefix of a mapping server Prefix-SID";
                        }

                        leaf range {
                            type uint32 {
                                range "0..65535";
                            }
                            default "1";
                            description "Range of addresses and their associated prefix SIDs";
                        }

                        leaf level-capability {
                            type types-isis:level;
                            description "Flags to assign in SID Label Binding TLV advertised by Segment Routing Mapping Server";
                        }

                        leaf clear-n-flag {
                            type boolean;
                            default "false";
                            description "Clear the node-sid flag (N-flag)";
                        }

                        leaf-list apply-groups {
                            type leafref {
                                path "../../../../../../groups/group/name";
                            }
                            max-elements 8;
                            ordered-by user;
                            description "Apply a configuration group at this level";
                        }

                        container set-flags {
                            description "Enter the set-flags context";

                            leaf bit-s {
                                type boolean;
                                default "false";
                                description "SID Label Binding TLV to be flooded across the entire routing domain";
                            }

                        } // container set-flags

                    } // list node-sid-map

                } // container mapping-server

            } // container segment-routing

            container igp-shortcut {
                description "Enter the igp-shortcut context";

                leaf admin-state {
                    type types-sros:admin-state;
                    default "disable";
                    description "Administrative state of RSVP-TE or SR-TE shortcut";
                }

                leaf-list apply-groups {
                    type leafref {
                        path "../../../../groups/group/name";
                    }
                    max-elements 8;
                    ordered-by user;
                    sros-ext:auto-restart-to-modify;
                    description "Apply a configuration group at this level";
                }

                container tunnel-next-hop {
                    sros-ext:auto-restart-to-modify;
                    description "Enter the tunnel-next-hop context";

                    list family {
                        key "family-type";
                        sros-ext:auto-restart-to-modify;
                        description "Enter the family list instance";

                        leaf family-type {
                            type types-igp:tunn-next-hop-family-type;
                            description "Address family type for tunnel next-hop";
                        }

                        leaf resolution {
                            type types-sros:resolution-type;
                            sros-ext:auto-restart-to-modify;
                            description "Resolution state for IGP shortcut tunnels";
                        }

                        leaf-list apply-groups {
                            type leafref {
                                path "../../../../../../groups/group/name";
                            }
                            max-elements 8;
                            ordered-by user;
                            sros-ext:auto-restart-to-modify;
                            description "Apply a configuration group at this level";
                        }

                        container resolution-filter {
                            sros-ext:auto-restart-to-modify;
                            description "Enter the resolution-filter context";

                            leaf rsvp {
                                type boolean;
                                sros-ext:auto-restart-to-modify;
                                default "false";
                                description "Use RSVP tunneling for next-hop resolution";
                            }

                            leaf sr-te {
                                type boolean;
                                sros-ext:auto-restart-to-modify;
                                default "false";
                                description "Use SR-TE tunneling for next-hop resolution";
                            }

                        } // container resolution-filter

                    } // list family

                } // container tunnel-next-hop

            } // container igp-shortcut

            list interface {
                key "interface-name";
                description "Enter the interface list instance";

                leaf interface-name {
                    type types-sros:interface-name;
                    description "Router interface name";
                }

                leaf admin-state {
                    type types-sros:admin-state;
                    default "enable";
                    description "Administrative state of interface";
                }

                leaf hello-authentication-key {
                    type types-sros:encrypted-leaf {
                        length "1..366";
                    }
                    description "Authentication key or hash string for Hello PDUs";
                }

                leaf hello-authentication-keychain {
                    type leafref {
                        path "../../../../system/security/keychains/keychain/keychain-name";
                    }
                    description "Authentication keychain to use for the session.";
                }

                leaf hello-authentication-type {
                    type types-isis:auth-type;
                    description "Hello authentication type";
                }

                leaf hello-padding {
                    type types-isis:hello-padding-type;
                    description "Padding on IS-IS Hello packets";
                }

                leaf passive {
                    type boolean;
                    default "false";
                    description "Passive interface";
                }

                leaf csnp-interval {
                    type uint32 {
                        range "1..65535";
                    }
                    units "seconds";
                    default "10";
                    description "Time interval between successive CSN PDUs sent from interface";
                }

                leaf default-instance {
                    type boolean;
                    default "false";
                    description "Allow non-MI capable router to establish an adjacency and operate with a router in non-zero instance";
                }

                leaf hello-authentication {
                    type boolean;
                    default "true";
                    description "Authenticate individual IS-IS protocol packets of Hello type";
                }

                leaf interface-type {
                    type types-isis:interface-type;
                    description "Interface type to broadcast, point-to-point, or to be default";
                }

                leaf ipv4-multicast {
                    type boolean;
                    default "true";
                    description "Clear IPv4 multicast routing for interface";
                }

                leaf ipv6-multicast {
                    type boolean;
                    default "true";
                    description "Clear IPv4 multicast routing for interface";
                }

                leaf ipv6-unicast {
                    type boolean;
                    default "true";
                    description "Clear IPv4 multicast routing for interface";
                }

                leaf level-capability {
                    type types-isis:level;
                    description "IS-IS levels for this interface";
                }

                leaf load-balancing-weight {
                    type uint32;
                    description "Load balancing weight";
                }

                leaf lsp-pacing-interval {
                    type uint32 {
                        range "0..65535";
                    }
                    units "milliseconds";
                    default "100";
                    description "Interval for sending LSPs from interface";
                }

                leaf retransmit-interval {
                    type uint32 {
                        range "1..65535";
                    }
                    units "seconds";
                    default "5";
                    description "Minimum time between LSP PDU retransmissions on point-to-point interface";
                }

                leaf sid-protection {
                    type boolean;
                    default "true";
                    description "Allow adjacency SID protection by LFA and remote LFA";
                }

                leaf tag {
                    type uint32 {
                        range "1..max";
                    }
                    description "Route tag for IP address of interface";
                }

                leaf-list apply-groups {
                    type leafref {
                        path "../../../../groups/group/name";
                    }
                    max-elements 8;
                    ordered-by user;
                    description "Apply a configuration group at this level";
                }

                container ipv4-adjacency-sid {
                    presence "Assign IPv4 static adjacency sid to interface";
                    description "Enter the ipv4-adjacency-sid context";

                    choice type {
                        case label {

                            leaf label {
                                type int64 {
                                    range "1..1048575";
                                }
                                description "Adjacency SID";
                            }

                        }
                    }
                } // container ipv4-adjacency-sid

                container ipv6-adjacency-sid {
                    presence "Assign IPv6 static adjacency sid to interface";
                    description "Enter the ipv6-adjacency-sid context";

                    choice type {
                        case label {

                            leaf label {
                                type int64 {
                                    range "1..1048575";
                                }
                                description "Adjacency SID";
                            }

                        }
                    }
                } // container ipv6-adjacency-sid

                container loopfree-alternate {
                    description "Enter the loopfree-alternate context";

                    leaf exclude {
                        type boolean;
                        default "false";
                        description "Enable/disable Loopfree Alternative at interface level.";
                    }

                    container policy-map {
                        presence "Configure a route-next-hop template";
                        description "Enter the policy-map context";

                        leaf route-nh-template {
                            type leafref {
                                path "../../../../../../routing-options/route-next-hop-policy/template/template-name";
                            }
                            mandatory true;
                            description "Route next hop policy template that is applied to interface";
                        }

                    } // container policy-map

                } // container loopfree-alternate

                container mesh-group {
                    presence "Configure mesh groups";
                    description "Enter the mesh-group context";

                    choice type {
                        case value {

                            leaf value {
                                type int32 {
                                    range "1..2000000000";
                                }
                                description "Mesh group for the interface";
                            }

                        }
                        case blocked {

                            leaf blocked {
                                type empty;
                                description "Prevent the interface from flooding LSPs";
                            }

                        }
                    }
                } // container mesh-group

                container bfd-liveness {
                    description "Enter the bfd-liveness context";

                    container ipv4 {
                        presence "Enable BFD for IPv4";
                        description "Enter the ipv4 context";

                        leaf include-bfd-tlv {
                            type boolean;
                            default "false";
                            description "BFD-enabled TLV for IPv4 to include on this IS-IS interface";
                        }

                    } // container ipv4

                    container ipv6 {
                        presence "Enable BFD for IPv6";
                        description "Enter the ipv6 context";

                        leaf include-bfd-tlv {
                            type boolean;
                            default "false";
                            description "BFD-enabled TLV for IPv4 to include on this IS-IS interface";
                        }

                    } // container ipv6

                } // container bfd-liveness

                container ipv4-node-sid {
                    presence "Configure IPv4 node SID for this interface";
                    description "Enter the ipv4-node-sid context";

                    leaf clear-n-flag {
                        type boolean;
                        default "false";
                        description "Clear the node-sid flag (N-flag)";
                    }

                    choice type {
                        case label {

                            leaf label {
                                type int64 {
                                    range "1..4294967295";
                                }
                                description "Specifies IPvX node SID label for this interface.";
                            }

                        }
                        case index {

                            leaf index {
                                type int64 {
                                    range "0..4294967295";
                                }
                                description "IPvX node SID index for this interface";
                            }

                        }
                    }
                } // container ipv4-node-sid

                container ipv6-node-sid {
                    presence "Configure IPv6 node SID for this interface";
                    description "Enter the ipv6-node-sid context";

                    leaf clear-n-flag {
                        type boolean;
                        default "false";
                        description "Clear the node-sid flag (N-flag)";
                    }

                    choice type {
                        case label {

                            leaf label {
                                type int64 {
                                    range "1..4294967295";
                                }
                                description "Specifies IPvX node SID label for this interface.";
                            }

                        }
                        case index {

                            leaf index {
                                type int64 {
                                    range "0..4294967295";
                                }
                                description "IPvX node SID index for this interface";
                            }

                        }
                    }
                } // container ipv6-node-sid

                list adjacency-set {
                    key "id";
                    description "Add a list entry for adjacency-set";

                    leaf id {
                        type leafref {
                            path "../../../segment-routing/adjacency-set/id";
                        }
                        description "Adjacency set identity";
                    }

                } // list adjacency-set

                list level {
                    key "level-number";
                    max-elements 2;
                    description "Enter the level list instance";

                    leaf level-number {
                        type enumeration {
                            enum "1"                            { value 1; }
                            enum "2"                            { value 2; }
                        }
                        description "IS-IS protocol level to which these attributes apply";
                    }

                    leaf hello-authentication-key {
                        type types-sros:encrypted-leaf {
                            length "1..366";
                        }
                        description "Authentication or hash key string.";
                    }

                    leaf hello-authentication-keychain {
                        type leafref {
                            path "../../../../../system/security/keychains/keychain/keychain-name";
                        }
                        description "Authentication keychain to use for the session.";
                    }

                    leaf hello-authentication-type {
                        type types-isis:auth-type;
                        description "Hello-authentication-type to be enabled.";
                    }

                    leaf hello-padding {
                        type types-isis:hello-padding-type;
                        description "Padding on IS-IS Hello packets";
                    }

                    leaf passive {
                        type boolean;
                        default "false";
                        description "Passive interface";
                    }

                    leaf hello-interval {
                        type uint32 {
                            range "1..20000";
                        }
                        units "seconds";
                        default "9";
                        description "Interval between Hello messages sent on this level";
                    }

                    leaf hello-multiplier {
                        type int32 {
                            range "2..100";
                        }
                        default "3";
                        description "Hello messages missed from neighbor before router declares adjacency down";
                    }

                    leaf ipv4-multicast-metric {
                        type types-isis:metric;
                        description "IS-IS interface metric applied for IPv4 multicast";
                    }

                    leaf ipv6-multicast-metric {
                        type types-isis:metric;
                        description "IS-IS interface metric applied for IPv6 multicast";
                    }

                    leaf ipv6-unicast-metric {
                        type types-isis:metric;
                        description "IS-IS interface metric applied for IPv6 unicast";
                    }

                    leaf metric {
                        type types-isis:metric;
                        description "IS-IS interface metric applied for IPv4 unicast";
                    }

                    leaf priority {
                        type uint32 {
                            range "0..127";
                        }
                        default "64";
                        description "Router to become the designated router on a multi-access network";
                    }

                    leaf sd-offset {
                        type types-isis:metric;
                        description "Value of the signal degrade offset";
                    }

                    leaf sf-offset {
                        type types-isis:metric;
                        description "Value of the signal fail offset";
                    }

                    leaf-list apply-groups {
                        type leafref {
                            path "../../../../../groups/group/name";
                        }
                        max-elements 8;
                        ordered-by user;
                        description "Apply a configuration group at this level";
                    }

                } // list level

            } // list interface

            list level {
                key "level-number";
                max-elements 2;
                description "Enter the level list instance";

                leaf level-number {
                    type enumeration {
                        enum "1"                            { value 1; }
                        enum "2"                            { value 2; }
                    }
                    description "IS-IS protocol level to which these attributes apply";
                }

                leaf authentication-keychain {
                    type leafref {
                        path "../../../../system/security/keychains/keychain/keychain-name";
                    }
                    description "The keychain used to sign and/or authenticate.";
                }

                leaf authentication-key {
                    type types-sros:encrypted-leaf {
                        length "1..366";
                    }
                    description "Authentication or hash key string.";
                }

                leaf authentication-type {
                    type types-isis:auth-type;
                    description "Configure the authentication type to be used.";
                }

                leaf csnp-authentication {
                    type boolean;
                    default "true";
                    description "Enable/disable authentication on received ISIS protocol packets of type CSNP.";
                }

                leaf psnp-authentication {
                    type boolean;
                    default "true";
                    description "Enable/disable authentication on received ISIS protocol packets of type PSNP.";
                }

                leaf advertise-router-capability {
                    type boolean;
                    default "true";
                    description "Allow router advertisement capabilities";
                }

                leaf database-export-exclude {
                    type boolean;
                    default "false";
                    description "Exclude IGP link-state information of a specific IS-IS level from being exported into extended TE-DB";
                }

                leaf default-ipv4-multicast-metric {
                    type types-isis:metric;
                    default "10";
                    description "Default metric for IPv4 unicast";
                }

                leaf default-ipv6-multicast-metric {
                    type types-isis:metric;
                    default "10";
                    description "Default metric for IPv6 unicast";
                }

                leaf default-ipv6-unicast-metric {
                    type types-isis:metric;
                    default "10";
                    description "Default metric for IPv6 unicast";
                }

                leaf default-metric {
                    type types-isis:metric;
                    default "10";
                    description "Default metric";
                }

                leaf external-preference {
                    type uint32 {
                        range "1..255";
                    }
                    description "External route preference for IS-IS level";
                }

                leaf hello-authentication {
                    type boolean;
                    default "true";
                    description "Authenticate individual IS-IS protocol packets of Hello type";
                }

                leaf hello-padding {
                    type types-isis:hello-padding-type;
                    description "Padding on IS-IS Hello packets";
                }

                leaf loopfree-alternate-exclude {
                    type boolean;
                    default "false";
                    description "Exclude interface participating in specific IS-IS level in SPF LFA computation";
                }

                leaf lsp-mtu-size {
                    type types-isis:lsp-buffer-ext-size;
                    units "bytes";
                    sros-ext:manual-restart-to-modify;
                    default "1492";
                    description "LSP MTU size";
                }

                leaf preference {
                    type uint32 {
                        range "1..255";
                    }
                    description "External route preference at level";
                }

                leaf wide-metrics-only {
                    type boolean;
                    default "false";
                    description "Use wide metrics advertisements in the LSPs";
                }

                leaf-list apply-groups {
                    type leafref {
                        path "../../../../groups/group/name";
                    }
                    max-elements 8;
                    ordered-by user;
                    description "Apply a configuration group at this level";
                }

                container bier {
                    description "Enter the bier context";

                    leaf admin-state {
                        type types-sros:admin-state;
                        default "disable";
                        description "Administrative state of BIER";
                    }

                    leaf template {
                        type leafref {
                            path "../../../../bier/template/template-name";
                        }
                        description "Specify BIER template name.";
                    }

                } // container bier

            } // list level

            list link-group {
                key "link-group-name";
                description "Enter the link-group list instance";

                leaf link-group-name {
                    type types-sros:named-item;
                    description "Link group name for the IS-IS protocol";
                }

                leaf description {
                    type types-sros:very-long-description;
                    description "Text description";
                }

                leaf-list apply-groups {
                    type leafref {
                        path "../../../../groups/group/name";
                    }
                    max-elements 8;
                    ordered-by user;
                    description "Apply a configuration group at this level";
                }

                list level {
                    key "level-number";
                    max-elements 2;
                    description "Enter the level list instance";

                    leaf level-number {
                        type enumeration {
                            enum "1"                            { value 1; }
                            enum "2"                            { value 2; }
                        }
                        description "IS-IS protocol level to which these attributes apply";
                    }

                    leaf ipv4-multicast-metric-offset {
                        type types-isis:metric;
                        description "Offset value for the IPv4 multicast address family";
                    }

                    leaf ipv4-unicast-metric-offset {
                        type types-isis:metric;
                        description "Offset value for the IPv4 unicast address family";
                    }

                    leaf ipv6-multicast-metric-offset {
                        type types-isis:metric;
                        description "Offset value for the IPv6 multicast address family";
                    }

                    leaf ipv6-unicast-metric-offset {
                        type types-isis:metric;
                        description "Offset value for the IPv6 unicast address family";
                    }

                    leaf oper-members {
                        type uint32 {
                            range "1..8";
                        }
                        description "Minimum number of operational links";
                    }

                    leaf revert-members {
                        type uint32 {
                            range "1..8";
                        }
                        description "Minimum number of operational links to return link group to normal state and remove offsets";
                    }

                    leaf-list apply-groups {
                        type leafref {
                            path "../../../../../groups/group/name";
                        }
                        max-elements 8;
                        ordered-by user;
                        description "Apply a configuration group at this level";
                    }

                    list member {
                        key "interface-name";
                        max-elements 8;
                        description "Add a list entry for member";

                        leaf interface-name {
                            type leafref {
                                path "../../../../interface/interface-name";
                            }
                            description "Router interface name for this link group";
                        }

                    } // list member

                } // list level

            } // list link-group

            list summary-address {
                key "ip-prefix";
                description "Enter the summary-address list instance";

                leaf ip-prefix {
                    type types-sros:ip-prefix;
                    description "Summary IP prefix";
                }

                leaf level-capability {
                    type types-isis:level;
                    description "IS-IS Level from which the prefix should be summarized";
                }

                leaf route-tag {
                    type uint32 {
                        range "1..max";
                    }
                    description "Route tag assigned to the summary address";
                }

                leaf-list apply-groups {
                    type leafref {
                        path "../../../../groups/group/name";
                    }
                    max-elements 8;
                    ordered-by user;
                    description "Apply a configuration group at this level";
                }

            } // list summary-address

        } // list isis

    } // grouping conf-router-isis

}
