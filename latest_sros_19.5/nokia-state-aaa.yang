submodule nokia-state-aaa {

    yang-version "1.1";

    belongs-to nokia-state { prefix "state"; }

    import ietf-inet-types                { prefix "inet"; }
    import ietf-yang-types                { prefix "yang"; }
    import nokia-sros-yang-extensions     { prefix "sros-ext"; }
    import nokia-types-diameter           { prefix "types-diam"; }
    import nokia-types-nat                { prefix "types-nat"; }
    import nokia-types-services           { prefix "types-services"; }
    import nokia-types-sros               { prefix "types-sros"; }


    sros-ext:sros-major-release "rel19";

    organization "Nokia";

    contact
        "Nokia SR OS Support
         Web: <http://www.nokia.com>";

    description
        "Nokia YANG Data model with operational state for authentication, authorization and accounting on SR OS based routers.

         Copyright 2016 Nokia. All rights reserved. Reproduction of this document
         is authorized on the condition that the foregoing copyright notice is included.

         This nokia-state-aaa YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-04-05";

    grouping state-aaa {
        container aaa {
            description "Enter the aaa context";

            container radius {
                description "Enter the radius context";

                list server-policy {
                    key "name";
                    description "Enter the server-policy context";

                    leaf name {
                        type types-sros:named-item;
                        description "RADIUS script policy name";
                    }

                    leaf blocked-state {
                        type enumeration {
                            enum "not-blocked"                  { value 0; }
                            enum "blocked"                      { value 1; }
                        }
                        description "Indicates whether or not the RADIUS server policy is blocked by the acct-on-off functions.";
                    }

                    container servers {
                        description "Enter the servers context";

                        list server {
                            key "server-index";
                            description "Enter the server context";

                            leaf server-index {
                                type uint32 {
                                    range "1..16";
                                }
                                description "RADIUS server index";
                            }

                            leaf oper-state {
                                type enumeration {
                                    enum "unknown"                      { value 1; }
                                    enum "in-service"                   { value 2; }
                                    enum "out-of-service"               { value 3; }
                                    enum "transition"                   { value 4; }
                                    enum "overloaded"                   { value 5; }
                                    enum "probing"                      { value 6; }
                                }
                                description "Operational state of RADIUS server";
                            }

                            leaf out-of-service-time {
                                type types-sros:time-duration;
                                description "Number of seconds that RADIUS server was out-of-service";
                            }

                            leaf overload-time {
                                type types-sros:time-duration;
                                description "Number of seconds that RADIUS server was overloaded";
                            }

                            container statistics {
                                description "Statistics about a specific server of a specific RADIUS server policy.";

                                container tx-request {
                                    description "Statistics about RADIUS request packets transmitted for this server.";

                                    leaf total-packets {
                                        type yang:counter32;
                                        description "The total number of RADIUS request packets transmitted for this server.";
                                    }

                                    leaf pending {
                                        type yang:counter32;
                                        description
                                            "The number of RADIUS request packets that are currently waiting
                                             for reply from this server.";
                                    }

                                    leaf timeout {
                                        type yang:counter32;
                                        description "The number of RADIUS request packets that have timed out for this server.";
                                    }

                                    leaf failed {
                                        type yang:counter32;
                                        description
                                            "The number of RADIUS request packets that could not be transmitted
                                             for this server.";
                                    }

                                    leaf failed-out-of-ids {
                                        type yang:counter32;
                                        description
                                            "The number of RADIUS request packets that could not be
                                             transmitted due to out of ids";
                                    }

                                } // container tx-request

                                container rx-response {
                                    description "Statistics about RADIUS response packets received from this server.";

                                    leaf total-packets {
                                        type yang:counter32;
                                        description "The total number of RADIUS response packets received from this server.";
                                    }

                                    leaf invalid-authenticator {
                                        type yang:counter32;
                                        description
                                            "The number of RADIUS response packets with an invalid Authenticator
                                             received from this server.";
                                    }

                                    leaf invalid-message-authenticator-attribute {
                                        type yang:counter32;
                                        description
                                            "The number of RADIUS response packets with an invalid Message-Authenticator
                                             attribute received from this server.";
                                    }

                                } // container rx-response

                                container accounting {
                                    description "Statistics related to accounting messages.";

                                    leaf failed {
                                        type yang:counter32;
                                        description "The number of accounting failures for this server.";
                                    }

                                    container average-delay {
                                        description "The average delay for the last accounting packets.";

                                        leaf last-10-packets {
                                            type yang:gauge32;
                                            description
                                                "This indicates (in microseconds) the average response delay
                                                 for the last 10 accounting packets.";
                                        }

                                        leaf last-100-packets {
                                            type yang:gauge32;
                                            description
                                                "This indicates (in microseconds) the average response delay
                                                 for the last 100 accounting packets.";
                                        }

                                        leaf last-1000-packets {
                                            type yang:gauge32;
                                            description
                                                "This indicates (in microseconds) the average response delay
                                                 for the last 1000 accounting packets.";
                                        }

                                        leaf last-10000-packets {
                                            type yang:gauge32;
                                            description
                                                "This indicates (in microseconds) the average response delay
                                                 for the last 10000 accounting packets.";
                                        }

                                    } // container average-delay

                                } // container accounting

                                container authentication {
                                    description "Statistics related to authentication messages.";

                                    leaf failed {
                                        type yang:counter32;
                                        description "The number of authentication failures for this server.";
                                    }

                                    container average-delay {
                                        description "The average delay for the last authentication packets.";

                                        leaf last-10-packets {
                                            type yang:gauge32;
                                            description
                                                "This indicates (in microseconds) the average response delay
                                                 for the last 10 authentication packets.";
                                        }

                                        leaf last-100-packets {
                                            type yang:gauge32;
                                            description
                                                "This indicates (in microseconds) the average response delay
                                                 for the last 100 authentication packets.";
                                        }

                                        leaf last-1000-packets {
                                            type yang:gauge32;
                                            description
                                                "This indicates (in microseconds) the average response delay
                                                 for the last 1000 authentication packets.";
                                        }

                                        leaf last-10000-packets {
                                            type yang:gauge32;
                                            description
                                                "This indicates (in microseconds) the average response delay
                                                 for the last 10000 authentication packets.";
                                        }

                                    } // container average-delay

                                } // container authentication

                            } // container statistics

                        } // list server

                    } // container servers

                    container acct-on-off {
                        description "Enter the acct-on-off context";

                        leaf oper-state {
                            type enumeration {
                                enum "not-applicable"               { value 0; }
                                enum "off"                          { value 1; }
                                enum "off-no-response"              { value 2; }
                                enum "on"                           { value 3; }
                                enum "sending-acct-on"              { value 4; }
                                enum "sending-acct-off"             { value 5; }
                            }
                            description "Indicates the operational state related to the sending of RADIUS Accounting-On and Accounting-Off messages for this RADIUS server policy.";
                        }

                        leaf session-id {
                            type types-sros:display-string-or-empty;
                            description "Indicates the accounting session id used in the RADIUS Accounting-On and Accounting-Off messages sent for this RADIUS server policy.";
                        }

                        leaf trigger {
                            type enumeration {
                                enum "not-applicable"               { value 0; }
                                enum "start-up"                     { value 1; }
                                enum "tools"                        { value 2; }
                                enum "tools-forced"                 { value 3; }
                                enum "reboot"                       { value 4; }
                                enum "group"                        { value 5; }
                            }
                            description "Indicates the event that caused the most recent operational state change as defined in oper-state.";
                        }

                        leaf server-name {
                            type types-sros:named-item-or-empty;
                            description "Indicates the name of the RADIUS server from which the most recent RADIUS response has been received.";
                        }

                        leaf retry-count {
                            type uint32;
                            description "Indicates the number of times the acct-on client has already sent a new RADIUS Accounting-On message after no accounting response was received in time.";
                        }

                    } // container acct-on-off

                    container statistics {
                        description "Statistics about a particular RADIUS server policy.";

                        leaf tx-request {
                            type yang:counter32;
                            description "The number of RADIUS transaction requests transmitted.";
                        }

                        leaf rx-response {
                            type yang:counter32;
                            description "The number of RADIUS transaction responses received.";
                        }

                        leaf request-timeout {
                            type yang:counter32;
                            description "The number of RADIUS transaction requests that have timed out.";
                        }

                        leaf request-send-fail {
                            type yang:counter32;
                            description "The number of RADIUS transaction requests that could not be transmitted.";
                        }

                        leaf request-send-retry {
                            type yang:counter32;
                            description "The number of times a RADIUS request packet was retransmitted to a server.";
                        }

                        leaf request-rejected {
                            type yang:counter32;
                            description "The number of RADIUS transaction requests rejected";
                        }

                        leaf accounting-fail {
                            type yang:counter32;
                            description "The number of accounting failures for this policy.";
                        }

                        leaf authentication-fail {
                            type yang:counter32;
                            description "The number of authentication failures for this policy.";
                        }

                        leaf access-reject-ratio {
                            type uint32 {
                                range "0..100";
                            }
                            description "The ratio of access-rejects in the authentication responses for this policy.";
                        }

                        leaf failure-ratio {
                            type uint32 {
                                range "0..100";
                            }
                            description "The transaction failure ratio for this policy.";
                        }

                        leaf success-ratio {
                            type uint32 {
                                range "0..100";
                            }
                            description "The transaction success ratio for this policy.";
                        }

                        container buffered-messages {
                            description
                                "Statistics related to RADIUS messages that are buffered for this
                                 Radius Server Policy.";

                            leaf accounting-interim {
                                type yang:counter32;
                                description "The number of buffered accounting interim update messages.";
                            }

                            leaf accounting-interim-drop {
                                type yang:counter32;
                                description
                                    "The number of accounting interim update messages dropped from
                                     the buffer because their lifetime expired.";
                            }

                            leaf accounting-stop {
                                type yang:counter32;
                                description "The number of buffered accounting stop messages.";
                            }

                            leaf accounting-stop-drop {
                                type yang:counter32;
                                description
                                    "The number of accounting stop messages dropped from
                                     the buffer because their lifetime expired.";
                            }

                            leaf last-cleared {
                                type yang:date-and-time;
                                description "The time of the most recent reset (empty) of the message buffer.";
                            }

                            leaf statistics-last-cleared {
                                type yang:date-and-time;
                                description "The time of the most recent reset of the message buffer statistics.";
                            }

                        } // container buffered-messages

                    } // container statistics

                } // list server-policy

                list route-downloader {
                    key "name";
                    description "Enter the route-downloader context";

                    leaf name {
                        type types-sros:named-item;
                        description "Route downloader name";
                    }

                    container statistics {
                        description "Statistics about a particular RADIUS Route Downloader";

                        leaf last-access-reject-received {
                            type yang:date-and-time;
                            description
                                "When this RADIUS Route Downloader last received a RADIUS
                                 Access-Reject packet";
                        }

                        leaf last-access-accept-received {
                            type yang:date-and-time;
                            description
                                "When this RADIUS Route Downloader last received a RADIUS
                                 Access-Accept packet";
                        }

                        leaf last-access-request-sent {
                            type yang:date-and-time;
                            description
                                "When this RADIUS Route Downloader last sent a RADIUS
                                 Access-Request packet";
                        }

                        leaf last-access-request-retried {
                            type yang:date-and-time;
                            description
                                "When this RADIUS Route Downloader last retried a RADIUS
                                 Access-Request packet";
                        }

                        leaf remaining-time-before-next-download-attempt {
                            type types-sros:time-interval;
                            description "The remaining time before the next download attempt";
                        }

                        leaf remaining-time-before-next-download-retry {
                            type types-sros:time-interval;
                            description "The remaining time before the next download retry";
                        }

                        leaf routes-received-count {
                            type yang:counter32;
                            description
                                "The number of routes received in the last completed
                                 route download process";
                        }

                        leaf access-reject-received-count {
                            type yang:counter32;
                            description
                                "The number of Access-Reject packets received
                                 by this RADIUS Route Downloader";
                        }

                        leaf access-accept-received-count {
                            type yang:counter32;
                            description
                                "The number of Access-Accept packets received
                                 by this RADIUS Route Downloader";
                        }

                        leaf access-accept-dropped-count {
                            type yang:counter32;
                            description
                                "The number of Access-Accept packets received but dropped
                                 by this RADIUS Route Downloader";
                        }

                        leaf access-request-sent-count {
                            type yang:counter32;
                            description
                                "The number of Access-Request packets sent
                                 by this RADIUS Route Downloader";
                        }

                        leaf access-request-retried-count {
                            type yang:counter32;
                            description
                                "The number of Access-Request packets retried
                                 by this RADIUS Route Downloader";
                        }

                        leaf download-count {
                            type yang:counter32;
                            description
                                "The number of downloads started
                                 by this RADIUS Route Downloader";
                        }

                        leaf route-failed-to-install-count {
                            type yang:counter32;
                            description
                                "The number of times installing received routes failed
                                 for this RADIUS Route Downloader";
                        }

                    } // container statistics

                } // list route-downloader

                list isa-policy {
                    key "name";
                    description "Enter the isa-policy context";

                    leaf name {
                        type types-sros:named-item;
                        description "Policy name";
                    }

                    container servers {
                        description "Enter the servers context";

                        leaf source-address-range-end {
                            type types-sros:ipv4-unicast-address;
                            description "End of the source address range of the RADIUS messages";
                        }

                        list server {
                            key "index";
                            description "Enter the server context";

                            leaf index {
                                type uint32 {
                                    range "1..10";
                                }
                                description "RADIUS server index that determines sequence in which servers are queried for auth requests";
                            }

                            list group-member {
                                key "group-id member-id";
                                description "Status information about the connections with ISA RADIUS servers.";

                                leaf group-id {
                                    type uint32;
                                    description "The identifier of the Integrated Service Adaptor group.";
                                }

                                leaf member-id {
                                    type types-nat:bb-group-member;
                                    description "The identifier of the ISA Group member.";
                                }

                                leaf source-address {
                                    type types-sros:ipv4-address;
                                    description
                                        "The source IP address used by this member for this connection
                                         with this RADIUS server.";
                                }

                                leaf purpose {
                                    type bits {
                                        bit accounting                     { position 0; }
                                        bit authentication                 { position 1; }
                                        bit coa                            { position 2; }
                                    }
                                    description "Purpose of this RADIUS server on this group member.";
                                }

                                list statistics {
                                    key "type";
                                    description "Statistical information about a connection with a particular RADIUS server.";

                                    leaf type {
                                        type uint32;
                                        description "The (numerical) type of ISA RADIUS server statistics.";
                                    }

                                    leaf type-name {
                                        type types-sros:display-string {
                                            length "1..64";
                                        }
                                        description "The human-readable identifier of the statistics.";
                                    }

                                    leaf value {
                                        type yang:counter32;
                                        description "The value of the statistics.";
                                    }

                                } // list statistics

                            } // list group-member

                        } // list server

                    } // container servers

                } // list isa-policy

                container statistics {
                    description "System wide radius statistics";

                    container coa {
                        description "Change-of-Authorization messages statistics";

                        leaf received {
                            type yang:counter32;
                            description "The number of Change-of-Authorization requests received.";
                        }

                        leaf accepted {
                            type yang:counter32;
                            description "The number of Change-of-Authorization requests accepted.";
                        }

                        leaf rejected {
                            type yang:counter32;
                            description "The number of Change-of-Authorization requests rejected.";
                        }

                        container dropped {
                            description "Dropped Change-of-Authorization message statistics";

                            leaf bad-authentication {
                                type yang:counter32;
                                description
                                    "The number of Change-of-Authorization requests rejected
                                     because of authentication failure.";
                            }

                            leaf missing-auth-policy {
                                type yang:counter32;
                                description
                                    "The number of Change-of-Authorization requests rejected
                                     due to missing authentication policy.";
                            }

                            leaf invalid {
                                type yang:counter32;
                                description
                                    "The number of Change-of-Authorization requests rejected
                                     because of decode errors.";
                            }

                            leaf missing-resource {
                                type yang:counter32;
                                description
                                    "The number of Change-of-Authorization requests rejected
                                     due to lack of resources.";
                            }

                        } // container dropped

                    } // container coa

                    container disconnect-messages {
                        description "Disconnect messages statistics";

                        leaf received {
                            type yang:counter32;
                            description "The number of disconnect requests received.";
                        }

                        leaf accepted {
                            type yang:counter32;
                            description "The number of disconnect requests accepted.";
                        }

                        leaf rejected {
                            type yang:counter32;
                            description "The number of disconnect requests rejected.";
                        }

                        container dropped {
                            description "Dropped disconnect message statistics";

                            leaf bad-authentication {
                                type yang:counter32;
                                description
                                    "The number of disconnect requests rejected
                                     because of authentication failure.";
                            }

                            leaf missing-auth-policy {
                                type yang:counter32;
                                description
                                    "The number of disconnect requests rejected
                                     due to missing authentication policy.";
                            }

                            leaf invalid {
                                type yang:counter32;
                                description
                                    "The number of disconnect requests rejected
                                     because of decode errors.";
                            }

                            leaf missing-resource {
                                type yang:counter32;
                                description
                                    "The number of disconnect requests rejected
                                     due to lack of resources.";
                            }

                        } // container dropped

                    } // container disconnect-messages

                } // container statistics

            } // container radius

            container diameter {
                description "Enter the diameter context";

                list node {
                    key "origin-host";
                    description "Enter the node context";

                    leaf origin-host {
                        type types-diam:diam-fqdn;
                        description "Origin-host name.";
                    }

                    leaf realm {
                        type string {
                            length "1..80";
                        }
                        description "The operational realm of this Diameter node.";
                    }

                    list peer {
                        key "index";
                        description "Enter the peer context";

                        leaf index {
                            type uint32 {
                                range "1..5";
                            }
                            description "Index of this peer within the Node.";
                        }

                        leaf state {
                            type types-diam:diam-peer-state;
                            description "The current state of the Diameter peer's state machine";
                        }

                        leaf active {
                            type boolean;
                            description
                                "Indicates if the Diameter peer can be actively used by
                                 Diameter applications";
                        }

                        leaf disconnect-cause {
                            type enumeration {
                                enum "rebooting"                    { value 0; }
                                enum "busy"                         { value 1; }
                                enum "stop"                         { value 2; }
                            }
                            description "The most recent disconnect cause";
                        }

                        leaf connection-time-left {
                            type uint32;
                            units "seconds";
                            description "Current time left of the connection timer";
                        }

                        leaf watchdog-time-left {
                            type uint32;
                            units "seconds";
                            description "Current time left of the watchdog timer";
                        }

                        leaf pending-messages-on-queue {
                            type uint32;
                            description
                                "The number of requests to be matched with the corresponding
                                 answers from the peer on the pending message queue";
                        }

                        container remote {
                            description "Information learned from the remote peer";

                            leaf realm {
                                type string {
                                    length "1..80";
                                }
                                description "The realm of the remote peer";
                            }

                            leaf origin-state-id {
                                type uint32;
                                description "The value of the remote peer's Origin-State-Id AVP";
                            }

                        } // container remote

                        container local {
                            description "Information regarding local peer";

                            leaf address {
                                type types-sros:ip-unicast-address;
                                description "The local IP address of the connection";
                            }

                            leaf tcp-port {
                                type types-sros:tcp-udp-port-non-zero;
                                description "The local TCP port of the connection";
                            }

                        } // container local

                        container application {
                            description
                                "The negotiated set of applications that can be used on this
                                 connection";

                            leaf nasreq {
                                type boolean;
                                description
                                    "Indicates if the NASREQ application is supported on this
                                     connection";
                            }

                            leaf gy {
                                type boolean;
                                description
                                    "Indicates if the Gy application is supported on this
                                     connection";
                            }

                            leaf gx {
                                type boolean;
                                description
                                    "Indicates if the Gx application is supported on this
                                     connection";
                            }

                            leaf relay {
                                type boolean;
                                description "Indicates that the peer is a relay agent";
                            }

                        } // container application

                        container statistics {
                            description "Statistics";

                            leaf last-cleared {
                                type yang:date-and-time;
                                description "When the statistics were last cleared";
                            }

                            container transmit {
                                description "The number of transmitted messages";

                                container request {
                                    description "The number of request messages";

                                    leaf capability-exchange {
                                        type yang:counter64;
                                        description "The number of Capability-Exchange messages";
                                    }

                                    leaf disconnect-peer {
                                        type yang:counter64;
                                        description "The number of Disconnect-Peer messages";
                                    }

                                    leaf device-watchdog {
                                        type yang:counter64;
                                        description "The number of Device-Watchdog messages";
                                    }

                                    leaf application {
                                        type yang:counter64;
                                        description "The number of application messages";
                                    }

                                } // container request

                                container answer {
                                    description "The number of answer messages";

                                    leaf capability-exchange {
                                        type yang:counter64;
                                        description "The number of Capability-Exchange messages";
                                    }

                                    leaf disconnect-peer {
                                        type yang:counter64;
                                        description "The number of Disconnect-Peer messages";
                                    }

                                    leaf device-watchdog {
                                        type yang:counter64;
                                        description "The number of Device-Watchdog messages";
                                    }

                                    leaf application {
                                        type yang:counter64;
                                        description "The number of application messages";
                                    }

                                } // container answer

                            } // container transmit

                            container receive {
                                description "The number of received messages";

                                container request {
                                    description "The number of request messages";

                                    leaf capability-exchange {
                                        type yang:counter64;
                                        description "The number of Capability-Exchange messages";
                                    }

                                    leaf disconnect-peer {
                                        type yang:counter64;
                                        description "The number of Disconnect-Peer messages";
                                    }

                                    leaf device-watchdog {
                                        type yang:counter64;
                                        description "The number of Device-Watchdog messages";
                                    }

                                    leaf application {
                                        type yang:counter64;
                                        description "The number of application messages";
                                    }

                                } // container request

                                container answer {
                                    description "The number of answer messages";

                                    leaf capability-exchange {
                                        type yang:counter64;
                                        description "The number of Capability-Exchange messages";
                                    }

                                    leaf disconnect-peer {
                                        type yang:counter64;
                                        description "The number of Disconnect-Peer messages";
                                    }

                                    leaf device-watchdog {
                                        type yang:counter64;
                                        description "The number of Device-Watchdog messages";
                                    }

                                    leaf application {
                                        type yang:counter64;
                                        description "The number of application messages";
                                    }

                                } // container answer

                            } // container receive

                        } // container statistics

                    } // list peer

                } // list node

                list peer-policy {
                    key "name";
                    description "Enter the peer-policy context";

                    leaf name {
                        type types-sros:named-item;
                        description "Diameter peer policy name";
                    }

                    list peer {
                        key "peer-name";
                        description "Enter the peer context";

                        leaf peer-name {
                            type types-sros:named-item;
                            description "Name of peer in Diameter peer policy";
                        }

                        leaf psm-state {
                            type types-diam:diam-peer-state;
                            description "the current state of the DIAMETER peer's state machine.";
                        }

                        leaf connection-suspended {
                            type boolean;
                            description "indicates whether the peer's DIAMETER connection that is in I-Open state has been temporarily put on suspension.";
                        }

                        leaf cooldown-sequence-stage {
                            type enumeration {
                                enum "stage-0"                      { value 0; }
                                enum "stage-1"                      { value 1; }
                                enum "stage-2"                      { value 2; }
                                enum "stage-3"                      { value 3; }
                            }
                            description "While the value of cooldown-sequence-active is 'true', the value of tmnxDiamPeerCooldownSeqStage indicates the current stage of the cooling down sequence";
                        }

                        leaf order {
                            type union {
                                type enumeration {
                                    enum "not-applicable"               { value 0; }
                                }
                                type uint32 {
                                    range "1..4294967295";
                                }
                            }
                            description "the runtime order of the DIAMETER policy's peers. It is determined both by the configuration level preference and other runtime conditions.";
                        }

                        leaf primary-secondary {
                            type enumeration {
                                enum "none"                         { value 0; }
                                enum "primary"                      { value 1; }
                                enum "secondary"                    { value 2; }
                            }
                            description "indicates whether the DIAMETER peer figures as primary or secondary peer in its policy.";
                        }

                        leaf tc-timer-time-left {
                            type types-sros:time-duration;
                            units "seconds";
                            description "the current countdown progress of the DIAMETER peer's connection timer.";
                        }

                        leaf tt-timer-time-left {
                            type types-sros:time-duration;
                            units "seconds";
                            description "the current countdown progress of the DIAMETER peer's transaction timer.";
                        }

                        leaf tw-timer-time-left {
                            type types-sros:time-duration;
                            units "seconds";
                            description " the current countdown progress of the DIAMETER peer's watchdog timer.";
                        }

                        leaf watchdog-algorithm-active {
                            type boolean;
                            description "indicates whether the DIAMETER application-layer watchdog algorithm is currently running.";
                        }

                        leaf watchdog-answer-pending {
                            type boolean;
                            description
                                "indicates whether reception of a DIAMETER Device Watchdog Answer (DWA) is expected for a
                                 corresponding Device Watchdog Request (DWR) waiting in the Pending Message Queue.";
                        }

                        leaf cooldown-sequence-pending {
                            type boolean;
                            description " indicates whether the DIAMETER peer's connection manages to get in a non-suspended I-Open state.";
                        }

                        leaf cooldown-sequence-active {
                            type boolean;
                            description "indicates whether the DIAMETER Cooldown Sequence is currently running.";
                        }

                        leaf peer-removal-pending {
                            type boolean;
                            description "indicates whether the execution of a DIAMETER peer's removal is still pending until the disconnect-peer roundtrip has finished.";
                        }

                        leaf pending-messages-on-queue {
                            type uint32;
                            description "the number of requests to be matched with the corresponding answers from the server on the pending message queue.";
                        }

                        container statistics {
                            description "Enter the statistics context";

                            list messages {
                                key "direction message-type";
                                description "contains statistics information about the peers defined in a Diameter Policy";

                                leaf direction {
                                    type enumeration {
                                        enum "rx"                           { value 1; }
                                        enum "tx"                           { value 2; }
                                    }
                                    description
                                        "indicates which direction packets are travelling in the system :
                                             rx  - Packets are being received by the system.
                                             tx  - Packets are being transmitted from the system.";
                                }

                                leaf message-type {
                                    type enumeration {
                                        enum "request"                      { value 1; }
                                        enum "answer"                       { value 2; }
                                    }
                                    description "indicates whether this message is a Request Message or whether this message is an Answer Message.";
                                }

                                leaf last-cleared {
                                    type yang:date-and-time;
                                    description
                                        "indicates the system-up-time when the counters were last reset.
                                         A zero value indicates that the counters have not been reset since the system has last been initialized.";
                                }

                                leaf total-messages {
                                    type uint32;
                                    description "the total number of messages.";
                                }

                                leaf failed-messages {
                                    type uint32;
                                    description "the number of failed messages.";
                                }

                                leaf capability-exchange-messages {
                                    type uint32;
                                    description "the number of Capabilities-Exchange messages.";
                                }

                                leaf disconnect-peer-messages {
                                    type uint32;
                                    description "the number of Disconnect-Peer messages.";
                                }

                                leaf device-watchdog-messages {
                                    type uint32;
                                    description "the number of Device-Watchdog messages.";
                                }

                                leaf authentication-authorization-messages {
                                    type uint32;
                                    description "the number of AA messages.";
                                }

                                leaf gy-credit-control-initial-messages {
                                    type uint32;
                                    description "the number of DIAMETER Gy Credit Control messages with CC-Request-Type AVP equal to INITIAL_REQUEST.";
                                }

                                leaf gy-credit-control-update-messages {
                                    type uint32;
                                    description "the number of DIAMETER Gy Credit Control messages with CC-Request-Type AVP equal to UPDATE_REQUEST.";
                                }

                                leaf gy-credit-control-terminate-messages {
                                    type uint32;
                                    description "the number of DIAMETER Gy Credit Control messages with CC-Request-Type AVP equal to TERMINATION_REQUEST.";
                                }

                                leaf gy-re-authorization-messages {
                                    type uint32;
                                    description "the number of DIAMETER Gy Re-Auth messages.";
                                }

                                leaf gy-session-abbort-messages {
                                    type uint32;
                                    description "the number of DIAMETER Gy Abort-Session messages.";
                                }

                                leaf gx-credit-control-initial-messages {
                                    type uint32;
                                    description "the number of DIAMETER Gx Credit Control messages with CC-Request-Type AVP equal to INITIAL_REQUEST.";
                                }

                                leaf gx-credit-control-update-messages {
                                    type uint32;
                                    description "the number of DIAMETER Gx Credit Control messages with CC-Request-Type AVP equal to UPDATE_REQUEST.";
                                }

                                leaf gx-credit-control-terminate-messages {
                                    type uint32;
                                    description "the number of DIAMETER Gx Credit Control messages with CC-Request-Type AVP equal to TERMINATION_REQUEST.";
                                }

                                leaf gx-re-authorization-messages {
                                    type uint32;
                                    description "the number of DIAMETER Gx Re-Auth messages.";
                                }

                                leaf gx-session-abbort-messages {
                                    type uint32;
                                    description "the number of DIAMETER Gx Abort-Session messages.";
                                }

                            } // list messages

                        } // container statistics

                    } // list peer

                    container proxy {
                        description "Enter the proxy context";

                        leaf oper-state {
                            type enumeration {
                                enum "in-service"                   { value 1; }
                                enum "out-of-service"               { value 2; }
                            }
                            description "Proxy operational state.";
                        }

                        leaf local-state {
                            type types-diam:diam-proxy-mcs-state;
                            description "Proxy multi-chassis redundancy local State.";
                        }

                        leaf local-origin-state-id {
                            type uint32;
                            description "Proxy multi-chassis redundancy local Origin-State-Id.";
                        }

                        leaf local-mac-address {
                            type yang:mac-address;
                            description "Proxy multi-chassis redundancy local MAC address.";
                        }

                        leaf local-controller-mac-address {
                            type yang:mac-address;
                            description "Proxy multi-chassis redundancy local controller MAC address.";
                        }

                        leaf remote-state {
                            type types-diam:diam-proxy-mcs-state;
                            description "Proxy multi-chassis redundancy remote state.";
                        }

                        leaf remote-origin-state-id {
                            type uint32;
                            description "Proxy multi-chassis redundancy remote Origin-State-Id.";
                        }

                        leaf remote-mac-address {
                            type yang:mac-address;
                            description "Proxy multi-chassis redundancy remote MAC address.";
                        }

                        leaf remote-controller-mac-address {
                            type yang:mac-address;
                            description "Proxy multi-chassis redundancy remote controller MAC address.";
                        }

                        container statistics {
                            description "Enter the statistics context";

                            list client-side-messages {
                                key "ip-address port direction message-type";
                                description "contains statistics information about the client-side peers of the Diameter proxy instances";

                                leaf ip-address {
                                    type types-sros:ip-address;
                                    description "the source IP address from a client-side peer of a DIAMETER proxy instance.";
                                }

                                leaf port {
                                    type types-sros:tcp-udp-port;
                                    description "the TCP source port from a client-side peer of a DIAMETER proxy instance.";
                                }

                                leaf direction {
                                    type enumeration {
                                        enum "rx"                           { value 1; }
                                        enum "tx"                           { value 2; }
                                    }
                                    description
                                        "indicates which direction packets are travelling in the system :
                                             rx  - Packets are being received by the system.
                                             tx  - Packets are being transmitted from the system.";
                                }

                                leaf message-type {
                                    type enumeration {
                                        enum "request"                      { value 1; }
                                        enum "answer"                       { value 2; }
                                    }
                                    description "indicates whether this message is a Request Message or whether this message is an Answer Message.";
                                }

                                leaf last-cleared {
                                    type yang:date-and-time;
                                    description
                                        "indicates the system-up-time when the counters were last reset.
                                         A zero value indicates that the counters have not been reset since the system has last been initialized.";
                                }

                                leaf total-messages {
                                    type uint32;
                                    description "the total number of messages.";
                                }

                                leaf failed-messages {
                                    type uint32;
                                    description "the number of failed messages.";
                                }

                                leaf capability-exchange-messages {
                                    type uint32;
                                    description "the number of Capabilities-Exchange messages.";
                                }

                                leaf disconnect-peer-messages {
                                    type uint32;
                                    description "the number of Disconnect-Peer messages.";
                                }

                                leaf device-watchdog-messages {
                                    type uint32;
                                    description "the number of Device-Watchdog messages.";
                                }

                                leaf authentication-authorization-messages {
                                    type uint32;
                                    description "the number of AA messages.";
                                }

                                leaf gy-credit-control-initial-messages {
                                    type uint32;
                                    description "the number of DIAMETER Gy Credit Control messages with CC-Request-Type AVP equal to INITIAL_REQUEST.";
                                }

                                leaf gy-credit-control-update-messages {
                                    type uint32;
                                    description "the number of DIAMETER Gy Credit Control messages with CC-Request-Type AVP equal to UPDATE_REQUEST.";
                                }

                                leaf gy-credit-control-terminate-messages {
                                    type uint32;
                                    description "the number of DIAMETER Gy Credit Control messages with CC-Request-Type AVP equal to TERMINATION_REQUEST.";
                                }

                                leaf gy-re-authorization-messages {
                                    type uint32;
                                    description "the number of DIAMETER Gy Re-Auth messages.";
                                }

                                leaf gy-session-abbort-messages {
                                    type uint32;
                                    description "the number of DIAMETER Gy Abort-Session messages.";
                                }

                                leaf gx-credit-control-initial-messages {
                                    type uint32;
                                    description "the number of DIAMETER Gx Credit Control messages with CC-Request-Type AVP equal to INITIAL_REQUEST.";
                                }

                                leaf gx-credit-control-update-messages {
                                    type uint32;
                                    description "the number of DIAMETER Gx Credit Control messages with CC-Request-Type AVP equal to UPDATE_REQUEST.";
                                }

                                leaf gx-credit-control-terminate-messages {
                                    type uint32;
                                    description "the number of DIAMETER Gx Credit Control messages with CC-Request-Type AVP equal to TERMINATION_REQUEST.";
                                }

                                leaf gx-re-authorization-messages {
                                    type uint32;
                                    description "the number of DIAMETER Gx Re-Auth messages.";
                                }

                                leaf gx-session-abbort-messages {
                                    type uint32;
                                    description "the number of DIAMETER Gx Abort-Session messages.";
                                }

                            } // list client-side-messages

                        } // container statistics

                        list client-side-peer-info {
                            key "ip-address port";
                            description "information about the client-side peers of the Diameter proxy instances.";

                            leaf ip-address {
                                type types-sros:ip-address;
                                description "the source IP address from a client-side peer of a DIAMETER proxy instance.";
                            }

                            leaf port {
                                type types-sros:tcp-udp-port;
                                description "the TCP source port from a client-side peer of a DIAMETER proxy instance.";
                            }

                            leaf psm-state {
                                type enumeration {
                                    enum "r-open"                       { value 1; }
                                    enum "wait-r-cer"                   { value 2; }
                                }
                                description "the state of the peer's state machine.";
                            }

                            leaf pending-transactions {
                                type uint32;
                                description "the number of pending transactions.";
                            }

                        } // list client-side-peer-info

                    } // container proxy

                } // list peer-policy

            } // container diameter

            container wpp {
                description "Enter the wpp context";

                list portal-group {
                    key "group-name";
                    description "Enter the portal-group context";

                    leaf group-name {
                        type types-sros:named-item;
                        description "Portal group name";
                    }

                    leaf controlled-router {
                        type types-sros:router-instance;
                        description "The router controlled by this portal group.";
                    }

                    leaf enabled-interfaces {
                        type uint32;
                        description
                            "The number of adminstratively enabled interfaces that are
                             associated with this portal group.";
                    }

                    leaf triggered-hosts {
                        type boolean;
                        description
                            "Indicates if triggered hosts are enabled or disabled on this
                             portal group.";
                    }

                    list host {
                        key "address";
                        description "The hosts controlled by the portal group";

                        leaf address {
                            type types-sros:ipv4-unicast-address;
                            description "The address of the WPP host.";
                        }

                        leaf state {
                            type enumeration {
                                enum "idle"                         { value 1; }
                                enum "challenged"                   { value 2; }
                                enum "authenticating"               { value 3; }
                                enum "authenticated"                { value 4; }
                                enum "established"                  { value 5; }
                                enum "logging-out"                  { value 6; }
                            }
                            description "The state of the WPP host.";
                        }

                        leaf serial-number {
                            type uint32 {
                                range "1..4294967295";
                            }
                            description "The serial number of the WPP host.";
                        }

                        leaf request-id {
                            type uint32 {
                                range "1..4294967295";
                            }
                            description "The request-id of the WPP host.";
                        }

                        leaf remote-port {
                            type inet:port-number;
                            description "The UDP source port used by the portal while sending a message for this host.";
                        }

                        leaf local-address {
                            type types-sros:ipv4-unicast-address;
                            description "The destination address used by the portal while sending a message for this host.";
                        }

                        leaf user-name {
                            type types-sros:display-string;
                            description "The WPP user name of this WPP host.";
                        }

                        leaf service {
                            type types-services:service-name;
                            description "The service to which the WPP host belongs.";
                        }

                        leaf mac-address {
                            type yang:mac-address;
                            description "The mac-address of the WPP host.";
                        }

                        leaf is-triggered {
                            type boolean;
                            description "True if the creation of the host was triggered by the portal, false otherwise.";
                        }

                        leaf track-srrp-instance {
                            type uint32;
                            description
                                "The SRRP instance whose state is tracked by this WPP host to determine if
                                 it is on the MCS master or backup node.";
                        }

                        leaf is-mcs-backup {
                            type boolean;
                            description "True if the WPP host is on the MCS backup node, false otherwise.";
                        }

                        container active-portal {
                            description "The active portal in case the host is in state authenticating or logging-out.";

                            leaf router-instance {
                                type types-sros:router-instance;
                                description "The router-instance of the active portal.";
                            }

                            leaf name {
                                type types-sros:named-item;
                                description "The name of the active portal.";
                            }

                        } // container active-portal

                    } // list host

                } // list portal-group

            } // container wpp

        } // container aaa

    } // grouping state-aaa

}
