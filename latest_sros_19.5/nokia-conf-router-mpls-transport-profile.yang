submodule nokia-conf-router-mpls-transport-profile {

    yang-version "1.1";

    belongs-to nokia-conf { prefix "conf"; }

    import ietf-yang-types                { prefix "yang"; }
    import nokia-sros-yang-extensions     { prefix "sros-ext"; }
    import nokia-types-mpls               { prefix "types-mpls"; }
    import nokia-types-sros               { prefix "types-sros"; }

    include nokia-conf-bfd;
    include nokia-conf-groups;

    sros-ext:sros-major-release "rel19";

    organization "Nokia";

    contact
        "Nokia SR OS Support
         Web: <http://www.nokia.com>";

    description
        "Nokia YANG Data model to configure mpls transport profile on SR OS based routers.

         Copyright 2016 Nokia. All rights reserved. Reproduction of this document
         is authorized on the condition that the foregoing copyright notice is included.

         This nokia-conf-router-mpls-transport-profile YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-04-05";

    grouping conf-router-mpls-transport-profile-mpls-tp {
    } // grouping conf-router-mpls-transport-profile-mpls-tp

    grouping conf-router-mpls-transport-profile-working-tp-path {
    } // grouping conf-router-mpls-transport-profile-working-tp-path

    grouping conf-router-mpls-transport-profile-protect-tp-path {
    } // grouping conf-router-mpls-transport-profile-protect-tp-path

    grouping conf-router-mpls-transport-profile-mpls-tp-mep {
    } // grouping conf-router-mpls-transport-profile-mpls-tp-mep

}
