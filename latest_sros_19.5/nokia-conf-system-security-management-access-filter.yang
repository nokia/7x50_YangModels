submodule nokia-conf-system-security-management-access-filter {

    yang-version "1.1";

    belongs-to nokia-conf { prefix "conf"; }

    import ietf-yang-types                { prefix "yang"; }
    import nokia-sros-yang-extensions     { prefix "sros-ext"; }
    import nokia-types-filter             { prefix "types-filter"; }
    import nokia-types-services           { prefix "types-services"; }
    import nokia-types-sros               { prefix "types-sros"; }

    include nokia-conf-groups;

    sros-ext:sros-major-release "rel19";

    organization "Nokia";

    contact
        "Nokia SR OS Support
         Web: <http://www.nokia.com>";

    description
        "Nokia YANG Data model to configure System security management access filter configuration. on SR OS based routers.

         Copyright 2016 Nokia. All rights reserved. Reproduction of this document
         is authorized on the condition that the foregoing copyright notice is included.

         This nokia-conf-system-security-management-access-filter YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-04-23";

    grouping conf-system-security-management-access-filter {
        container management-access-filter {
            description "Enter the management-access-filter context";

            container ip-filter {
                description "Enter the ip-filter context";

                leaf admin-state {
                    type types-sros:admin-state;
                    default "enable";
                    description "Administrative state of the MAF.";
                }

                leaf default-action {
                    type types-filter:maf-action;
                    default "ignore-match";
                    description
                        "Specifies the default action for management access in the absence
                         of a specific management access filter entry match.";
                }

                list entry {
                    key "entry-id";
                    description "Enter the entry context";

                    leaf entry-id {
                        type uint32 {
                            range "1..9999";
                        }
                        description "The id used to uniquely identify this filter entry.";
                    }

                    leaf action {
                        type types-filter:maf-action;
                        default "ignore-match";
                        description
                            "Specifies the default action for management access in the absence
                             of a specific management access filter entry match.";
                    }

                    leaf description {
                        type types-sros:description;
                        description "Description for this entry";
                    }

                    leaf log-events {
                        type boolean;
                        default "false";
                        description "If is 'true', entry match logging is enabled.";
                    }

                    container match {
                        description "Enter the match context";

                        leaf router-instance {
                            type string;
                            description "Specifies router instance to be matched.";
                        }

                        leaf protocol {
                            type types-sros:ipv4-match-protocol;
                            description "Specifies protocol to match.";
                        }

                        container src-ip {
                            description "Enter the src-ip context";

                            choice src-ip {
                                case address {

                                    leaf address {
                                        type union {
                                            type types-sros:ipv4-prefix;
                                            type types-sros:ipv4-address;
                                        }
                                        description "IP address or IP prefix.";
                                    }

                                    leaf mask {
                                        type types-sros:ipv4-address;
                                        description "IP address mask.";
                                    }

                                }
                            }
                        } // container src-ip

                        container mgmt-port {
                            description "Enter the mgmt-port context";

                            choice mgmt-port {
                                case port-id {

                                    leaf port-id {
                                        type types-sros:port;
                                        description "Specifies source port.";
                                    }

                                }
                                case cpm {

                                    leaf cpm {
                                        type empty;
                                        description "Specifies source cpm.";
                                    }

                                }
                                case lag-id {

                                    leaf lag-id {
                                        type uint16 {
                                            range "1..800";
                                        }
                                        description "Specifies source lag.";
                                    }

                                }
                            }
                        } // container mgmt-port

                        container dst-port {
                            presence "Enables management access IP filter entry destination port.";
                            description "Enter the dst-port context";

                            leaf port {
                                type uint16 {
                                    range "1..65535";
                                }
                                mandatory true;
                                description "Specifies port to match.";
                            }

                            leaf mask {
                                type uint16 {
                                    range "1..65535";
                                }
                                default "65535";
                                description "Specifies mask to match.";
                            }

                        } // container dst-port

                    } // container match

                } // list entry

            } // container ip-filter

            container ipv6-filter {
                description "Enter the ipv6-filter context";

                leaf admin-state {
                    type types-sros:admin-state;
                    default "enable";
                    description "Administrative state of the MAF.";
                }

                leaf default-action {
                    type types-filter:maf-action;
                    default "ignore-match";
                    description
                        "Specifies the default action for management access in the absence
                         of a specific management access filter entry match.";
                }

                list entry {
                    key "entry-id";
                    description "Enter the entry context";

                    leaf entry-id {
                        type uint32 {
                            range "1..9999";
                        }
                        description "The id used to uniquely identify this filter entry.";
                    }

                    leaf action {
                        type types-filter:maf-action;
                        default "ignore-match";
                        description
                            "Specifies the default action for management access in the absence
                             of a specific management access filter entry match.";
                    }

                    leaf description {
                        type types-sros:description;
                        description "Description for this entry";
                    }

                    leaf log-events {
                        type boolean;
                        default "false";
                        description "If is 'true', entry match logging is enabled.";
                    }

                    container match {
                        description "Enter the match context";

                        leaf router-instance {
                            type string;
                            description "Specifies router instance to be matched.";
                        }

                        leaf next-header {
                            type types-sros:ipv6-match-next-header;
                            description
                                "IPv6 next header to match. Because the match criteria only pertains to the last
                                 next-header, the following values will not match a filter entry: 0, 43, 44, 50, 51,
                                 and 60.";
                        }

                        leaf flow-label {
                            type types-filter:filter-match-flow-label;
                            description "Specifies the flow label to be matched.";
                        }

                        container src-ip {
                            description "Enter the src-ip context";

                            choice src-ip {
                                case address {

                                    leaf address {
                                        type union {
                                            type types-sros:ipv6-prefix;
                                            type types-sros:ipv6-address;
                                        }
                                        description "IPv6 address or IPv6 prefix.";
                                    }

                                    leaf mask {
                                        type types-sros:ipv6-address;
                                        description "IPv6 address mask.";
                                    }

                                }
                            }
                        } // container src-ip

                        container mgmt-port {
                            description "Enter the mgmt-port context";

                            choice mgmt-port {
                                case port-id {

                                    leaf port-id {
                                        type types-sros:port;
                                        description "Specifies source port.";
                                    }

                                }
                                case cpm {

                                    leaf cpm {
                                        type empty;
                                        description "Specifies source cpm.";
                                    }

                                }
                                case lag-id {

                                    leaf lag-id {
                                        type uint16 {
                                            range "1..800";
                                        }
                                        description "Specifies source lag.";
                                    }

                                }
                            }
                        } // container mgmt-port

                        container dst-port {
                            presence "Enables management access IPv6 filter entry destination port.";
                            description "Enter the dst-port context";

                            leaf port {
                                type uint16 {
                                    range "1..65535";
                                }
                                mandatory true;
                                description "Specifies port to match.";
                            }

                            leaf mask {
                                type uint16 {
                                    range "1..65535";
                                }
                                default "65535";
                                description "Specifies mask to match.";
                            }

                        } // container dst-port

                    } // container match

                } // list entry

            } // container ipv6-filter

            container mac-filter {
                description "Enter the mac-filter context";

                leaf admin-state {
                    type types-sros:admin-state;
                    default "enable";
                    description "Administrative state of the MAF.";
                }

                leaf default-action {
                    type types-filter:maf-mac-action;
                    default "ignore-match";
                    description
                        "Specifies the default action for management access in the absence
                         of a specific management access filter entry match.";
                }

                list entry {
                    key "entry-id";
                    description "Enter the entry context";

                    leaf entry-id {
                        type uint32 {
                            range "1..9999";
                        }
                        description "The id used to uniquely identify this filter entry.";
                    }

                    leaf action {
                        type types-filter:maf-mac-action;
                        default "ignore-match";
                        description
                            "Specifies the default action for management access in the absence
                             of a specific management access filter entry match.";
                    }

                    leaf description {
                        type types-sros:description;
                        description "Description for this entry";
                    }

                    leaf log-events {
                        type boolean;
                        default "false";
                        description "If is 'true', entry match logging is enabled.";
                    }

                    container match {
                        description "Enter the match context";

                        leaf service {
                            type types-services:service-name;
                            description
                                "Specifies the service id in which the packet is to be received
                                 for this entry to match.";
                        }

                        leaf frame-type {
                            type enumeration {
                                enum "802dot3"                      { value 0; }
                                enum "802dot2-llc"                  { value 1; }
                                enum "802dot2-snap"                 { value 2; }
                                enum "ethernet-ii"                  { value 3; }
                                enum "802dot1-ag"                   { value 4; }
                            }
                            default "802dot3";
                            description
                                "Specifies the type of mac frame for which we are defining this
                                 match criteria.";
                        }

                        leaf etype {
                            type types-services:etype-value;
                            description
                                "Specifies the Ethertype for this MAC filter entry. This object has
                                 no significance if the object frame-type is not set to Ethernet_II.";
                        }

                        leaf snap-pid {
                            type int32 {
                                range "0..65535";
                            }
                            description "Specifies snap-pid Match Criteria.";
                        }

                        leaf snap-oui {
                            type enumeration {
                                enum "zero"                         { value 2; }
                                enum "non-zero"                     { value 3; }
                            }
                            description "Specifies snap-oui Match Criteria.";
                        }

                        container src-mac {
                            presence "Enables management access MAC filter source MAC.";
                            description "Enter the src-mac context";

                            leaf address {
                                type yang:mac-address;
                                mandatory true;
                                description "MAC address";
                            }

                            leaf mask {
                                type yang:mac-address;
                                default "ff:ff:ff:ff:ff:ff";
                                description "MAC address mask";
                            }

                        } // container src-mac

                        container dst-mac {
                            presence "Enables management access MAC filter destination MAC.";
                            description "Enter the dst-mac context";

                            leaf address {
                                type yang:mac-address;
                                mandatory true;
                                description "MAC address";
                            }

                            leaf mask {
                                type yang:mac-address;
                                default "ff:ff:ff:ff:ff:ff";
                                description "MAC address mask";
                            }

                        } // container dst-mac

                        container dot1p {
                            presence "Enables management access MAC filter dot1p.";
                            description "Enter the dot1p context";

                            leaf priority {
                                type int32 {
                                    range "0..7";
                                }
                                mandatory true;
                                description "Specifies a Dot1p value to assign to the traffic generated by this application.";
                            }

                            leaf mask {
                                type int32 {
                                    range "1..7";
                                }
                                default "7";
                                description "Specifies a Dot1p value to assign to the traffic generated by this application.";
                            }

                        } // container dot1p

                        container llc-ssap {
                            presence "Enables management access MAC filter SSAP.";
                            description "Enter the llc-ssap context";

                            leaf ssap {
                                type int32 {
                                    range "0..255";
                                }
                                mandatory true;
                                description "Specifies SSAP value.";
                            }

                            leaf mask {
                                type int32 {
                                    range "1..255";
                                }
                                default "255";
                                description "Specifies SSAP mask.";
                            }

                        } // container llc-ssap

                        container llc-dsap {
                            presence "Enables management access MAC filter DSAP.";
                            description "Enter the llc-dsap context";

                            leaf dsap {
                                type int32 {
                                    range "0..255";
                                }
                                mandatory true;
                                description "Specifies DSAP value.";
                            }

                            leaf mask {
                                type int32 {
                                    range "1..255";
                                }
                                default "255";
                                description "Specifies DSAP mask.";
                            }

                        } // container llc-dsap

                        container cfm-opcode {
                            description "Enter the cfm-opcode context";

                            choice match-cfm-opcode {
                                case operator-eq {

                                    leaf eq {
                                        type uint32 {
                                            range "0..255";
                                        }
                                        description "Specifies the operator for op-code matching.";
                                    }

                                }
                                case operator-lt {

                                    leaf lt {
                                        type uint32 {
                                            range "1..255";
                                        }
                                        description "Specifies the operator for op-code matching.";
                                    }

                                }
                                case operator-gt {

                                    leaf gt {
                                        type uint32 {
                                            range "0..254";
                                        }
                                        description "Specifies the operator for op-code matching.";
                                    }

                                }
                                case opcode-range {

                                    container range {
                                        presence "range";
                                        description "Enter the range context";

                                        leaf start {
                                            type uint32 {
                                                range "0..254";
                                            }
                                            mandatory true;
                                            description "Specifies lower bound for the range of op-code to match.";
                                        }

                                        leaf end {
                                            type uint32 {
                                                range "1..255";
                                            }
                                            mandatory true;
                                            description "Specifies upper bound for the range of op-code to match.";
                                        }

                                    } // container range

                                }
                            }
                        } // container cfm-opcode

                    } // container match

                } // list entry

            } // container mac-filter

        } // container management-access-filter

    } // grouping conf-system-security-management-access-filter

}
