submodule nokia-conf-port-dwdm-coherent {

    yang-version "1.1";

    belongs-to nokia-conf { prefix "conf"; }

    import nokia-sros-yang-extensions     { prefix "sros-ext"; }
    import nokia-types-port               { prefix "types-port"; }


    sros-ext:sros-major-release "rel19";

    organization "Nokia";

    contact
        "Nokia SR OS Support
         Web: <http://www.nokia.com>";

    description
        "Nokia YANG Data model to configure dense wavelength division multiplexing coherent ports on SR OS based routers.

         Copyright 2016 Nokia. All rights reserved. Reproduction of this document
         is authorized on the condition that the foregoing copyright notice is included.

         This nokia-conf-port-dwdm-coherent YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2018-09-11";

    grouping conf-port-dwdm-coherent {
        container coherent {
            description "Enter the coherent context";

            leaf channel {
                type types-port:optical-dwdm-channel;
                description "Received channel number";
            }

            leaf compatibility {
                type types-port:optical-compatibility-mode;
                default "long-haul";
                description "Optical mode and rate of operation";
            }

            leaf cpr-window-size {
                type uint32 {
                    range "2|4|8|16|32|64";
                }
                units "symbols";
                default "32";
                description "Window size for the carrier phase recovery";
            }

            leaf dispersion {
                type int32 {
                    range "-50000..50000";
                }
                units "picoseconds per nanometer";
                description "Dispersion compensation";
            }

            leaf mode {
                type types-port:optical-dispersion-control-mode;
                default "automatic";
                description "Dispersion algorithm mode";
            }

            leaf rx-los-reaction {
                type types-port:los-reaction;
                default "squelch";
                description "Reaction to RX LOS";
            }

            leaf rx-los-thresh {
                type decimal64 {
                    range "-24..-13";
                    fraction-digits 2;
                }
                units "decibels per milliwatt";
                default "-23";
                description "LOS threshold of the average input power";
            }

            leaf target-power {
                type decimal64 {
                    range "-20..3";
                    fraction-digits 2;
                }
                units "decibels per milliwatt";
                default "1";
                description "Target for average of the output power";
            }

            container report-alarm {
                description "Enter the report-alarm context";

                leaf modflt {
                    type boolean;
                    default "true";
                    description "Report module fault alarm";
                }

                leaf mod {
                    type boolean;
                    default "true";
                    description "Report module alarm";
                }

                leaf netrx {
                    type boolean;
                    default "true";
                    description "Report network (optical side) receive alarm";
                }

                leaf nettx {
                    type boolean;
                    default "true";
                    description "Report network (optical side) transmit alarm";
                }

                leaf hosttx {
                    type boolean;
                    default "true";
                    description "Report host (electrical side) transmit alarm";
                }

            } // container report-alarm

            container sweep {
                description "Enter the sweep context";

                leaf start {
                    type int32 {
                        range "-50000..50000";
                    }
                    units "picoseconds per nanometer";
                    default "-25500";
                    description "Start value of dispersion sweeping";
                }

                leaf end {
                    type int32 {
                        range "-50000..50000";
                    }
                    units "picoseconds per nanometer";
                    default "2000";
                    description "End value of dispersion sweeping";
                }

            } // container sweep

        } // container coherent

    } // grouping conf-port-dwdm-coherent

}
