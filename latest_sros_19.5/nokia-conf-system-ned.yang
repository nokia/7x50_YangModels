submodule nokia-conf-system-ned {

    yang-version "1.1";

    belongs-to nokia-conf { prefix "conf"; }

    import nokia-sros-yang-extensions     { prefix "sros-ext"; }
    import nokia-types-sros               { prefix "types-sros"; }

    include nokia-conf-groups;

    sros-ext:sros-major-release "rel19";

    organization "Nokia";

    contact
        "Nokia SR OS Support
         Web: <http://www.nokia.com>";

    description
        "Nokia YANG Data model to configure system network-element-discovery on SR OS based routers.

         Copyright 2016 Nokia. All rights reserved. Reproduction of this document
         is authorized on the condition that the foregoing copyright notice is included.

         This nokia-conf-system-ned YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-04-16";

    grouping conf-system-ned-network-element-discovery {
        container network-element-discovery {
            description "Network element discovery parameters";

            leaf generate-traps {
                type boolean;
                default "false";
                description "Generation of NE discovery traps";
            }

            list profile {
                key "name";
                max-elements 1;
                description "NE profile parameters";

                leaf name {
                    type types-sros:named-item;
                    description "Profile name";
                }

                leaf neid {
                    type string {
                        length "7..8";
                    }
                    description "The network element identifier of the advertised node";
                }

                leaf platform-type {
                    type types-sros:named-item-255;
                    description "The platform name and chassis type to be advertised";
                }

                leaf vendor-id {
                    type types-sros:named-item-255;
                    default "Nokia";
                    description "The vendor identifier to be advertised";
                }

                leaf system-mac {
                    type types-sros:mac-unicast-address-no-zero;
                    description "The MAC address of the advertised node";
                }

                container neip {
                    description "Network element IP address parameters";

                    leaf ipv4 {
                        type types-sros:ipv4-unicast-address;
                        description "The neip IPv4 address of the advertised node";
                    }

                    leaf ipv6 {
                        type types-sros:ipv6-address;
                        description "The neip IPv6 address of the advertised node";
                    }

                } // container neip

            } // list profile

        } // container network-element-discovery

    } // grouping conf-system-ned-network-element-discovery

}
