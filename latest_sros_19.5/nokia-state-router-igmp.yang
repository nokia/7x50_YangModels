submodule nokia-state-router-igmp {

    yang-version "1.1";

    belongs-to nokia-state { prefix "state"; }

    import ietf-yang-types                { prefix "yang"; }
    import nokia-sros-yang-extensions     { prefix "sros-ext"; }
    import nokia-types-igmp               { prefix "types-igmp"; }
    import nokia-types-sros               { prefix "types-sros"; }
    import nokia-types-subscriber-mgmt    { prefix "types-submgt"; }

    include nokia-state-router;

    sros-ext:sros-major-release "rel19";

    organization "Nokia";

    contact
        "Nokia SR OS Support
         Web: <http://www.nokia.com>";

    description
        "Nokia YANG Data model with operational state for igmp protocol on SR OS based routers.

         Copyright 2016 Nokia. All rights reserved. Reproduction of this document
         is authorized on the condition that the foregoing copyright notice is included.

         This nokia-state-router-igmp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-03-21";

    grouping state-router-igmp {
        container igmp {
            description "Enter the igmp context";

            leaf oper-state {
                type types-sros:oper-state;
                description "The current operating state of this IGMP protocol instance on this router.";
            }

            list interface {
                key "ip-interface-name";
                description "Enter the interface context";

                leaf ip-interface-name {
                    type types-sros:interface-name;
                    description "Interface name.";
                }

                leaf oper-state {
                    type types-sros:oper-state;
                    description "The current operating state of the IGMP protocol on this interface.";
                }

                leaf oper-version {
                    type types-igmp:igmp-version;
                    description "The operational version of the IGMP which is running on this interface.";
                }

                leaf group-count {
                    type int32;
                    description "The number of multicast groups which have been learned on this interface.";
                }

                leaf next-general-query-time {
                    type uint32;
                    units "seconds";
                    description
                        "The time remaining before the general query is sent on this interface
                         if this router is the querier.";
                }

                leaf maximum-groups-until-now {
                    type uint32;
                    description "The highest value that 'group-count' had till now.";
                }

                leaf querier {
                    type types-sros:ipv4-address;
                    description "The address of the IGMP Querier on the IP subnet to which this interface is attached.";
                }

                leaf querier-uptime {
                    type uint32;
                    units "seconds";
                    description "The time since 'querier' was last elected as querier.";
                }

                leaf querier-expiry-time {
                    type uint32;
                    units "seconds";
                    description "The time remaining before querier is aged out.";
                }

                leaf redundant-multicast-forwarder {
                    type boolean;
                    description
                        "This interface is the forwarding interface
                         of a pair of redundant multicast interfaces.";
                }

                container mcac {
                    description "Enter the mcac context";

                    leaf in-use-mandatory-bandwidth {
                        type uint32;
                        units "kilobps";
                        description
                            "The in-use bandwidth for the mandatory channels for this
                             protocol interface instance.";
                    }

                    leaf in-use-optional-bandwidth {
                        type uint32;
                        units "kilobps";
                        description
                            "The in-use bandwidth for the optional channels for this
                             protocol interface instance.";
                    }

                    leaf available-mandatory-bandwidth {
                        type uint32;
                        units "kilobps";
                        description
                            "The pre-reserved bandwidth for the mandatory channels for
                             this interface instance.";
                    }

                    leaf available-optional-bandwidth {
                        type uint32;
                        units "kilobps";
                        description "The available bandwidth for this interface instance.";
                    }

                    leaf values-in-transit {
                        type boolean;
                        description
                            "The operational (available and in-use mandatory/optional) value for the
                             following objects is in transition due to configuration change:
                             - available-mandatory-bandwidth
                             - available-bandwidth
                             - in-use-mandatory-bandwidth
                             - in-use-optional-bandwidth.";
                    }

                } // container mcac

                container static {
                    description "Enter the static context";

                    list group-range {
                        key "start end step";
                        description "Enter the group-range context";

                        leaf start {
                            type types-sros:ipv4-multicast-address;
                            description "Start of group range of multicast channel";
                        }

                        leaf end {
                            type types-sros:ipv4-multicast-address;
                            description "End of group range for multicast channel";
                        }

                        leaf step {
                            type types-sros:ipv4-address;
                            description "Step interval for the group-range addresses";
                        }

                        leaf group-count {
                            type uint32;
                            description "The number of groups in the group-range.";
                        }

                    } // list group-range

                } // container static

                container statistics {

                    container received {
                        description "Received message statistics.";

                        leaf general-queries {
                            type yang:counter32;
                            description "General Queries.";
                        }

                        leaf group-queries {
                            type yang:counter32;
                            description "Group Specific Queries.";
                        }

                        leaf group-source-queries {
                            type yang:counter32;
                            description "Group and Source Specific Queries.";
                        }

                        leaf v1-reports {
                            type yang:counter32;
                            description "V1 Reports.";
                        }

                        leaf v2-reports {
                            type yang:counter32;
                            description "V2 Reports.";
                        }

                        leaf v3-reports {
                            type yang:counter32;
                            description "V3 Reports.";
                        }

                        leaf leaves {
                            type yang:counter32;
                            description "Leaves.";
                        }

                        leaf drops {
                            type yang:counter32;
                            description "Total number of dropped packets.";
                        }

                    } // container received

                    container transmitted {
                        description "Transmit message statistics.";

                        leaf general-queries {
                            type yang:counter32;
                            description "General Queries.";
                        }

                        leaf group-queries {
                            type yang:counter32;
                            description "Group Specific Queries.";
                        }

                        leaf group-source-queries {
                            type yang:counter32;
                            description "Group and Source Specific Queries.";
                        }

                        leaf v1-reports {
                            type yang:counter32;
                            description "V1 Reports.";
                        }

                        leaf v2-reports {
                            type yang:counter32;
                            description "V2 Reports.";
                        }

                        leaf v3-reports {
                            type yang:counter32;
                            description "V3 Reports.";
                        }

                        leaf leaves {
                            type yang:counter32;
                            description "Leaves.";
                        }

                        leaf drops {
                            type yang:counter32;
                            description "Total number of dropped packets.";
                        }

                        leaf errors {
                            type yang:counter32;
                            description "Transmission Errors.";
                        }

                    } // container transmitted

                    container error {
                        description "Error message statistics.";

                        leaf bad-length {
                            type yang:counter32;
                            description "Bad length.";
                        }

                        leaf bad-ip-checksum {
                            type yang:counter32;
                            description "Bad Ip checksum.";
                        }

                        leaf unknown-type {
                            type yang:counter32;
                            description "Unknown type.";
                        }

                        leaf wrong-version {
                            type yang:counter32;
                            description "Wrong version.";
                        }

                        leaf import-policy-drops {
                            type yang:counter32;
                            description
                                "Number of times we matched the host IP address or group or
                                 source addresses specified in the import policy.";
                        }

                        leaf missing-router-alert {
                            type yang:counter32;
                            description "Router alert flag is not set.";
                        }

                        leaf bad-encoding {
                            type yang:counter32;
                            description "Badly encoded.";
                        }

                        leaf local-scope {
                            type yang:counter32;
                            description "Link-local scope multicast group address.";
                        }

                        leaf mcac-policy-drops {
                            type yang:counter32;
                            description
                                "Number of times a join is dropped because of applying a
                                 multicast CAC policy.";
                        }

                        leaf reached-maximum-number-groups {
                            type yang:counter32;
                            description
                                "Number of times a join is dropped because we reached the maximum
                                 number of groups.";
                        }

                        leaf reached-maximum-number-group-sources {
                            type yang:counter32;
                            description
                                "Number of times a join is dropped because we reached the maximum
                                 number group-source combinations.";
                        }

                        leaf reached-maximum-number-sources {
                            type yang:counter32;
                            description
                                "Number of times a join is dropped because we reached the maximum
                                 number of sources per group.";
                        }

                        leaf out-of-memory-drops {
                            type yang:counter32;
                            description "Number of times a join is dropped because we ran out of memory.";
                        }

                        leaf mcs-failures {
                            type yang:counter32;
                            description "Number of times a group could not be synced through multi chassis synchronisation (MCS).";
                        }

                        leaf non-local {
                            type yang:counter32;
                            description "Non-local sender source IP address.";
                        }

                    } // container error

                } // container statistics

                list group {
                    key "group-address";
                    description "Multicast group membership information that joined on the interface.";

                    leaf group-address {
                        type types-sros:ipv4-multicast-address;
                        description "Group address of multicast channel";
                    }

                    leaf group-type {
                        type types-igmp:learn-type;
                    }

                    leaf filter-mode {
                        type types-igmp:filter-mode;
                    }

                    leaf expiry-time {
                        type uint32;
                        units "seconds";
                        description "The time left before multicast group timeout.";
                    }

                    leaf uptime {
                        type uint32;
                        units "seconds";
                        description "The time elapsed since this entry was created.";
                    }

                    leaf v1-host-timer {
                        type uint32;
                        units "seconds";
                        description
                            "The time remaining until the local router will assume that
                             there are no longer any version 1 members.";
                    }

                    leaf v2-host-timer {
                        type uint32;
                        units "seconds";
                        description
                            "The time remaining until the local router will assume that
                             there are no longer any version 2 members.";
                    }

                    leaf igmp-compatibility-mode {
                        type types-igmp:igmp-version;
                        description "Compatibility with older version routers.";
                    }

                    leaf last-reporter {
                        type types-sros:ip-address;
                        description
                            "The last host address which has sent the report to join
                             the multicast group.";
                    }

                    list source {
                        key "source-address";
                        description "List of multicast source information of the multicast group.";

                        leaf source-address {
                            type types-sros:ipv4-address;
                            description "Source address of multicast channel.";
                        }

                        leaf source-type {
                            type types-igmp:learn-type;
                        }

                        leaf forwarding-state {
                            type types-igmp:forwarding-state;
                            description "Traffic forwardeding state on this port.";
                        }

                        leaf expiry-time {
                            type uint32;
                            units "seconds";
                            description "The time left before multicast group timeout.";
                        }

                        leaf uptime {
                            type uint32;
                            units "seconds";
                            description "The time elapsed since this entry was created.";
                        }

                    } // list source

                } // list group

            } // list interface

            list group-interface {
                key "group-interface-name";
                description "Enter the group-interface context";

                leaf group-interface-name {
                    type types-sros:interface-name;
                    description "Group interface name";
                }

                leaf oper-state {
                    type types-sros:oper-state;
                    description "The current operating state of the IGMP protocol on this group interface.";
                }

                container mcac {
                    description "Enter the mcac context";

                    leaf in-use-mandatory-bandwidth {
                        type uint32;
                        units "kilobps";
                        description
                            "The in-use bandwidth for the mandatory channels for this
                             protocol interface instance.";
                    }

                    leaf in-use-optional-bandwidth {
                        type uint32;
                        units "kilobps";
                        description
                            "The in-use bandwidth for the optional channels for this
                             protocol interface instance.";
                    }

                    leaf available-mandatory-bandwidth {
                        type uint32;
                        units "kilobps";
                        description
                            "The pre-reserved bandwidth for the mandatory channels for
                             this interface instance.";
                    }

                    leaf available-optional-bandwidth {
                        type uint32;
                        units "kilobps";
                        description "The available bandwidth for this interface instance.";
                    }

                    leaf values-in-transit {
                        type boolean;
                        description
                            "The operational (available and in-use mandatory/optional) value for the
                             following objects is in transition due to configuration change:
                             - available-mandatory-bandwidth
                             - available-bandwidth
                             - in-use-mandatory-bandwidth
                             - in-use-optional-bandwidth.";
                    }

                } // container mcac

                list sap {
                    key "sap-id";
                    description "List of saps.";

                    leaf sap-id {
                        type types-sros:sap;
                        description "SAP identifier.";
                    }

                    leaf oper-state {
                        type types-sros:oper-state;
                        description "The current operating state of the IGMP protocol on this interface.";
                    }

                    leaf oper-version {
                        type types-igmp:igmp-version;
                        description "The operational version of the IGMP which is running on this interface.";
                    }

                    leaf group-count {
                        type int32;
                        description "The number of multicast groups which have been learned on this interface.";
                    }

                    leaf next-general-query-time {
                        type uint32;
                        units "seconds";
                        description
                            "The time remaining before the general query is sent on this interface
                             if this router is the querier.";
                    }

                    leaf maximum-groups-until-now {
                        type uint32;
                        description "The highest value that 'group-count' had till now.";
                    }

                    container statistics {

                        container received {
                            description "Received message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                        } // container received

                        container transmitted {
                            description "Transmit message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                            leaf errors {
                                type yang:counter32;
                                description "Transmission Errors.";
                            }

                        } // container transmitted

                        container error {
                            description "Error message statistics.";

                            leaf bad-length {
                                type yang:counter32;
                                description "Bad length.";
                            }

                            leaf bad-ip-checksum {
                                type yang:counter32;
                                description "Bad Ip checksum.";
                            }

                            leaf unknown-type {
                                type yang:counter32;
                                description "Unknown type.";
                            }

                            leaf wrong-version {
                                type yang:counter32;
                                description "Wrong version.";
                            }

                            leaf import-policy-drops {
                                type yang:counter32;
                                description
                                    "Number of times we matched the host IP address or group or
                                     source addresses specified in the import policy.";
                            }

                            leaf missing-router-alert {
                                type yang:counter32;
                                description "Router alert flag is not set.";
                            }

                            leaf bad-encoding {
                                type yang:counter32;
                                description "Badly encoded.";
                            }

                            leaf local-scope {
                                type yang:counter32;
                                description "Link-local scope multicast group address.";
                            }

                            leaf mcac-policy-drops {
                                type yang:counter32;
                                description
                                    "Number of times a join is dropped because of applying a
                                     multicast CAC policy.";
                            }

                            leaf reached-maximum-number-groups {
                                type yang:counter32;
                                description
                                    "Number of times a join is dropped because we reached the maximum
                                     number of groups.";
                            }

                            leaf reached-maximum-number-group-sources {
                                type yang:counter32;
                                description
                                    "Number of times a join is dropped because we reached the maximum
                                     number group-source combinations.";
                            }

                            leaf reached-maximum-number-sources {
                                type yang:counter32;
                                description
                                    "Number of times a join is dropped because we reached the maximum
                                     number of sources per group.";
                            }

                            leaf out-of-memory-drops {
                                type yang:counter32;
                                description "Number of times a join is dropped because we ran out of memory.";
                            }

                            leaf mcs-failures {
                                type yang:counter32;
                                description "Number of times a group could not be synced through multi chassis synchronisation (MCS).";
                            }

                            leaf non-local {
                                type yang:counter32;
                                description "Non-local sender source IP address.";
                            }

                        } // container error

                    } // container statistics

                    list group {
                        key "group-address";
                        description "Multicast group membership information that joined on the sap.";

                        leaf group-address {
                            type types-sros:ipv4-multicast-address;
                            description "Group address of multicast channel";
                        }

                        leaf group-type {
                            type types-igmp:learn-type;
                        }

                        leaf filter-mode {
                            type types-igmp:filter-mode;
                        }

                        leaf expiry-time {
                            type uint32;
                            units "seconds";
                            description "The time left before multicast group timeout.";
                        }

                        leaf uptime {
                            type uint32;
                            units "seconds";
                            description "The time elapsed since this entry was created.";
                        }

                        leaf v1-host-timer {
                            type uint32;
                            units "seconds";
                            description
                                "The time remaining until the local router will assume that
                                 there are no longer any version 1 members.";
                        }

                        leaf v2-host-timer {
                            type uint32;
                            units "seconds";
                            description
                                "The time remaining until the local router will assume that
                                 there are no longer any version 2 members.";
                        }

                        leaf igmp-compatibility-mode {
                            type types-igmp:igmp-version;
                            description "Compatibility with older version routers.";
                        }

                        leaf last-reporter {
                            type types-sros:ip-address;
                            description
                                "The last host address which has sent the report to join
                                 the multicast group.";
                        }

                        list source {
                            key "source-address";
                            description "List of multicast source information of the multicast group.";

                            leaf source-address {
                                type types-sros:ipv4-address;
                                description "Source address of multicast channel.";
                            }

                            leaf source-type {
                                type types-igmp:learn-type;
                            }

                            leaf forwarding-state {
                                type types-igmp:forwarding-state;
                                description "Traffic forwardeding state on this port.";
                            }

                            leaf expiry-time {
                                type uint32;
                                units "seconds";
                                description "The time left before multicast group timeout.";
                            }

                            leaf uptime {
                                type uint32;
                                units "seconds";
                                description "The time elapsed since this entry was created.";
                            }

                        } // list source

                    } // list group

                } // list sap

                list host {
                    key "ip-address mac-address pppoe-session-id";
                    description "List of hosts.";

                    leaf ip-address {
                        type types-sros:ipv4-address;
                        description "The IP address of this host.";
                    }

                    leaf mac-address {
                        type yang:mac-address;
                        description "The MAC address of this host.";
                    }

                    leaf pppoe-session-id {
                        type uint32;
                        description "The PPPoE session id of this host.";
                    }

                    leaf oper-state {
                        type types-sros:oper-state;
                        description "The current operating state of the IGMP protocol on this interface.";
                    }

                    leaf oper-version {
                        type types-igmp:igmp-version;
                        description "The operational version of the IGMP which is running on this interface.";
                    }

                    leaf group-count {
                        type int32;
                        description "The number of multicast groups which have been learned on this interface.";
                    }

                    leaf next-general-query-time {
                        type uint32;
                        units "seconds";
                        description
                            "The time remaining before the general query is sent on this interface
                             if this router is the querier.";
                    }

                    leaf maximum-groups-until-now {
                        type uint32;
                        description "The highest value that 'group-count' had till now.";
                    }

                    leaf subscriber-id {
                        type types-sros:named-item;
                        description "The subscriber identification of this subscriber host.";
                    }

                    leaf bonding-context-id {
                        type types-submgt:bonding-context-id;
                        description "The bonding context identifier of the session of this host.";
                    }

                    leaf bonding-connection-index {
                        type types-submgt:bonding-connection-index;
                        description "The bonding connection index of the session of this host.";
                    }

                    leaf igmp-policy {
                        type types-sros:named-item;
                        description "The igmp-policy in use.";
                    }

                    container statistics {

                        container received {
                            description "Received message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                        } // container received

                        container transmitted {
                            description "Transmit message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                            leaf errors {
                                type yang:counter32;
                                description "Transmission Errors.";
                            }

                        } // container transmitted

                        container error {
                            description "Error message statistics.";

                            leaf bad-length {
                                type yang:counter32;
                                description "Bad length.";
                            }

                            leaf bad-ip-checksum {
                                type yang:counter32;
                                description "Bad Ip checksum.";
                            }

                            leaf unknown-type {
                                type yang:counter32;
                                description "Unknown type.";
                            }

                            leaf wrong-version {
                                type yang:counter32;
                                description "Wrong version.";
                            }

                            leaf import-policy-drops {
                                type yang:counter32;
                                description
                                    "Number of times we matched the host IP address or group or
                                     source addresses specified in the import policy.";
                            }

                            leaf missing-router-alert {
                                type yang:counter32;
                                description "Router alert flag is not set.";
                            }

                            leaf bad-encoding {
                                type yang:counter32;
                                description "Badly encoded.";
                            }

                            leaf local-scope {
                                type yang:counter32;
                                description "Link-local scope multicast group address.";
                            }

                            leaf mcac-policy-drops {
                                type yang:counter32;
                                description
                                    "Number of times a join is dropped because of applying a
                                     multicast CAC policy.";
                            }

                            leaf reached-maximum-number-groups {
                                type yang:counter32;
                                description
                                    "Number of times a join is dropped because we reached the maximum
                                     number of groups.";
                            }

                            leaf reached-maximum-number-group-sources {
                                type yang:counter32;
                                description
                                    "Number of times a join is dropped because we reached the maximum
                                     number group-source combinations.";
                            }

                            leaf reached-maximum-number-sources {
                                type yang:counter32;
                                description
                                    "Number of times a join is dropped because we reached the maximum
                                     number of sources per group.";
                            }

                            leaf out-of-memory-drops {
                                type yang:counter32;
                                description "Number of times a join is dropped because we ran out of memory.";
                            }

                            leaf mcs-failures {
                                type yang:counter32;
                                description "Number of times a group could not be synced through multi chassis synchronisation (MCS).";
                            }

                            leaf non-local {
                                type yang:counter32;
                                description "Non-local sender source IP address.";
                            }

                            leaf redirection-drops {
                                type yang:counter32;
                                description
                                    "Number of times a Group is dropped because of a failure
                                     while applying a redirection policy for this host.";
                            }

                        } // container error

                        container multicast-reporter {
                            description "Multicast reporting destination statistics";

                            container reported {

                                leaf successfully-joined-streams {
                                    type yang:counter32;
                                    description "Number of joins that were successful.";
                                }

                                leaf denied-streams {
                                    type yang:counter32;
                                    description "Number of joins that were denied.";
                                }

                                leaf dropped-streams {
                                    type yang:counter32;
                                    description "Number of streams that were dropped.";
                                }

                            } // container reported

                            container not-reported {

                                leaf successfully-joined-streams {
                                    type yang:counter32;
                                    description "Number of joins that were successful.";
                                }

                                leaf denied-streams {
                                    type yang:counter32;
                                    description "Number of joins that were denied.";
                                }

                                leaf dropped-streams {
                                    type yang:counter32;
                                    description "Number of streams that were dropped.";
                                }

                            } // container not-reported

                        } // container multicast-reporter

                    } // container statistics

                    list group {
                        key "group-address";
                        description "Multicast group membership information that joined on the host.";

                        leaf group-address {
                            type types-sros:ipv4-multicast-address;
                            description "Group address of multicast channel";
                        }

                        leaf group-type {
                            type types-igmp:learn-type;
                        }

                        leaf filter-mode {
                            type types-igmp:filter-mode;
                        }

                        leaf expiry-time {
                            type uint32;
                            units "seconds";
                            description "The time left before multicast group timeout.";
                        }

                        leaf uptime {
                            type uint32;
                            units "seconds";
                            description "The time elapsed since this entry was created.";
                        }

                        leaf v1-host-timer {
                            type uint32;
                            units "seconds";
                            description
                                "The time remaining until the local router will assume that
                                 there are no longer any version 1 members.";
                        }

                        leaf v2-host-timer {
                            type uint32;
                            units "seconds";
                            description
                                "The time remaining until the local router will assume that
                                 there are no longer any version 2 members.";
                        }

                        leaf igmp-compatibility-mode {
                            type types-igmp:igmp-version;
                            description "Compatibility with older version routers.";
                        }

                        leaf last-reporter {
                            type types-sros:ip-address;
                            description
                                "The last host address which has sent the report to join
                                 the multicast group.";
                        }

                        list source {
                            key "source-address";
                            description "List of multicast source information of the multicast group.";

                            leaf source-address {
                                type types-sros:ipv4-address;
                                description "Source address of multicast channel.";
                            }

                            leaf source-type {
                                type types-igmp:learn-type;
                            }

                            leaf forwarding-state {
                                type types-igmp:forwarding-state;
                                description "Traffic forwardeding state on this port.";
                            }

                            leaf expiry-time {
                                type uint32;
                                units "seconds";
                                description "The time left before multicast group timeout.";
                            }

                            leaf uptime {
                                type uint32;
                                units "seconds";
                                description "The time elapsed since this entry was created.";
                            }

                        } // list source

                    } // list group

                } // list host

            } // list group-interface

            list host {
                key "ip-address mac-address pppoe-session-id";
                description "List of subscriber management hosts.";

                leaf ip-address {
                    type types-sros:ipv4-address;
                    description "The IP address of this host.";
                }

                leaf mac-address {
                    type yang:mac-address;
                    description "The MAC address of this host.";
                }

                leaf pppoe-session-id {
                    type uint32;
                    description "The PPPoE session id of this host.";
                }

                leaf group-interface-name {
                    type leafref {
                        path "../../group-interface/group-interface-name";
                    }
                    description "The group-interface this host belongs to.";
                }

            } // list host

            container tunnel-interface {
                description "Enter the tunnel-interface context";

                list rsvp-p2mp-root {
                    key "lsp-name";
                    description "Enter the rsvp-p2mp-root context";

                    leaf lsp-name {
                        type leafref {
                            path "../../../../tunnel-interface/rsvp-p2mp-root/lsp-name";
                        }
                        description "RSVP p2mp lsp name.";
                    }

                    leaf oper-state {
                        type types-sros:oper-state;
                        description "The current operating state of the IGMP protocol on this interface.";
                    }

                    container statistics {

                        container received {
                            description "Received message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                        } // container received

                        container transmitted {
                            description "Transmit message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                            leaf errors {
                                type yang:counter32;
                                description "Transmission Errors.";
                            }

                        } // container transmitted

                        container error {
                            description "Error message statistics.";

                            leaf bad-length {
                                type yang:counter32;
                                description "Bad length.";
                            }

                            leaf bad-ip-checksum {
                                type yang:counter32;
                                description "Bad Ip checksum.";
                            }

                            leaf unknown-type {
                                type yang:counter32;
                                description "Unknown type.";
                            }

                            leaf wrong-version {
                                type yang:counter32;
                                description "Wrong version.";
                            }

                            leaf import-policy-drops {
                                type yang:counter32;
                                description
                                    "Number of times we matched the host IP address or group or
                                     source addresses specified in the import policy.";
                            }

                            leaf missing-router-alert {
                                type yang:counter32;
                                description "Router alert flag is not set.";
                            }

                            leaf bad-encoding {
                                type yang:counter32;
                                description "Badly encoded.";
                            }

                            leaf local-scope {
                                type yang:counter32;
                                description "Link-local scope multicast group address.";
                            }

                            leaf mcac-policy-drops {
                                type yang:counter32;
                                description
                                    "Number of times a join is dropped because of applying a
                                     multicast CAC policy.";
                            }

                            leaf reached-maximum-number-groups {
                                type yang:counter32;
                                description
                                    "Number of times a join is dropped because we reached the maximum
                                     number of groups.";
                            }

                            leaf reached-maximum-number-group-sources {
                                type yang:counter32;
                                description
                                    "Number of times a join is dropped because we reached the maximum
                                     number group-source combinations.";
                            }

                            leaf reached-maximum-number-sources {
                                type yang:counter32;
                                description
                                    "Number of times a join is dropped because we reached the maximum
                                     number of sources per group.";
                            }

                            leaf out-of-memory-drops {
                                type yang:counter32;
                                description "Number of times a join is dropped because we ran out of memory.";
                            }

                            leaf mcs-failures {
                                type yang:counter32;
                                description "Number of times a group could not be synced through multi chassis synchronisation (MCS).";
                            }

                            leaf non-local {
                                type yang:counter32;
                                description "Non-local sender source IP address.";
                            }

                        } // container error

                    } // container statistics

                    list group {
                        key "group-address";
                        description "Multicast group membership information that joined on the tunnel.";

                        leaf group-address {
                            type types-sros:ipv4-multicast-address;
                            description "Group address of multicast channel";
                        }

                        leaf group-type {
                            type types-igmp:learn-type;
                        }

                        leaf filter-mode {
                            type types-igmp:filter-mode;
                        }

                        leaf expiry-time {
                            type uint32;
                            units "seconds";
                            description "The time left before multicast group timeout.";
                        }

                        leaf uptime {
                            type uint32;
                            units "seconds";
                            description "The time elapsed since this entry was created.";
                        }

                        leaf v1-host-timer {
                            type uint32;
                            units "seconds";
                            description
                                "The time remaining until the local router will assume that
                                 there are no longer any version 1 members.";
                        }

                        leaf v2-host-timer {
                            type uint32;
                            units "seconds";
                            description
                                "The time remaining until the local router will assume that
                                 there are no longer any version 2 members.";
                        }

                        leaf igmp-compatibility-mode {
                            type types-igmp:igmp-version;
                            description "Compatibility with older version routers.";
                        }

                        leaf last-reporter {
                            type types-sros:ip-address;
                            description
                                "The last host address which has sent the report to join
                                 the multicast group.";
                        }

                        list source {
                            key "source-address";
                            description "List of multicast source information of the multicast group.";

                            leaf source-address {
                                type types-sros:ipv4-address;
                                description "Source address of multicast channel.";
                            }

                            leaf source-type {
                                type types-igmp:learn-type;
                            }

                            leaf forwarding-state {
                                type types-igmp:forwarding-state;
                                description "Traffic forwardeding state on this port.";
                            }

                            leaf expiry-time {
                                type uint32;
                                units "seconds";
                                description "The time left before multicast group timeout.";
                            }

                            leaf uptime {
                                type uint32;
                                units "seconds";
                                description "The time elapsed since this entry was created.";
                            }

                        } // list source

                    } // list group

                } // list rsvp-p2mp-root

                list ldp-p2mp-root {
                    key "p2mp-id sender-address";
                    description "Enter the ldp-p2mp-root context";

                    leaf p2mp-id {
                        type leafref {
                            path "../../../../tunnel-interface/ldp-p2mp-root/p2mp-id";
                        }
                        description "LDP p2mp Id.";
                    }

                    leaf sender-address {
                        type leafref {
                            path "../../../../tunnel-interface/ldp-p2mp-root[p2mp-id=current()/../p2mp-id]/sender-address";
                        }
                        description "The sender address of the root node.";
                    }

                    leaf oper-state {
                        type types-sros:oper-state;
                        description "The current operating state of the IGMP protocol on this interface.";
                    }

                    container statistics {

                        container received {
                            description "Received message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                        } // container received

                        container transmitted {
                            description "Transmit message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                            leaf errors {
                                type yang:counter32;
                                description "Transmission Errors.";
                            }

                        } // container transmitted

                        container error {
                            description "Error message statistics.";

                            leaf bad-length {
                                type yang:counter32;
                                description "Bad length.";
                            }

                            leaf bad-ip-checksum {
                                type yang:counter32;
                                description "Bad Ip checksum.";
                            }

                            leaf unknown-type {
                                type yang:counter32;
                                description "Unknown type.";
                            }

                            leaf wrong-version {
                                type yang:counter32;
                                description "Wrong version.";
                            }

                            leaf import-policy-drops {
                                type yang:counter32;
                                description
                                    "Number of times we matched the host IP address or group or
                                     source addresses specified in the import policy.";
                            }

                            leaf missing-router-alert {
                                type yang:counter32;
                                description "Router alert flag is not set.";
                            }

                            leaf bad-encoding {
                                type yang:counter32;
                                description "Badly encoded.";
                            }

                            leaf local-scope {
                                type yang:counter32;
                                description "Link-local scope multicast group address.";
                            }

                            leaf mcac-policy-drops {
                                type yang:counter32;
                                description
                                    "Number of times a join is dropped because of applying a
                                     multicast CAC policy.";
                            }

                            leaf reached-maximum-number-groups {
                                type yang:counter32;
                                description
                                    "Number of times a join is dropped because we reached the maximum
                                     number of groups.";
                            }

                            leaf reached-maximum-number-group-sources {
                                type yang:counter32;
                                description
                                    "Number of times a join is dropped because we reached the maximum
                                     number group-source combinations.";
                            }

                            leaf reached-maximum-number-sources {
                                type yang:counter32;
                                description
                                    "Number of times a join is dropped because we reached the maximum
                                     number of sources per group.";
                            }

                            leaf out-of-memory-drops {
                                type yang:counter32;
                                description "Number of times a join is dropped because we ran out of memory.";
                            }

                            leaf mcs-failures {
                                type yang:counter32;
                                description "Number of times a group could not be synced through multi chassis synchronisation (MCS).";
                            }

                            leaf non-local {
                                type yang:counter32;
                                description "Non-local sender source IP address.";
                            }

                        } // container error

                    } // container statistics

                    list group {
                        key "group-address";
                        description "Multicast group membership information that joined on the tunnel.";

                        leaf group-address {
                            type types-sros:ipv4-multicast-address;
                            description "Group address of multicast channel";
                        }

                        leaf group-type {
                            type types-igmp:learn-type;
                        }

                        leaf filter-mode {
                            type types-igmp:filter-mode;
                        }

                        leaf expiry-time {
                            type uint32;
                            units "seconds";
                            description "The time left before multicast group timeout.";
                        }

                        leaf uptime {
                            type uint32;
                            units "seconds";
                            description "The time elapsed since this entry was created.";
                        }

                        leaf v1-host-timer {
                            type uint32;
                            units "seconds";
                            description
                                "The time remaining until the local router will assume that
                                 there are no longer any version 1 members.";
                        }

                        leaf v2-host-timer {
                            type uint32;
                            units "seconds";
                            description
                                "The time remaining until the local router will assume that
                                 there are no longer any version 2 members.";
                        }

                        leaf igmp-compatibility-mode {
                            type types-igmp:igmp-version;
                            description "Compatibility with older version routers.";
                        }

                        leaf last-reporter {
                            type types-sros:ip-address;
                            description
                                "The last host address which has sent the report to join
                                 the multicast group.";
                        }

                        list source {
                            key "source-address";
                            description "List of multicast source information of the multicast group.";

                            leaf source-address {
                                type types-sros:ipv4-address;
                                description "Source address of multicast channel.";
                            }

                            leaf source-type {
                                type types-igmp:learn-type;
                            }

                            leaf forwarding-state {
                                type types-igmp:forwarding-state;
                                description "Traffic forwardeding state on this port.";
                            }

                            leaf expiry-time {
                                type uint32;
                                units "seconds";
                                description "The time left before multicast group timeout.";
                            }

                            leaf uptime {
                                type uint32;
                                units "seconds";
                                description "The time elapsed since this entry was created.";
                            }

                        } // list source

                    } // list group

                } // list ldp-p2mp-root

            } // container tunnel-interface

            list ipsec-static-tunnel {
                key "tunnel-name sa-id";
                description "IGMP IPsec Static tunnel parameters.";

                leaf tunnel-name {
                    type types-sros:named-item;
                    description "IPsec tunnel name.";
                }

                leaf sa-id {
                    type uint32 {
                        range "1..16";
                    }
                    description "Security Association Id";
                }

                leaf oper-state {
                    type types-sros:oper-state;
                    description "The current operating state of the IGMP protocol on this interface.";
                }

                leaf oper-version {
                    type types-igmp:igmp-version;
                    description "The operational version of the IGMP which is running on this interface.";
                }

                leaf group-count {
                    type int32;
                    description "The number of multicast groups which have been learned on this interface.";
                }

                leaf next-general-query-time {
                    type uint32;
                    units "seconds";
                    description
                        "The time remaining before the general query is sent on this interface
                         if this router is the querier.";
                }

                container statistics {

                    container received {
                        description "Received message statistics.";

                        leaf general-queries {
                            type yang:counter32;
                            description "General Queries.";
                        }

                        leaf group-queries {
                            type yang:counter32;
                            description "Group Specific Queries.";
                        }

                        leaf group-source-queries {
                            type yang:counter32;
                            description "Group and Source Specific Queries.";
                        }

                        leaf v1-reports {
                            type yang:counter32;
                            description "V1 Reports.";
                        }

                        leaf v2-reports {
                            type yang:counter32;
                            description "V2 Reports.";
                        }

                        leaf v3-reports {
                            type yang:counter32;
                            description "V3 Reports.";
                        }

                        leaf leaves {
                            type yang:counter32;
                            description "Leaves.";
                        }

                        leaf drops {
                            type yang:counter32;
                            description "Total number of dropped packets.";
                        }

                    } // container received

                    container transmitted {
                        description "Transmit message statistics.";

                        leaf general-queries {
                            type yang:counter32;
                            description "General Queries.";
                        }

                        leaf group-queries {
                            type yang:counter32;
                            description "Group Specific Queries.";
                        }

                        leaf group-source-queries {
                            type yang:counter32;
                            description "Group and Source Specific Queries.";
                        }

                        leaf v1-reports {
                            type yang:counter32;
                            description "V1 Reports.";
                        }

                        leaf v2-reports {
                            type yang:counter32;
                            description "V2 Reports.";
                        }

                        leaf v3-reports {
                            type yang:counter32;
                            description "V3 Reports.";
                        }

                        leaf leaves {
                            type yang:counter32;
                            description "Leaves.";
                        }

                        leaf drops {
                            type yang:counter32;
                            description "Total number of dropped packets.";
                        }

                        leaf errors {
                            type yang:counter32;
                            description "Transmission Errors.";
                        }

                    } // container transmitted

                    container error {
                        description "Error message statistics.";

                        leaf bad-length {
                            type yang:counter32;
                            description "Bad length.";
                        }

                        leaf bad-ip-checksum {
                            type yang:counter32;
                            description "Bad Ip checksum.";
                        }

                        leaf unknown-type {
                            type yang:counter32;
                            description "Unknown type.";
                        }

                        leaf wrong-version {
                            type yang:counter32;
                            description "Wrong version.";
                        }

                        leaf import-policy-drops {
                            type yang:counter32;
                            description
                                "Number of times we matched the host IP address or group or
                                 source addresses specified in the import policy.";
                        }

                        leaf missing-router-alert {
                            type yang:counter32;
                            description "Router alert flag is not set.";
                        }

                        leaf bad-encoding {
                            type yang:counter32;
                            description "Badly encoded.";
                        }

                        leaf local-scope {
                            type yang:counter32;
                            description "Link-local scope multicast group address.";
                        }

                        leaf mcac-policy-drops {
                            type yang:counter32;
                            description
                                "Number of times a join is dropped because of applying a
                                 multicast CAC policy.";
                        }

                        leaf reached-maximum-number-groups {
                            type yang:counter32;
                            description
                                "Number of times a join is dropped because we reached the maximum
                                 number of groups.";
                        }

                        leaf reached-maximum-number-group-sources {
                            type yang:counter32;
                            description
                                "Number of times a join is dropped because we reached the maximum
                                 number group-source combinations.";
                        }

                        leaf reached-maximum-number-sources {
                            type yang:counter32;
                            description
                                "Number of times a join is dropped because we reached the maximum
                                 number of sources per group.";
                        }

                        leaf out-of-memory-drops {
                            type yang:counter32;
                            description "Number of times a join is dropped because we ran out of memory.";
                        }

                        leaf mcs-failures {
                            type yang:counter32;
                            description "Number of times a group could not be synced through multi chassis synchronisation (MCS).";
                        }

                        leaf non-local {
                            type yang:counter32;
                            description "Non-local sender source IP address.";
                        }

                    } // container error

                } // container statistics

                list group {
                    key "group-address";
                    description "Multicast group membership information that joined on the tunnel.";

                    leaf group-address {
                        type types-sros:ipv4-multicast-address;
                        description "Group address of multicast channel";
                    }

                    leaf group-type {
                        type types-igmp:learn-type;
                    }

                    leaf filter-mode {
                        type types-igmp:filter-mode;
                    }

                    leaf expiry-time {
                        type uint32;
                        units "seconds";
                        description "The time left before multicast group timeout.";
                    }

                    leaf uptime {
                        type uint32;
                        units "seconds";
                        description "The time elapsed since this entry was created.";
                    }

                    leaf v1-host-timer {
                        type uint32;
                        units "seconds";
                        description
                            "The time remaining until the local router will assume that
                             there are no longer any version 1 members.";
                    }

                    leaf v2-host-timer {
                        type uint32;
                        units "seconds";
                        description
                            "The time remaining until the local router will assume that
                             there are no longer any version 2 members.";
                    }

                    leaf igmp-compatibility-mode {
                        type types-igmp:igmp-version;
                        description "Compatibility with older version routers.";
                    }

                    leaf last-reporter {
                        type types-sros:ip-address;
                        description
                            "The last host address which has sent the report to join
                             the multicast group.";
                    }

                    list source {
                        key "source-address";
                        description "List of multicast source information of the multicast group.";

                        leaf source-address {
                            type types-sros:ipv4-address;
                            description "Source address of multicast channel.";
                        }

                        leaf source-type {
                            type types-igmp:learn-type;
                        }

                        leaf forwarding-state {
                            type types-igmp:forwarding-state;
                            description "Traffic forwardeding state on this port.";
                        }

                        leaf expiry-time {
                            type uint32;
                            units "seconds";
                            description "The time left before multicast group timeout.";
                        }

                        leaf uptime {
                            type uint32;
                            units "seconds";
                            description "The time elapsed since this entry was created.";
                        }

                    } // list source

                } // list group

            } // list ipsec-static-tunnel

            list ipsec-ru-tunnel {
                key "gateway-name sap-address sap-port sa-id";
                description "IGMP IPsec Remote-User tunnel parameters.";

                leaf gateway-name {
                    type types-sros:named-item;
                    description "IPsec gateway name.";
                }

                leaf sap-address {
                    type types-sros:ipv4-address;
                    description "The address of the SAP IPsec gateway to the tunnel.";
                }

                leaf sap-port {
                    type types-sros:tcp-udp-port;
                    description "The UDP port of the SAP IPsec gateway to the tunnel.";
                }

                leaf sa-id {
                    type uint32 {
                        range "1..16";
                    }
                    description "SA Id";
                }

                leaf oper-state {
                    type types-sros:oper-state;
                    description "The current operating state of the IGMP protocol on this interface.";
                }

                leaf oper-version {
                    type types-igmp:igmp-version;
                    description "The operational version of the IGMP which is running on this interface.";
                }

                leaf group-count {
                    type int32;
                    description "The number of multicast groups which have been learned on this interface.";
                }

                leaf next-general-query-time {
                    type uint32;
                    units "seconds";
                    description
                        "The time remaining before the general query is sent on this interface
                         if this router is the querier.";
                }

                container statistics {

                    container received {
                        description "Received message statistics.";

                        leaf general-queries {
                            type yang:counter32;
                            description "General Queries.";
                        }

                        leaf group-queries {
                            type yang:counter32;
                            description "Group Specific Queries.";
                        }

                        leaf group-source-queries {
                            type yang:counter32;
                            description "Group and Source Specific Queries.";
                        }

                        leaf v1-reports {
                            type yang:counter32;
                            description "V1 Reports.";
                        }

                        leaf v2-reports {
                            type yang:counter32;
                            description "V2 Reports.";
                        }

                        leaf v3-reports {
                            type yang:counter32;
                            description "V3 Reports.";
                        }

                        leaf leaves {
                            type yang:counter32;
                            description "Leaves.";
                        }

                        leaf drops {
                            type yang:counter32;
                            description "Total number of dropped packets.";
                        }

                    } // container received

                    container transmitted {
                        description "Transmit message statistics.";

                        leaf general-queries {
                            type yang:counter32;
                            description "General Queries.";
                        }

                        leaf group-queries {
                            type yang:counter32;
                            description "Group Specific Queries.";
                        }

                        leaf group-source-queries {
                            type yang:counter32;
                            description "Group and Source Specific Queries.";
                        }

                        leaf v1-reports {
                            type yang:counter32;
                            description "V1 Reports.";
                        }

                        leaf v2-reports {
                            type yang:counter32;
                            description "V2 Reports.";
                        }

                        leaf v3-reports {
                            type yang:counter32;
                            description "V3 Reports.";
                        }

                        leaf leaves {
                            type yang:counter32;
                            description "Leaves.";
                        }

                        leaf drops {
                            type yang:counter32;
                            description "Total number of dropped packets.";
                        }

                        leaf errors {
                            type yang:counter32;
                            description "Transmission Errors.";
                        }

                    } // container transmitted

                    container error {
                        description "Error message statistics.";

                        leaf bad-length {
                            type yang:counter32;
                            description "Bad length.";
                        }

                        leaf bad-ip-checksum {
                            type yang:counter32;
                            description "Bad Ip checksum.";
                        }

                        leaf unknown-type {
                            type yang:counter32;
                            description "Unknown type.";
                        }

                        leaf wrong-version {
                            type yang:counter32;
                            description "Wrong version.";
                        }

                        leaf import-policy-drops {
                            type yang:counter32;
                            description
                                "Number of times we matched the host IP address or group or
                                 source addresses specified in the import policy.";
                        }

                        leaf missing-router-alert {
                            type yang:counter32;
                            description "Router alert flag is not set.";
                        }

                        leaf bad-encoding {
                            type yang:counter32;
                            description "Badly encoded.";
                        }

                        leaf local-scope {
                            type yang:counter32;
                            description "Link-local scope multicast group address.";
                        }

                        leaf mcac-policy-drops {
                            type yang:counter32;
                            description
                                "Number of times a join is dropped because of applying a
                                 multicast CAC policy.";
                        }

                        leaf reached-maximum-number-groups {
                            type yang:counter32;
                            description
                                "Number of times a join is dropped because we reached the maximum
                                 number of groups.";
                        }

                        leaf reached-maximum-number-group-sources {
                            type yang:counter32;
                            description
                                "Number of times a join is dropped because we reached the maximum
                                 number group-source combinations.";
                        }

                        leaf reached-maximum-number-sources {
                            type yang:counter32;
                            description
                                "Number of times a join is dropped because we reached the maximum
                                 number of sources per group.";
                        }

                        leaf out-of-memory-drops {
                            type yang:counter32;
                            description "Number of times a join is dropped because we ran out of memory.";
                        }

                        leaf mcs-failures {
                            type yang:counter32;
                            description "Number of times a group could not be synced through multi chassis synchronisation (MCS).";
                        }

                        leaf non-local {
                            type yang:counter32;
                            description "Non-local sender source IP address.";
                        }

                    } // container error

                } // container statistics

                list group {
                    key "group-address";
                    description "Multicast group membership information that joined on the tunnel.";

                    leaf group-address {
                        type types-sros:ipv4-multicast-address;
                        description "Group address of multicast channel";
                    }

                    leaf group-type {
                        type types-igmp:learn-type;
                    }

                    leaf filter-mode {
                        type types-igmp:filter-mode;
                    }

                    leaf expiry-time {
                        type uint32;
                        units "seconds";
                        description "The time left before multicast group timeout.";
                    }

                    leaf uptime {
                        type uint32;
                        units "seconds";
                        description "The time elapsed since this entry was created.";
                    }

                    leaf v1-host-timer {
                        type uint32;
                        units "seconds";
                        description
                            "The time remaining until the local router will assume that
                             there are no longer any version 1 members.";
                    }

                    leaf v2-host-timer {
                        type uint32;
                        units "seconds";
                        description
                            "The time remaining until the local router will assume that
                             there are no longer any version 2 members.";
                    }

                    leaf igmp-compatibility-mode {
                        type types-igmp:igmp-version;
                        description "Compatibility with older version routers.";
                    }

                    leaf last-reporter {
                        type types-sros:ip-address;
                        description
                            "The last host address which has sent the report to join
                             the multicast group.";
                    }

                    list source {
                        key "source-address";
                        description "List of multicast source information of the multicast group.";

                        leaf source-address {
                            type types-sros:ipv4-address;
                            description "Source address of multicast channel.";
                        }

                        leaf source-type {
                            type types-igmp:learn-type;
                        }

                        leaf forwarding-state {
                            type types-igmp:forwarding-state;
                            description "Traffic forwardeding state on this port.";
                        }

                        leaf expiry-time {
                            type uint32;
                            units "seconds";
                            description "The time left before multicast group timeout.";
                        }

                        leaf uptime {
                            type uint32;
                            units "seconds";
                            description "The time elapsed since this entry was created.";
                        }

                    } // list source

                } // list group

            } // list ipsec-ru-tunnel

        } // container igmp

    } // grouping state-router-igmp

}
