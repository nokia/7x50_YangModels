submodule nokia-state-router-bgp {

    yang-version "1.1";

    belongs-to nokia-state { prefix "state"; }

    import ietf-inet-types                { prefix "inet"; }
    import ietf-yang-types                { prefix "yang"; }
    import nokia-sros-yang-extensions     { prefix "sros-ext"; }
    import nokia-types-bgp                { prefix "types-bgp"; }
    import nokia-types-router             { prefix "types-router"; }
    import nokia-types-services           { prefix "types-services"; }
    import nokia-types-sros               { prefix "types-sros"; }


    sros-ext:sros-major-release "rel19";

    organization "Nokia";

    contact
        "Nokia SR OS Support
         Web: <http://www.nokia.com>";

    description
        "Nokia YANG Data model with operational state for bgp protocol on SR OS based routers.

         Copyright 2016 Nokia. All rights reserved. Reproduction of this document
         is authorized on the condition that the foregoing copyright notice is included.

         This nokia-state-router-bgp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-04-22";

    grouping state-router-bgp {
        container bgp {
            description "Enter the bgp context";

            container statistics {

                leaf operational-state {
                    type string;
                }

                leaf peer-groups {
                    type uint32;
                }

                leaf peers {
                    type uint32;
                }

                leaf vpn-peer-groups {
                    type uint32;
                }

                leaf vpn-peers {
                    type uint32;
                }

                leaf bgp-paths {
                    type uint32;
                }

                leaf path-memory {
                    type uint32;
                }

                container routes-per-family {
                    description "Family specific routes counters.";

                    container ipv4 {
                        description "ipv4 counter values.";

                        leaf remote-routes {
                            type uint32;
                        }

                        leaf remote-active-routes {
                            type uint32;
                        }

                        leaf backup-routes {
                            type uint32;
                        }

                    } // container ipv4

                    container ipv6 {
                        description "ipv6 counter values.";

                        leaf remote-routes {
                            type uint32;
                        }

                        leaf remote-active-routes {
                            type uint32;
                        }

                        leaf backup-routes {
                            type uint32;
                        }

                    } // container ipv6

                    container route-flap-dampening {

                        container ipv4-ipv6 {
                            description "flap dampening statistics for ipv4 and ipv6 unicast prefixes.";

                            leaf suppressed-routes {
                                type uint32;
                            }

                            leaf history-routes {
                                type uint32;
                            }

                            leaf decay-routes {
                                type uint32;
                            }

                        } // container ipv4-ipv6

                        container vpnipv4-vpnipv6 {
                            description "flap dampening statistics for vpn-ipv4 and vpn-ipv6 prefixes.";

                            leaf local-routes {
                                type uint32;
                            }

                            leaf suppressed-routes {
                                type uint32;
                            }

                            leaf history-routes {
                                type uint32;
                            }

                            leaf decay-routes {
                                type uint32;
                            }

                        } // container vpnipv4-vpnipv6

                    } // container route-flap-dampening

                    container vpn-ipv4 {
                        description "vpn-ipv4 counter values.";

                        leaf remote-routes {
                            type uint32;
                        }

                        leaf remote-active-routes {
                            type uint32;
                        }

                        leaf backup-routes {
                            type uint32;
                        }

                    } // container vpn-ipv4

                    container vpn-ipv6 {
                        description "vpn-ipv6 counter values.";

                        leaf remote-routes {
                            type uint32;
                        }

                        leaf remote-active-routes {
                            type uint32;
                        }

                        leaf backup-routes {
                            type uint32;
                        }

                    } // container vpn-ipv6

                    container mvpn-ipv4 {
                        description "mvpn-ipv4 counter values.";

                        leaf remote-routes {
                            type uint32;
                        }

                        leaf remote-active-routes {
                            type uint32;
                        }

                        leaf backup-routes {
                            type uint32;
                        }

                    } // container mvpn-ipv4

                    container mvpn-ipv6 {
                        description "mvpn-ipv6 counter values.";

                        leaf remote-routes {
                            type uint32;
                        }

                        leaf remote-active-routes {
                            type uint32;
                        }

                        leaf backup-routes {
                            type uint32;
                        }

                    } // container mvpn-ipv6

                    container mcast-ipv4 {
                        description "mcast-ipv4 counter values.";

                        leaf remote-routes {
                            type uint32;
                        }

                        leaf remote-active-routes {
                            type uint32;
                        }

                        leaf backup-routes {
                            type uint32;
                        }

                    } // container mcast-ipv4

                    container mcast-ipv6 {
                        description "mcast-ipv6 counter values.";

                        leaf remote-routes {
                            type uint32;
                        }

                        leaf remote-active-routes {
                            type uint32;
                        }

                        leaf backup-routes {
                            type uint32;
                        }

                    } // container mcast-ipv6

                    container l2-vpn {
                        description "l2-vpn counter values.";

                        leaf remote-routes {
                            type uint32;
                        }

                        leaf remote-active-routes {
                            type uint32;
                        }

                        leaf backup-routes {
                            type uint32;
                        }

                    } // container l2-vpn

                    container mdt-safi {
                        description "mdt-safi counter values.";

                        leaf remote-routes {
                            type uint32;
                        }

                        leaf remote-active-routes {
                            type uint32;
                        }

                        leaf backup-routes {
                            type uint32;
                        }

                    } // container mdt-safi

                    container ms-pw {
                        description "ms-pw counter values.";

                        leaf remote-routes {
                            type uint32;
                        }

                        leaf remote-active-routes {
                            type uint32;
                        }

                        leaf backup-routes {
                            type uint32;
                        }

                    } // container ms-pw

                    container flow-ipv4 {
                        description "flow-ipv4 counter values.";

                        leaf remote-routes {
                            type uint32;
                        }

                        leaf remote-active-routes {
                            type uint32;
                        }

                        leaf backup-routes {
                            type uint32;
                        }

                    } // container flow-ipv4

                    container flow-ipv6 {
                        description "flow-ipv6 counter values.";

                        leaf remote-routes {
                            type uint32;
                        }

                        leaf remote-active-routes {
                            type uint32;
                        }

                        leaf backup-routes {
                            type uint32;
                        }

                    } // container flow-ipv6

                    container route-target {
                        description "route-target counter values.";

                        leaf remote-routes {
                            type uint32;
                        }

                        leaf remote-active-routes {
                            type uint32;
                        }

                        leaf backup-routes {
                            type uint32;
                        }

                    } // container route-target

                    container mcast-vpn-ipv4 {
                        description "mcast-vpn-ipv4 counter values.";

                        leaf remote-routes {
                            type uint32;
                        }

                        leaf remote-active-routes {
                            type uint32;
                        }

                        leaf backup-routes {
                            type uint32;
                        }

                    } // container mcast-vpn-ipv4

                    container mcast-vpn-ipv6 {
                        description "mcast-vpn-ipv6 counter values.";

                        leaf remote-routes {
                            type uint32;
                        }

                        leaf remote-active-routes {
                            type uint32;
                        }

                        leaf backup-routes {
                            type uint32;
                        }

                    } // container mcast-vpn-ipv6

                    container evpn {
                        description "evpn counter values.";

                        leaf remote-routes {
                            type uint32;
                        }

                        leaf remote-active-routes {
                            type uint32;
                        }

                        leaf backup-routes {
                            type uint32;
                        }

                    } // container evpn

                    container label-ipv4 {
                        description "label-ipv4 counter values.";

                        leaf remote-routes {
                            type uint32;
                        }

                        leaf remote-active-routes {
                            type uint32;
                        }

                        leaf backup-routes {
                            type uint32;
                        }

                    } // container label-ipv4

                    container label-ipv6 {
                        description "label-ipv6 counter values.";

                        leaf remote-routes {
                            type uint32;
                        }

                        leaf remote-active-routes {
                            type uint32;
                        }

                        leaf backup-routes {
                            type uint32;
                        }

                    } // container label-ipv6

                    container bgp-ls {
                        description "bgp-ls counter values.";

                        leaf remote-routes {
                            type uint32;
                        }

                        leaf remote-active-routes {
                            type uint32;
                        }

                        leaf backup-routes {
                            type uint32;
                        }

                    } // container bgp-ls

                    container sr-policy-ipv4 {
                        description "sr-policy-ipv4 counter values.";

                        leaf remote-routes {
                            type uint32;
                        }

                        leaf remote-active-routes {
                            type uint32;
                        }

                        leaf backup-routes {
                            type uint32;
                        }

                    } // container sr-policy-ipv4

                } // container routes-per-family

            } // container statistics

            list neighbor {
                key "ip-address";
                description "Enter the neighbor context";

                leaf ip-address {
                    type types-sros:ip-address-with-zone;
                    description "BGP group neighbor";
                }

                container statistics {

                    leaf peer-as {
                        type uint32;
                        description "specifies the AS number for dynamic peers.";
                    }

                    leaf peer-port {
                        type int32;
                        description "specifies the peer's port.";
                    }

                    leaf local-port {
                        type int32;
                        description "specifies the local port on this peer.";
                    }

                    leaf session-state {
                        type string {
                            length "0..32";
                        }
                        description "specifies the current BGP state of this peer.";
                    }

                    leaf last-state {
                        type string {
                            length "0..32";
                        }
                        description "specifies the last BGP state of this peer.";
                    }

                    leaf last-event {
                        type string {
                            length "0..32";
                        }
                        description "specifies the last BGP event of this peer.";
                    }

                    leaf last-error {
                        type string {
                            length "0..80";
                        }
                        description "specifies the last error of this peer.";
                    }

                    leaf-list negotiated-family {
                        type string {
                            length "0..16";
                        }
                        description "specifies the family successfully negotiated with the peer.";
                    }

                    leaf operational-local-address {
                        type types-sros:ip-unicast-address;
                        description "Local IP address used by the neighbor when communicating with BGP peers";
                    }

                    leaf peer-identifier {
                        type string {
                            length "0..16";
                        }
                        description "specifies the peers ip address.";
                    }

                    leaf established-transitions {
                        type uint32;
                        description "specifies the number of state transitions made by the peer.";
                    }

                    leaf last-established-time {
                        type yang:date-and-time;
                        description "specifies the time when the peer established the BGP session.";
                    }

                    leaf in-update-elapsed-time {
                        type yang:timeticks;
                        description "specifies the time elapsed since the last update was received.";
                    }

                    leaf hold-time-interval {
                        type int32;
                        description "specifies the hold time value negotiated with the peer.";
                    }

                    leaf remaining-idle-hold-time {
                        type uint32;
                        description
                            "specifies how much time is remaining until the Idle hold time
                             period runs out and session establishment can begin again for this peer.";
                    }

                    leaf keep-alive-interval {
                        type int32;
                        description "specifies the keep alive time value negotiated with the peer.";
                    }

                    leaf number-of-update-flaps {
                        type uint32;
                        description "specifies the number of flaps of updates from this peer.";
                    }

                    leaf update-errors {
                        type uint32;
                        description "specifies the number of update errors received from this peer.";
                    }

                    leaf-list negotiated-capability {
                        type string {
                            length "0..16";
                        }
                        description "specifies the capabilities successfully negotiated with the peer.";
                    }

                    leaf received-paths {
                        type uint32;
                        description "specifies the number of paths received from this peer.";
                    }

                    leaf dynamically-configured {
                        type boolean;
                        description "specifies dynamic peer.";
                    }

                    container remote-family {
                        description
                            "specifies the types of routing information to be distributed
                             by the remote end of this Peer of the BGP protocol.";

                        leaf-list family {
                            type string {
                                length "0..16";
                            }
                        }

                    } // container remote-family

                    container local-capability {
                        description "specifies the capabilities supported on the local end of the BGP Peer.";

                        leaf-list capability {
                            type string {
                                length "0..16";
                            }
                            description "specifies the capability name.";
                        }

                    } // container local-capability

                    container remote-capability {
                        description "specifies the capabilities advertised by the remote end of the BGP Peer.";

                        leaf-list capability {
                            type string {
                                length "0..16";
                            }
                            description "specifies the capability name.";
                        }

                    } // container remote-capability

                    container remote-add-path-capability {
                        description
                            "specifies the address families for which the add-path
                             receive capability is supported on the remote end of the BGP Peer.";

                        leaf-list send-capability {
                            type string {
                                length "0..16";
                            }
                            description "specifies the send capability families.";
                        }

                        leaf-list receive-capability {
                            type string {
                                length "0..16";
                            }
                            description "specifies the receive capability families.";
                        }

                    } // container remote-add-path-capability

                    container family-prefix {
                        description "prefix counter values.";

                        container ipv4 {
                            description "ipv4 counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container ipv4

                        container ipv6 {
                            description "ipv6 counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container ipv6

                        container vpn-ipv4 {
                            description "vpn-ipv4 counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container vpn-ipv4

                        container vpn-ipv6 {
                            description "vpn-ipv6 counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container vpn-ipv6

                        container mvpn-ipv4 {
                            description "mvpn-ipv4 counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container mvpn-ipv4

                        container mvpn-ipv6 {
                            description "mvpn-ipv6 counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container mvpn-ipv6

                        container mcast-ipv4 {
                            description "mcast-ipv4 counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container mcast-ipv4

                        container mcast-ipv6 {
                            description "mcast-ipv6 counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container mcast-ipv6

                        container l2-vpn {
                            description "l2-vpn counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container l2-vpn

                        container mdt-safi {
                            description "mdt-safi counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container mdt-safi

                        container ms-pw {
                            description "ms-pw counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container ms-pw

                        container flow-ipv4 {
                            description "flow-ipv4 counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container flow-ipv4

                        container flow-ipv6 {
                            description "flow-ipv6 counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container flow-ipv6

                        container route-target {
                            description "route-target counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container route-target

                        container mcast-vpn-ipv4 {
                            description "mcast-vpn-ipv4 counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container mcast-vpn-ipv4

                        container mcast-vpn-ipv6 {
                            description "mcast-vpn-ipv6 counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container mcast-vpn-ipv6

                        container evpn {
                            description "evpn counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container evpn

                        container label-ipv4 {
                            description "label-ipv4 counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container label-ipv4

                        container label-ipv6 {
                            description "label-ipv6 counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container label-ipv6

                        container bgp-ls {
                            description "bgp-ls counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container bgp-ls

                        container sr-policy-ipv4 {
                            description "sr-policy-ipv4 counter values.";

                            leaf backup {
                                type uint32;
                                description "specifies the number routes selected as backup from this peer.";
                            }

                            leaf received {
                                type uint32;
                                description "specifies the number of prefixes received from this peer.";
                            }

                            leaf active {
                                type uint32;
                                description "specifies the number of active prefixes from this peer.";
                            }

                            leaf suppressed {
                                type uint32;
                                description "specifies the number prefixes from this peer, which have been suppressed by damping.";
                            }

                            leaf rejected {
                                type uint32;
                                description "specifies the number of prefixes rejected from this peer.";
                            }

                            leaf sent {
                                type uint32;
                                description "specifies the number of prefixes transmitted to this peer.";
                            }

                        } // container sr-policy-ipv4

                    } // container family-prefix

                    container sent {
                        description "the counter values for queues, messages, octets, updates sent to the peer.";

                        leaf queues {
                            type uint64;
                        }

                        leaf messages {
                            type uint64;
                        }

                        leaf octets {
                            type uint64;
                        }

                        leaf updates {
                            type uint64;
                        }

                    } // container sent

                    container received {
                        description "the counter values for queues, messages, octets, updates received from the peer.";

                        leaf queues {
                            type uint64;
                        }

                        leaf messages {
                            type uint64;
                        }

                        leaf octets {
                            type uint64;
                        }

                        leaf updates {
                            type uint64;
                        }

                    } // container received

                } // container statistics

                container graceful-restart {
                    description "Enter the graceful-restart context";

                    leaf support {
                        type boolean;
                        description "specifies graceful-restart capability signaled by the peer.";
                    }

                    leaf restart-time-requested {
                        type uint32;
                        description "specifies the restart time requested by the peer.";
                    }

                    leaf stale-route-time {
                        type uint32;
                        description "specifies the time value until when stale routes can be used.";
                    }

                    leaf peer-status {
                        type string {
                            length "0..32";
                        }
                        description "specifies the graceful-restart operational status on the peer.";
                    }

                    leaf number-of-restarts {
                        type uint32;
                        description "specifies the number of times the peer has attempted restart.";
                    }

                    leaf last-restart-time {
                        type yang:date-and-time;
                        description "specifies the last time the peer attempted restart.";
                    }

                    container restart-family {
                        description "specifies the AFI/SAFI the peer supports restart for.";

                        leaf-list family {
                            type string {
                                length "0..16";
                            }
                        }

                    } // container restart-family

                    container forwarding-family {
                        description "specifies the AFI/SAFI the peer saved forwarding for.";

                        leaf-list family {
                            type string {
                                length "0..16";
                            }
                        }

                    } // container forwarding-family

                    container negotiated-family {
                        description
                            "specifies the capability type of NLRI that NOTIFICATION-triggered
                             restart is negotiated for by the peer.";

                        leaf-list family {
                            type string {
                                length "0..16";
                            }
                        }

                    } // container negotiated-family

                    container received-end-of-rib-marker {
                        description "specifies the NLRI types that the peer received end of rib marker for.";

                        leaf-list family {
                            type string {
                                length "0..16";
                            }
                        }

                    } // container received-end-of-rib-marker

                    container sent-end-of-rib-marker {
                        description "specifies the NLRI types the peer sent end of rib marker for.";

                        leaf-list family {
                            type string {
                                length "0..16";
                            }
                        }

                    } // container sent-end-of-rib-marker

                    container notification-family {
                        description "specifies the NLRI types that the peer supports notification for.";

                        leaf-list family {
                            type string {
                                length "0..16";
                            }
                        }

                    } // container notification-family

                    container long-lived {
                        description "Enter the long-lived context";

                        list family {
                            key "family-type";
                            description "Enter the family context";

                            leaf family-type {
                                type types-bgp:llgr-family-identifiers;
                                description "Address family type for LLGR";
                            }

                            leaf advertised-stale-time-received {
                                type uint32;
                                description "Long Lived stale time received from the peer for this family.";
                            }

                            leaf stale-time-negotiated {
                                type uint32;
                                description "Long Lived stale time negotiated with the peer for this family.";
                            }

                            leaf flags-received {
                                type boolean;
                                description "specifies F-bit recieved  by the peer.";
                            }

                            leaf flags-supported {
                                type boolean;
                                description "specifies F-bit supported  by the peer.";
                            }

                        } // list family

                    } // container long-lived

                } // container graceful-restart

                list prefix-limit {
                    key "family";
                    description "Enter the prefix-limit context";

                    leaf family {
                        type types-bgp:ip-family-identifier;
                        description "Address family to which the limit applies";
                    }

                    leaf inherit {
                        type boolean;
                        description
                            "The value of this object specifies if the peer entry in this row, should inherit the operational value of an object,
                             or use the administratively set value.";
                    }

                } // list prefix-limit

            } // list neighbor

            list bmp-session {
                key "station-name";
                description
                    "Statistics for the BMP sessions between this router
                     and a BMP station.";

                leaf station-name {
                    type types-sros:named-item;
                    description "BMP station used for the BMP session.";
                }

                leaf connection-state {
                    type enumeration {
                        enum "inactive"                     { value 0; description "The BMP station is configured, but other constraints prevent BMP from starting a session."; }
                        enum "shutdown"                     { value 1; description "The connection to the BMP-station is administratively disabled."; }
                        enum "idle"                         { value 2; description "BMP is in between attempts to open a new session to the BMP-station."; }
                        enum "connecting"                   { value 3; description "BMP is actively trying to set up a TCP connection to the BMP-station."; }
                        enum "welcoming"                    { value 4; description "BMP has succesfully set up a TCP connection, but hasn't started sending BMP messages yet."; }
                        enum "established"                  { value 5; description "BMP has a fully functional BMP-session to the BMP-station."; }
                    }
                    description "Operational state of the BMP session with the BMP station.";
                }

                leaf local-address {
                    type types-sros:ip-address;
                    description "Local IP address of the BMP session with the BMP station.";
                }

                leaf local-port {
                    type types-sros:tcp-udp-port;
                    description "Local TCP port of the BMP session with the BMP station.";
                }

                leaf connection-state-changed {
                    type yang:date-and-time;
                    description "Last time the connection-state of the BMP session with the BMP station was changed.";
                }

                leaf last-message-sent {
                    type yang:date-and-time;
                    description "Last time a message was sent in the BMP session with the BMP station.";
                }

                leaf bytes-sent {
                    type uint64;
                    description "Total number of bytes that were sent in the BMP session with the BMP station.";
                }

                leaf route-monitoring-messages {
                    type uint64;
                    description "Total number of route monitoring messages that were sent in the BMP session with the BMP station.";
                }

                leaf statistics-messages {
                    type uint64;
                    description "Total number of statistics messages that were sent in the BMP session with the BMP station.";
                }

                leaf peer-up-notifications {
                    type uint64;
                    description "Total number of peer-up notifications that were sent in the BMP session with the BMP station.";
                }

                leaf peer-down-notifications {
                    type uint64;
                    description "Total number of peer-down notification that were sent in the BMP session with the BMP station.";
                }

                leaf initiation-messages {
                    type uint64;
                    description "Total number of initiation messages that were sent in the BMP session with the BMP station.";
                }

                leaf termination-messages {
                    type uint64;
                    description "Total number of termination messages that were sent in the BMP session with the BMP station.";
                }

                leaf route-mirroring-messages {
                    type uint64;
                    description "Total number of route monitoring messages that were sent in the BMP session with the BMP station.";
                }

            } // list bmp-session

        } // container bgp

    } // grouping state-router-bgp

}
