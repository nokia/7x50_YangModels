submodule nokia-state-system-telemetry {

    yang-version "1.1";

    belongs-to nokia-state { prefix "state"; }

    import nokia-sros-yang-extensions     { prefix "sros-ext"; }
    import nokia-types-qos                { prefix "types-qos"; }
    import nokia-types-sros               { prefix "types-sros"; }


    sros-ext:sros-major-release "rel19";

    organization "Nokia";

    contact
        "Nokia SR OS Support
         Web: <http://www.nokia.com>";

    description
        "Nokia YANG Data model with operational state for system telemetry parameters. on SR OS based routers.

         Copyright 2016 Nokia. All rights reserved. Reproduction of this document
         is authorized on the condition that the foregoing copyright notice is included.

         This nokia-state-system-telemetry YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-02-14";

    grouping state-system-telemetry {
        container telemetry {
            description "Configure system telemetry related parameters.";

            container grpc {
                description
                    "This container holds information relating to
                     telemetry subscriptions over gRPC Subscribe RPC.";

                list subscription {
                    key "subscription-id";
                    description "List of gRPC subscriptions.";

                    leaf subscription-id {
                        type uint32;
                        description
                            "System generated identifier of the telemetry
                             subscription.";
                    }

                    leaf user-name {
                        type types-sros:named-item;
                        description "The name of the user who initiated subscription.";
                    }

                    leaf destination-address {
                        type types-sros:ip-address;
                        description "IP address of the telemetry stream destination.";
                    }

                    leaf destination-port {
                        type types-qos:tcp-udp-match-port;
                        description
                            "Protocol (UDP or TCP) port number for the telemetry
                             stream destination.";
                    }

                    leaf mode {
                        type enumeration {
                            enum "stream"                       { value 0; }
                            enum "once"                         { value 1; }
                        }
                        description
                            "Subscription mode, indicating trigger
                             source for data notifications.

                             Value 'stream' indicates that subscription is
                             long-lived and stream data according to the triggers
                             specified within the individual subscription paths.

                             Value 'once' indicates that subscription is
                             short-lived and stream single sample of all paths
                             and is terminated afterwards.";
                    }

                    leaf requested-qos {
                        type types-qos:dscp-name;
                        description
                            "Requested DSCP value in qos field of
                             the subscription.";
                    }

                    leaf operational-qos {
                        type types-qos:dscp-name;
                        description
                            "Operational DSCP value of subscription connection.
                             Only first qos request is accepted on connection.
                             DSCP value is reset to sgt-qos default after last
                             subscription on connection is terminated.";
                    }

                    list path {
                        key "path";
                        description "List of paths in gRPC subscription.";

                        leaf path {
                            type string {
                                length "1..4096";
                            }
                            description
                                "Path to a section of operational state of interest
                                 (the sensor).";
                        }

                        leaf mode {
                            type enumeration {
                                enum "target-defined"               { value 0; }
                                enum "on-change"                    { value 1; }
                                enum "sample"                       { value 2; }
                            }
                            description
                                "Subscription path mode, indicating how the
                                 SROS must return values in a subscription.

                                 Value 'target-defined' indicates that the SROS
                                 selects the relevant mode for each leaf.

                                 Value 'on-change' indicates that the SROS sends
                                 an update on leaf value change.

                                 Value 'sample' indicates that the SROS samples
                                 values according to the interval.";
                        }

                        leaf sample-interval {
                            type uint64;
                            units "milliseconds";
                            description
                                "Time in milliseconds between the device's sample of a
                                 telemetry data source.";
                        }

                        leaf finished-collection-count {
                            type uint64;
                            description
                                "Finished count of collection sample of a telemetry
                                 data source.";
                        }

                        leaf deferred-collection-count {
                            type uint64;
                            description
                                "Deferred count of collection sample of a telemetry
                                 data source.";
                        }

                        leaf total-collection-time {
                            type uint64;
                            units "milliseconds";
                            description
                                "Total collection time in milliseconds of all
                                 samples of a telemetry data source.";
                        }

                        leaf min-collection-time {
                            type uint32;
                            units "milliseconds";
                            description
                                "Minimum collection time in milliseconds of single
                                 sample of a telemetry data source.";
                        }

                        leaf avg-collection-time {
                            type uint32;
                            units "milliseconds";
                            description
                                "Average collection time in milliseconds of single
                                 sample of a telemetry data source.";
                        }

                        leaf max-collection-time {
                            type uint32;
                            units "milliseconds";
                            description
                                "Maximum collection time in milliseconds of single
                                 sample of a telemetry data source.";
                        }

                    } // list path

                    list scale-path {
                        key "scale-path";
                        description "List of scale-paths related to subscribed path.";

                        leaf scale-path {
                            type string {
                                length "1..4096";
                            }
                            description "Path to the scale telemetry section of operational state of interest";
                        }

                        leaf mode {
                            type enumeration {
                                enum "once"                         { value 0; }
                                enum "on-change"                    { value 1; }
                                enum "sample"                       { value 2; }
                            }
                            description
                                "Subscription path mode, indicating how the
                                 SROS must return values in a subscription.

                                 Value 'once' indicates that subscription is
                                 short-lived and stream single sample of all paths
                                 and is terminated afterwards.

                                 Value 'on-change' indicates that the SROS sends
                                 an update on leaf value change.

                                 Value 'sample' indicates that the SROS samples
                                 values according to the interval.";
                        }

                        leaf sample-interval {
                            type uint64;
                            units "milliseconds";
                            description
                                "Time in milliseconds between the device's sample of a
                                 telemetry data source.";
                        }

                        leaf finished-collection-count {
                            type uint64;
                            description
                                "Finished count of collection sample of a telemetry
                                 data source.";
                        }

                        leaf deferred-collection-count {
                            type uint64;
                            description
                                "Deferred count of collection sample of a telemetry
                                 data source.";
                        }

                        leaf total-collection-time {
                            type uint64;
                            units "milliseconds";
                            description
                                "Total collection time in milliseconds of all
                                 samples of a telemetry data source.";
                        }

                        leaf min-collection-time {
                            type uint32;
                            units "milliseconds";
                            description
                                "Minimum collection time in milliseconds of single
                                 sample of a telemetry data source.";
                        }

                        leaf avg-collection-time {
                            type uint32;
                            units "milliseconds";
                            description
                                "Average collection time in milliseconds of single
                                 sample of a telemetry data source.";
                        }

                        leaf max-collection-time {
                            type uint32;
                            units "milliseconds";
                            description
                                "Maximum collection time in milliseconds of single
                                 sample of a telemetry data source.";
                        }

                    } // list scale-path

                } // list subscription

            } // container grpc

        } // container telemetry

    } // grouping state-system-telemetry

}
