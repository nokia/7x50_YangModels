module nokia-sr-openconfig-rsvp-sr-ext-deviations {

    namespace "urn:nokia.com:sros:ns:yang:sr:openconfig_rsvp_sr_ext_deviations";

    prefix "nokia-sr-oc-sr-rsvp-ext-devs";

    import nokia-sros-yang-extensions     { prefix "sros-ext"; }
    import openconfig-extensions          { prefix "ocext"; }
    import openconfig-mpls                { prefix "oc-mpls"; }
    import openconfig-network-instance    { prefix "oc-netinst"; }
    import openconfig-rsvp-sr-ext         { prefix "oc-sr-rsvp-ext"; }
    import openconfig-types               { prefix "oc-types"; }

    sros-ext:sros-major-release "rel19";

    organization "Nokia";

    contact
        "Nokia SR OS Support
         Web: <http://www.nokia.com>";

    description
        "This module contains the list of deviations against the openconfig-rsvp-sr-ext
          module for the Nokia SR OS based routers.

         Copyright 2016 Nokia. All rights reserved. Reproduction of this document
         is authorized on the condition that the foregoing copyright notice is included.

         This nokia-sr-openconfig-rsvp-sr-ext-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2017-03-06";

    deviation /oc-netinst:network-instances/oc-netinst:network-instance/oc-netinst:mpls/oc-netinst:te-global-attributes/oc-sr-rsvp-ext:bandwidth-measurement/oc-sr-rsvp-ext:config/oc-sr-rsvp-ext:collection-interval {
        deviate replace {
            type uint32 {
                range 10..600;
            }
        }
        deviate add {
            default 30;
        }
    }

    deviation /oc-netinst:network-instances/oc-netinst:network-instance/oc-netinst:mpls/oc-netinst:te-global-attributes/oc-sr-rsvp-ext:bandwidth-measurement/oc-sr-rsvp-ext:config/oc-sr-rsvp-ext:adjustment-interval {
        deviate add {
            default 90;
        }
    }

    deviation /oc-netinst:network-instances/oc-netinst:network-instance/oc-netinst:mpls/oc-netinst:te-global-attributes/oc-sr-rsvp-ext:bandwidth-measurement/oc-sr-rsvp-ext:config/oc-sr-rsvp-ext:bandwidth-multiplier {
        deviate replace {
            type decimal64 {
                fraction-digits 4;
                range 0.0000..1000.0000;
            }
        }
        deviate replace {
            default 100.0000;
        }
    }

    deviation /oc-netinst:network-instances/oc-netinst:network-instance/oc-netinst:mpls/oc-netinst:te-global-attributes/oc-sr-rsvp-ext:bandwidth-measurement/oc-sr-rsvp-ext:state/oc-sr-rsvp-ext:collection-interval {
        deviate replace {
            type uint32 {
                range 10..600;
            }
        }
        deviate add {
            default 30;
        }
    }

    deviation /oc-netinst:network-instances/oc-netinst:network-instance/oc-netinst:mpls/oc-netinst:te-global-attributes/oc-sr-rsvp-ext:bandwidth-measurement/oc-sr-rsvp-ext:state/oc-sr-rsvp-ext:adjustment-interval {
        deviate add {
            default 90;
        }
    }

    deviation /oc-netinst:network-instances/oc-netinst:network-instance/oc-netinst:mpls/oc-netinst:te-global-attributes/oc-sr-rsvp-ext:bandwidth-measurement/oc-sr-rsvp-ext:state/oc-sr-rsvp-ext:bandwidth-multiplier {
        deviate replace {
            type decimal64 {
                fraction-digits 4;
                range 0.0000..1000.0000;
            }
        }
        deviate replace {
            default 100.0000;
        }
    }

    deviation /oc-netinst:network-instances/oc-netinst:network-instance/oc-netinst:mpls/oc-netinst:te-global-attributes/oc-sr-rsvp-ext:bandwidth-measurement/oc-sr-rsvp-ext:state/oc-sr-rsvp-ext:effective-adjustment-interval {
        deviate not-supported;
    }

    deviation /oc-netinst:network-instances/oc-netinst:network-instance/oc-netinst:mpls/oc-netinst:te-global-attributes/oc-sr-rsvp-ext:bandwidth-measurement/oc-sr-rsvp-ext:update-trigger/oc-sr-rsvp-ext:config/oc-sr-rsvp-ext:update-trigger {
        deviate not-supported;
    }

    deviation /oc-netinst:network-instances/oc-netinst:network-instance/oc-netinst:mpls/oc-netinst:te-global-attributes/oc-sr-rsvp-ext:bandwidth-measurement/oc-sr-rsvp-ext:update-trigger/oc-sr-rsvp-ext:config/oc-sr-rsvp-ext:sr-traffic-pct {
        deviate not-supported;
    }

    deviation /oc-netinst:network-instances/oc-netinst:network-instance/oc-netinst:mpls/oc-netinst:te-global-attributes/oc-sr-rsvp-ext:bandwidth-measurement/oc-sr-rsvp-ext:update-trigger/oc-sr-rsvp-ext:state/oc-sr-rsvp-ext:update-trigger {
        deviate not-supported;
    }

    deviation /oc-netinst:network-instances/oc-netinst:network-instance/oc-netinst:mpls/oc-netinst:te-global-attributes/oc-sr-rsvp-ext:bandwidth-measurement/oc-sr-rsvp-ext:update-trigger/oc-sr-rsvp-ext:state/oc-sr-rsvp-ext:sr-traffic-pct {
        deviate not-supported;
    }

    deviation /oc-netinst:network-instances/oc-netinst:network-instance/oc-netinst:mpls/oc-netinst:signaling-protocols/oc-netinst:rsvp-te/oc-netinst:interface-attributes/oc-netinst:interface/oc-netinst:subscription/oc-netinst:state/oc-sr-rsvp-ext:adjusted-absolute-subscription-bw {
        deviate replace {
            units kilobps;
        }
    }

    deviation /oc-netinst:network-instances/oc-netinst:network-instance/oc-netinst:mpls/oc-netinst:te-interface-attributes/oc-netinst:interface/oc-sr-rsvp-ext:bandwidth-measurement/oc-sr-rsvp-ext:state/oc-sr-rsvp-ext:last-sample-measured-rsvp-util {
        deviate not-supported;
    }

    deviation /oc-netinst:network-instances/oc-netinst:network-instance/oc-netinst:mpls/oc-netinst:te-interface-attributes/oc-netinst:interface/oc-sr-rsvp-ext:bandwidth-measurement/oc-sr-rsvp-ext:state/oc-sr-rsvp-ext:last-sample-measured-sr-util {
        deviate replace {
            units kilobps;
        }
    }

}
