module nokia-sr-openconfig-acl-deviations {

    namespace "urn:nokia.com:sros:ns:yang:sr:openconfig_acl_deviations";

    prefix "nokia-sr-oc-acl-devs";

    import nokia-sros-yang-extensions     { prefix "sros-ext"; }
    import openconfig-acl                 { prefix "oc-acl"; }
    import openconfig-extensions          { prefix "ocext"; }
    import openconfig-interfaces          { prefix "oc-if"; }
    import openconfig-packet-match        { prefix "oc-pkt-match"; }
    import openconfig-packet-match-types  { prefix "oc-pkt-match-types"; }
    import openconfig-yang-types          { prefix "oc-yang"; }

    sros-ext:sros-major-release "rel19";

    organization "Nokia";

    contact
        "Nokia SR OS Support
         Web: <http://www.nokia.com>";

    description
        "This module contains the list of deviations against the openconfig-acl
          module for the Nokia SR OS based routers.

         Copyright 2016 Nokia. All rights reserved. Reproduction of this document
         is authorized on the condition that the foregoing copyright notice is included.

         This nokia-sr-openconfig-acl-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2017-05-26";

    deviation /oc-acl:acl {
        deviate not-supported;
    }

}
