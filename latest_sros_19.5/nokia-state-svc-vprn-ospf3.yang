submodule nokia-state-svc-vprn-ospf3 {

    yang-version "1.1";

    belongs-to nokia-state { prefix "state"; }

    import ietf-inet-types                { prefix "inet"; }
    import ietf-yang-types                { prefix "yang"; }
    import nokia-sros-yang-extensions     { prefix "sros-ext"; }
    import nokia-types-ospf               { prefix "types-ospf"; }
    import nokia-types-router             { prefix "types-router"; }
    import nokia-types-sros               { prefix "types-sros"; }

    include nokia-state-router;
    include nokia-state-router-ospf;

    sros-ext:sros-major-release "rel19";

    organization "Nokia";

    contact
        "Nokia SR OS Support
         Web: <http://www.nokia.com>";

    description
        "Nokia YANG Data model with operational state for vprn ospf3 protocol attributes on SR OS based routers.

         Copyright 2016 Nokia. All rights reserved. Reproduction of this document
         is authorized on the condition that the foregoing copyright notice is included.

         This nokia-state-svc-vprn-ospf3 YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-03-18";

    grouping state-svc-vprn-ospf3 {
        list ospf3 {
            key "ospf-instance";
            description "Enter the ospf3 context";

            leaf ospf-instance {
                type uint32 {
                    range "0..31|64..95";
                }
                description "Specifies the value of the integrated OSPF instance.";
            }

            leaf oper-state {
                type enumeration {
                    enum "enabled"                      { value 1; }
                    enum "disabled"                     { value 2; }
                }
                description
                    "the value of oper-state indicates the current operating state of this
                     instance of OSPF in this router.";
            }

            leaf last-disabled-reason {
                type string {
                    length "0..20";
                }
                description "Reason why the disabled state was entered the last time.";
            }

            leaf oper-router-id {
                type types-sros:ipv4-address;
                description
                    "the value of oper-router-id indicates the 32-bit integer used to uniquely
                     identify the router in the autonomous system. the default OSPF instance
                     will use the value specified by router-id or the one derived from the
                     IP layer. For the non-default instances of OSPF, this is the same value as
                     router-id, which must be specified before the OSPF instance can become
                     operational.";
            }

            leaf area-border-router {
                type boolean;
                description "This indicates whether this router is an area border router.";
            }

            leaf as-border-router {
                type boolean;
                description "This indicates whether this router is an AS border router.";
            }

            leaf backbone-router {
                type boolean;
                description "This indicates whether or not this router is configured as an OSPF back bone router.";
            }

            leaf overload-state {
                type enumeration {
                    enum "overload"                     { value 1; }
                    enum "no-overload"                  { value 2; }
                }
                description "the value of overload-oper-state indicates whether or not the OSPF application is presently in overload state or not.";
            }

            leaf overload-rem-interval {
                type int32 {
                    range "0..65535";
                }
                description "the value of overload-rem-interval indicates the time for which the system will be in overload state if OSPF is in overload state. the value of 0 implies that the system is indefinitely in overload state.";
            }

            leaf last-overload-entered-time {
                type yang:date-and-time;
                description "the value of last-overload-entrd-time indicates the time at which the system last went into overload state.";
            }

            leaf last-overload-exit-time {
                type yang:date-and-time;
                description "the value of last-overload-exit-time indicates the time at which the system last came out of overload state.";
            }

            leaf last-overload-enter-code {
                type enumeration {
                    enum "none"                         { value 1; }
                    enum "spf-failed"                   { value 2; }
                    enum "boot-overload"                { value 3; }
                    enum "manual-overload"              { value 4; }
                    enum "sfm-overload"                 { value 5; }
                    enum "fib-add-fail"                 { value 6; }
                    enum "rtm-add-fail"                 { value 7; }
                    enum "rtr-adv-lsa-limit"            { value 8; }
                }
                description "the value of last-overload-enter-code indicates the condition which caused OSPF to get into overload.";
            }

            leaf last-overload-exit-code {
                type enumeration {
                    enum "none"                         { value 1; }
                    enum "bgp-sig-recv"                 { value 2; }
                    enum "timer-expired"                { value 3; }
                    enum "manual-exit"                  { value 4; }
                    enum "sfm-overload-done"            { value 5; }
                }
                description "the value of last-overload-exit-code indicates the reason why OSPF came out of overload state the last time, since reset.";
            }

            leaf overflow {
                type boolean;
                description
                    "The value of in-overflow-state indicates the current overflow state (true/false).
                     This overflow state occurs when the number of non-default AS-external-LS-as
                     entries exceed the link-state database capability.";
            }

            leaf last-overflow-entered-time {
                type yang:date-and-time;
                description "The value of last-ovrflw-entered-time indicates the value of sys-up-time the last time we entered overflow state. this overflow state occurs when the number of non-default AS-external-LS-as entries exceed the link-state database capability.";
            }

            leaf last-overflow-exit-time {
                type yang:date-and-time;
                description "the value of last-overflow-exit-time indicates the value of sys-up-time the last time we exited overflow state. this overflow state occurs when the number of non-default AS-external-LS-as entries exceed the link-state database capability.";
            }

            leaf stub-router-support {
                type boolean;
                description "the value of stub-router-support indicates the router's support for stub router functionality.";
            }

            leaf opaque-lsa-support {
                type boolean;
                description "the value of opaque-lsa-support indicates the router's support for opaque LSA types. this object is valid only when version is 'version2'.";
            }

            leaf last-enabled-time {
                type yang:date-and-time;
                description "the value of last-enabled-time indicates the value of sys-up-time when admin-state was last set to 'enabled'. when admin-state is set to 'disabled', the OSPF counters are stopped when admin-state is reset to 'enabled', the counters are reset to zero.";
            }

            leaf routes-submitted {
                type yang:gauge32;
                description "the value of routes-submitted indicates the number of routes submitted to the route table manager (RTM) by this instance of OSPF.";
            }

            leaf total-exported-routes {
                type yang:gauge32;
                description "the value of total-exported-routes indicates the total number of routes exported into OSPF from the route table manager when an export policy is configured. value of total-exported-routes would be 0 when no export policy is configured.";
            }

            leaf ovld-lsa-limit-rem-interval {
                type int32 {
                    range "0..65535";
                }
                description "the value of ovld-lsa-limit-rem-interval indicates the remaining time in seconds for which the system will be in overload state due to advertising router LSA limit exceeded. the value of 0 implies that the system is either not in overload or indefinitely in overload state.";
            }

            leaf db-asn {
                type inet:as-number;
                description "the value of the object db-asn indicates the autonomous system number the IGP is using during its database export. the value from TIMETRA-VRTR-MIB::v-rtr-AS4byte at the moment database-export is enabled is used as AS number. the used AS number gets updated when the value from admin-state changes from disabled (2) to enabled (1) or when the value from database-export changes from disabled(2) to enabled(1).";
            }

            container spf {
                description "SPF related information";

                leaf max-spf-run-interval {
                    type int32 {
                        range "0..2147483647";
                    }
                    description "the value of max-spf-run-interval indicates the maximum time, in hundredths of seconds, used to perform a total SPF calculation.";
                }

                leaf min-spf-run-interval {
                    type int32 {
                        range "0..2147483647";
                    }
                    description "the value of min-spf-run-interval indicates the minimum time, in hundredths of seconds, used to perform a total SPF calculation.";
                }

                leaf avg-spf-run-interval {
                    type int32 {
                        range "0..2147483647";
                    }
                    description "the value of avg-spf-run-interval indicates the average time, in hundredths of seconds, of all the total SPF calculations performed by this OSPF router.";
                }

                leaf max-rtm-update-interval {
                    type int32 {
                        range "0..2147483647";
                    }
                    description "the value of max-rtm-update-time indicates the maximum time, in hundredths of seconds, used to update RTM.";
                }

                leaf min-rtm-update-interval {
                    type int32 {
                        range "0..2147483647";
                    }
                    description "the value of min-rtm-update-time indicates the minimum time, in hundredths of seconds, used to update RTM.";
                }

                leaf avg-rtm-update-interval {
                    type int32 {
                        range "0..2147483647";
                    }
                    description "the value of avg-rtm-update-time indicates the average time, in hundredths of seconds, used to update RTM.";
                }

                leaf max-lfa-spf-interval {
                    type int32 {
                        range "0..2147483647";
                    }
                    description "the value of max-lfa-spf-interval indicates the maximum time, in hundredths of seconds, used to run LFA SPF.";
                }

                leaf min-lfa-spf-interval {
                    type int32 {
                        range "0..2147483647";
                    }
                    description "the value of min-lfa-spf-interval indicates the minimum time, in hundredths of seconds, used to run LFA SPF.";
                }

                leaf avg-lfa-spf-interval {
                    type int32 {
                        range "0..2147483647";
                    }
                    description "the value of avg-lfa-spf-interval indicates the average time, in hundredths of seconds, used to run LFA SPF.";
                }

                container last-full-spf {
                    description "Information about the last full SPF run";

                    leaf run-time {
                        type yang:date-and-time;
                        description "the value of last-full-spf-run-time indicates the time at which the system last performed a full dijkstra (SPF) run.";
                    }

                    leaf total-time {
                        type int32 {
                            range "0..2147483647";
                        }
                        description "Time it toook, in hundredths of seconds, to complete the last SPF run completely.";
                    }

                    leaf intra-spf-time {
                        type int32 {
                            range "0..2147483647";
                        }
                        description "Time it toook, in hundredths of seconds, to complete the intra-area SPF calculations.";
                    }

                    leaf inter-spf-time {
                        type int32 {
                            range "0..2147483647";
                        }
                        description "Time it toook, in hundredths of seconds, to complete the inter-area SPF calculations.";
                    }

                    leaf extern-spf-time {
                        type int32 {
                            range "0..2147483647";
                        }
                        description "Time it toook, in hundredths of seconds, to complete the external LSA calculations.";
                    }

                    leaf rtm-update-time {
                        type int32 {
                            range "0..2147483647";
                        }
                        description "Time it toook, in hundredths of seconds, to complete the RTM updates.";
                    }

                } // container last-full-spf

                container last-ext-spf {
                    description "Information about the last external SPF run";

                    leaf run-time {
                        type yang:date-and-time;
                        description "the value of last-ext-spf-run-time indicates the value of sys-up-time when the external OSPF dijkstra (SPF) was last run.";
                    }

                    leaf interval {
                        type int32 {
                            range "0..2147483647";
                        }
                        description "the value of ext-spf-run-interval indicates the time, in hundredths of seconds, used to perform the most recent total external (not incremental) SPF calculation.";
                    }

                } // container last-ext-spf

                container last-lfa-spf {
                    description "Information about the last LFA SPF run";

                    leaf run-time {
                        type yang:date-and-time;
                        description "the value of last-lfa-spf-run-time indicates the time at which the system last performed a dijkstra (LFA SPF) run.";
                    }

                    leaf interval {
                        type int32 {
                            range "0..2147483647";
                        }
                        description "the time, in hundredths of seconds, used to perform the last LFA SPF calculation.";
                    }

                } // container last-lfa-spf

            } // container spf

            container statistics {
                description "Holds statistics for an instance of OSPF protocol.";

                leaf num-times-in-overload {
                    type yang:counter32;
                    description "The count of the number of times the system was overloaded.";
                }

                leaf num-times-in-overflow {
                    type yang:counter32;
                    description "The count of the number of times the system was in the overflow state.";
                }

                leaf neighbor-count {
                    type yang:gauge32;
                    description "The number of OSPF neighbors.";
                }

                leaf virt-nbr-count {
                    type yang:gauge32;
                    description "The number of OSPF virtual link neighbors.";
                }

                container spf {
                    description "SPF related statistics.";

                    leaf full-spf-runs {
                        type yang:counter32;
                        description "The total number of times that complete SPF has been run on the router since OSPF was last enabled.";
                    }

                    leaf ext-spf-runs {
                        type yang:counter32;
                        description "The total number of times that only the external portion of the SPF has been run since OSPF was last enabled.";
                    }

                    leaf incremental-inter-spf-runs {
                        type yang:counter32;
                        description "The total number of incremental SPF runs triggered by new or updated inter-area prefix or inter-area router LS-as.";
                    }

                    leaf incremental-ext-spf-runs {
                        type yang:counter32;
                        description "The total number of incremental SPF runs triggered by new or updated external LS-as.";
                    }

                    leaf spf-attempts-failed {
                        type yang:counter32;
                        description "The number of times an attempt to run SPF has failed because SPF runs have been stopped as a result of insufficient memory resources.";
                    }

                    leaf route-adds-failed {
                        type yang:counter32;
                        description "The number of times an attempt to add a route to the route table manager (RTM) failed for this OSPF instance.";
                    }

                    leaf route-dels-failed {
                        type yang:counter32;
                        description "The number of times an attempt to delete a route from the route table manager (RTM) failed for this instance of OSPF.";
                    }

                    leaf route-mods-failed {
                        type yang:counter32;
                        description "The number of times an attempt to modify a route in the route table manager (RTM) failed for this instance of OSPF.";
                    }

                    leaf lfa-spf-runs {
                        type yang:counter32;
                        description "The total number of times that complete LFA SPF has been run on the router since OSPF was last enabled.";
                    }

                    leaf rlfa-runs {
                        type yang:counter32;
                        description "The number of times remote-loopfree-alternate calculations have been made.";
                    }

                    leaf tilfa-runs {
                        type yang:counter32;
                        description "The number of times remote-loopfree-alternate calculations have been made.";
                    }

                    leaf cspf-requests {
                        type yang:counter32;
                        description "The number of cspf requests made to the OSPF protocol.";
                    }

                    leaf cspf-dropped-requests {
                        type yang:counter32;
                        description "The number of dropped cspf requests made by the OSPF protocol.";
                    }

                    leaf cspf-paths-found {
                        type yang:counter32;
                        description "The number of of paths found for the requests made to OSPF protocol.";
                    }

                    leaf cspf-paths-not-found {
                        type yang:counter32;
                        description "The number of of paths not found for the requests made to OSPF protocol.";
                    }

                } // container spf

                container lsdb {
                    description "Link state database related statistics.";

                    leaf new-lsas-originated {
                        type yang:counter32;
                        description "The number of new link-state advertisements that have been originated. This number is incremented each time the router originates a new LSA.";
                    }

                    leaf new-lsas-received {
                        type yang:counter32;
                        description "The number of link-state advertisements received determined to be new instantiations. This number does not include newer instantiations of self-originated link-state advertisements.";
                    }

                    leaf as-scope-lsa-count {
                        type yang:gauge32;
                        description "the value of as-scope-lsa-count indicates the number of AS-scope (e.g. AS-external) link state advertisements in the link-state database.";
                    }

                    leaf as-scope-lsa-cksum-sum {
                        type int32;
                        description "the value of as-scope-lsa-cksum-sum indicates the 32-bit unsigned sum of the LS checksums of the AS-scoped link-state advertisements contained in the link-state database. this sum can be used to determine if there has been a change in a router's link-state database, and to compare the link-state database of two routers.";
                    }

                    leaf as-scope-unk-lsa-count {
                        type yang:gauge32;
                        description "the value of as-scope-unk-lsa-count indicates the number of unknown AS-scope (e.g. AS-external) link-state advertisements in the link-state database.";
                    }

                    leaf as-scope-unk-lsa-cksum-sum {
                        type int32;
                        description "the value of as-scope-unk-lsa-cksum-sum indicates the 32-bit unsigned sum of the LS checksums of the unknown AS-scoped link-state advertisements contained in the link-state database. this sum can be used to determine if there has been a change in a router's link-state database, and to compare the link-state database of two routers.";
                    }

                    leaf extern-lsa-count {
                        type yang:gauge32;
                        description "the value of extern-lsa-count indicates the number of external LS-as (LS type 0x4005) in the link-state database";
                    }

                    leaf extern-lsa-cksum-sum {
                        type int32;
                        description "the value of extern-lsa-cksum-sum indicates the 32-bit unsigned sum of the LS checksums of the external link-state advertisements contained in the link-state database. this sum can be used to determine if there has been a change in a router's link state database, and to compare the link-state database of two routers.";
                    }

                    leaf as-lsdb-entries {
                        type yang:gauge32;
                        description "The number of row entries in the as-lsdb-table.";
                    }

                    leaf area-lsdb-entries {
                        type yang:gauge32;
                        description "The number of row entries in the area-lsdb-table.";
                    }

                    leaf link-lsdb-entries {
                        type yang:gauge32;
                        description "The number of row entries in the ng-link-lsdb-table.";
                    }

                } // container lsdb

                container sid {
                    description "SID related statistics";

                    leaf srgb-errors {
                        type yang:counter32;
                        description "The total number of errors for SI-ds that are not within the label-range of the router.";
                    }

                    leaf duplicated-errors {
                        type yang:counter32;
                        description "The total number of errors for SI-ds which are already assigned to another prefix.";
                    }

                } // container sid

                container packets {
                    description "Packet counters";

                    leaf tx-total {
                        type yang:counter32;
                        description "The total number of OSPF packets transmitted since admin-state was last set to 'enabled'.";
                    }

                    leaf tx-hello {
                        type yang:counter32;
                        description "The total number of OSPF hello packets transmitted since admin-state was last set to 'enabled'.";
                    }

                    leaf tx-db-description {
                        type yang:counter32;
                        description "The total number of OSPF database description packets transmitted since admin-state was last set to 'enabled'.";
                    }

                    leaf tx-ls-request {
                        type yang:counter32;
                        description "The total number of OSPF link state requests (LS-rs)transmitted since admin-state was last set to 'enabled'.";
                    }

                    leaf tx-ls-update {
                        type yang:counter32;
                        description "The total number of OSPF link state updates (LS-us) transmitted since admin-state was last set to 'enabled'.";
                    }

                    leaf tx-ls-ack {
                        type yang:counter32;
                        description "The total number of OSPF link state acknowledgements transmitted since admin-state was last set to 'enabled'.";
                    }

                    leaf rx-total {
                        type yang:counter32;
                        description "The total number of OSPF packets received since admin-state was last set to 'enabled'.";
                    }

                    leaf rx-hello {
                        type yang:counter32;
                        description "The total number of OSPF hello packets received since admin-state was last set to 'enabled'.";
                    }

                    leaf rx-db-description {
                        type yang:counter32;
                        description "The total number of OSPF database description packets received since admin-state was last set to 'enabled'.";
                    }

                    leaf rx-ls-request {
                        type yang:counter32;
                        description "The total number of link state requests (LS-rs) received since admin-state was last set to 'enabled'.";
                    }

                    leaf rx-ls-update {
                        type yang:counter32;
                        description "The total number of link state updates (LS-us) received since admin-state was last set to 'enabled'.";
                    }

                    leaf rx-ls-ack {
                        type yang:counter32;
                        description "The total number of link state acknowledgements received since admin-state was last set to 'enabled'.";
                    }

                    leaf discarded {
                        type yang:counter32;
                        description "The total number of OSPF packets discarded since admin-state was last set to 'enabled'.";
                    }

                    leaf retransmits {
                        type yang:counter32;
                        description "The total number of OSPF retransmits since admin-state was last set to 'enabled'.";
                    }

                    leaf bad-version {
                        type yang:counter32;
                        description "The total number of OSPF packets received with bad OSPF version numbers since admin-state was last set to 'enabled'.";
                    }

                    leaf bad-network {
                        type yang:counter32;
                        description "The total number of OSPF packets received with invalid network or mask since admin-state was last set to 'enabled'.";
                    }

                    leaf bad-area {
                        type yang:counter32;
                        description "The total number of OSPF packets received with an area mismatch since admin-state was last set to 'enabled'.";
                    }

                    leaf bad-dest-address {
                        type yang:counter32;
                        description "The total number of OSPF packets received with the incorrect IP destination address since admin-state was last set to 'enabled'.";
                    }

                    leaf bad-neighbors {
                        type yang:counter32;
                        description "The total number of OSPF packets received where the neighbor information does not match the information this router has for the neighbor since admin-state was last set to 'enabled'.";
                    }

                    leaf bad-packet-type {
                        type yang:counter32;
                        description "The total number of OSPF packets received with an invalid OSPF packet type since admin-state was last set to 'enabled'.";
                    }

                    leaf bad-length {
                        type yang:counter32;
                        description "The total number of OSPF packets received with a total length not equal to the length given in the packet itself since admin-state was last set to 'enabled'.";
                    }

                    leaf bad-hello-interval {
                        type yang:counter32;
                        description "the value of bad-hello-intervals indicates the total number of OSPF packets received where the hello interval given in packet was not equal to that configured on this interface since admin-state was last set to 'enabled'.";
                    }

                    leaf bad-dead-interval {
                        type yang:counter32;
                        description "The total number of OSPF packets received where the dead interval given in the packet was not equal to that configured on this interface since admin-state was last set to 'enabled'.";
                    }

                    leaf bad-options {
                        type yang:counter32;
                        description "The total number of OSPF packets received with an option that does not match those configured for this interface or area since admin-state was last set to 'enabled'.";
                    }

                    leaf rx-bad-checksum {
                        type yang:counter32;
                        description "The count of LS-as received with bad checksums.";
                    }

                    leaf bad-auth-type {
                        type yang:counter32;
                        description "The total number of OSPF packets received with an invalid authorization type since admin-state was last set to 'enabled'.";
                    }

                    leaf auth-failures {
                        type yang:counter32;
                        description "The total number of OSPF packets received with an invalid authorization key since admin-state was last set to 'enabled'.";
                    }

                    leaf bad-virtual-link {
                        type yang:counter32;
                        description "The total number of OSPF packets received that are destined to a virtual link that does not exist since admin-state was last set to 'enabled'.";
                    }

                } // container packets

            } // container statistics

            list area {
                key "area-id";
                description "Enter the area context";

                leaf area-id {
                    type types-sros:ipv4-address;
                    description "Attribute area-id";
                }

                leaf area-bdr-rtr-count {
                    type yang:gauge32;
                    description "The total number of area border routers reachable within this area.";
                }

                leaf as-bdr-rtr-count {
                    type yang:gauge32;
                    description "The total number of autonomous system border routers reachable within this area.";
                }

                leaf active-interfaces {
                    type uint32;
                    description "The number of active interfaces in this area.";
                }

                leaf interface-count {
                    type uint32;
                    description "The number of interfaces configured in this area.";
                }

                leaf virtual-link-count {
                    type uint32;
                    description "The total number of virtual links configured through this area.";
                }

                leaf neighbor-count {
                    type yang:gauge32;
                    description "The number of active neighbors in this area.";
                }

                leaf last-spf-run-time {
                    type yang:date-and-time;
                    description "The sys-up-time when intra-area SPF was last run on this area.";
                }

                leaf spf-runs {
                    type yang:counter32;
                    description "The number of times that the intra-area route table has been calculated using this area's link-state database.";
                }

                leaf nssa-translator-state {
                    type enumeration {
                        enum "enabled"                      { value 1; }
                        enum "elected"                      { value 2; }
                        enum "disabled"                     { value 3; }
                    }
                    description "The current NSSA translator state";
                }

                leaf nssa-translator-events {
                    type yang:counter32;
                    description "The number of translator state changes that have occurred since the last boot-up.";
                }

                container lsa-totals {
                    description "The number of LSAs of each type in this area's database";

                    leaf router-lsa {
                        type yang:gauge32;
                        description "The number of router LSAs in this area's link-state database.";
                    }

                    leaf e-router-lsa {
                        type yang:gauge32;
                        description "The number of OSPFv3 E-router LSAs in this area's link-state database.";
                    }

                    leaf network-lsa {
                        type yang:gauge32;
                        description "The number of network LSAs in this area's link-state database.";
                    }

                    leaf e-network-lsa {
                        type yang:gauge32;
                        description "The number of OSPFv3 E-network LSAs in this area's link-state database.";
                    }

                    leaf nssa-lsa {
                        type yang:gauge32;
                        description "The number of NSSA LSAs in this area's link-state database.";
                    }

                    leaf e-nssa-lsa {
                        type yang:gauge32;
                        description "The number of OSPFv3 E-NSSA LSAs in this area's link-state database.";
                    }

                    leaf inter-area-prefix-lsa {
                        type yang:gauge32;
                        description "The number of OSPFv3 inter-area-prefix LSAs in this area's link-state database.";
                    }

                    leaf e-inter-area-prefix-lsa {
                        type yang:gauge32;
                        description "The number of OSPFv3 E-inter-area-prefix LSAs in this area's link-state database.";
                    }

                    leaf inter-area-router-lsa {
                        type yang:gauge32;
                        description "The number of OSPFv3 inter-area-router LSAs in this area's link-state database.";
                    }

                    leaf e-inter-area-router-lsa {
                        type yang:gauge32;
                        description "The number of OSPFv3 E-inter-area-router LSAs in this area's link-state database.";
                    }

                    leaf intra-area-prefix-lsa {
                        type yang:gauge32;
                        description "The number of OSPFv3 intra-area-prefix LSAs in this area's link-state database.";
                    }

                    leaf e-intra-area-prefix-lsa {
                        type yang:gauge32;
                        description "The number of OSPFv3 E-intra-area-prefix LSAs in this area's link-state database.";
                    }

                    leaf router-info-lsa {
                        type yang:gauge32;
                        description "The number of OSPFv3 router-info LSAs in this area's link-state database.";
                    }

                    leaf unknown-lsa {
                        type yang:gauge32;
                        description "The number of unknown LSA advertisements in this area's link-state database.";
                    }

                    leaf total {
                        type yang:gauge32;
                        description "The number of area scope LSAs within this area.";
                    }

                    leaf total-lsa-cksum-sum {
                        type int32;
                        description "The 32-bit unsigned sum of the area scope LSA checksums contained in this area's link-state database. The sum can be used to determine if there has been a change in a router's link-state database, and to compare the link-state database of two routers.";
                    }

                } // container lsa-totals

                container lsa-filter-totals {
                    description "The number of LSAs not sent due to area policy.";

                    leaf export-filtered {
                        type yang:gauge32;
                        description "The number of LSAs not sent due to area export policy.";
                    }

                    leaf import-filtered {
                        type yang:gauge32;
                        description "The number of LSAs not sent due to area import policy.";
                    }

                } // container lsa-filter-totals

                list interface {
                    key "interface-name";
                    description "Enter the interface context";

                    leaf interface-name {
                        type types-sros:interface-name;
                        description "Router interface name.";
                    }

                    leaf type {
                        type enumeration {
                            enum "broadcast"                    { value 1; }
                            enum "non-broadcast"                { value 2; }
                            enum "point-to-point"               { value 3; }
                            enum "secondary"                    { value 6; }
                        }
                        description "the value of type indicates the operational OSPF interface type.";
                    }

                    leaf oper-state {
                        type enumeration {
                            enum "down"                         { value 1; }
                            enum "loopback"                     { value 2; }
                            enum "waiting"                      { value 3; }
                            enum "point-to-point"               { value 4; }
                            enum "designated-router"            { value 5; }
                            enum "backup-designated-router"     { value 6; }
                            enum "other-designated-router"      { value 7; }
                        }
                        description "the OSPF interface state.";
                    }

                    leaf last-enabled-time {
                        type yang:date-and-time;
                        description "the value of last-enabled-time indicates the sys-up-time value when ospf-if-admin-stat was last set to enabled (1) to run the ospf on this interface.";
                    }

                    leaf oper-mtu {
                        type int32;
                        description "the value of oper-MTU indicates the operational size of the largest packet which can be sent/received on this OSPF interface, specified in octets. this size DOES include the underlying IP header length, but not the underlying layer headers/trailers.";
                    }

                    leaf oper-metric {
                        type int32 {
                            range "0..65535";
                        }
                        description "the value of metric-value indicates the metric value this interface is using. the default value of the metric is (reference bandwidth / if-speed). the value of the reference bandwidth is configured by the reference-bandwidth object.";
                    }

                    leaf neighbor-count {
                        type yang:gauge32;
                        description "The total number of OSPF neighbors adjacent on this interface, in a state of INIT or greater, since admin-state was last set to 'enabled'.";
                    }

                    leaf dr-id {
                        type types-sros:ipv4-address;
                        description "the value of DR-id indicates the router ID of the designated router.";
                    }

                    leaf dr-ip-address {
                        type types-sros:ip-address-with-zone;
                        description "the IP address of the designated router.";
                    }

                    leaf bdr-id {
                        type types-sros:ipv4-address;
                        description "the value of BDR-id indicates the router ID of the backup designated router.";
                    }

                    leaf bdr-ip-address {
                        type types-sros:ip-address-with-zone;
                        description "the IP address of the backup designated router.";
                    }

                    leaf link-lsa-count {
                        type yang:gauge32;
                        description "the value of link-lsa-count indicates the total number of link-scope link-state advertisements in this link's link-state database.";
                    }

                    leaf link-lsa-cksum-sum {
                        type int32;
                        description "the value of link-lsa-cksum-sum indicates the 32-bit unsigned sum of the link-scope link-state advertisements' LS checksums contained in this link's link-state database. the sum can be used to determine if there has been a change in a router's link-state database, and to compare the link state database of two routers.";
                    }

                    leaf local-ip-address {
                        type types-sros:ip-address-with-zone;
                        description "the value of local-ip-address indicates the IP address of this OSPF interface.";
                    }

                    leaf events {
                        type yang:counter32;
                        description "the value of events indicates the number of times this OSPF interface has changed its state, or an error has occurred.";
                    }

                    leaf last-event-time {
                        type yang:date-and-time;
                        description "the value of last-event-time indicates the value of sys-up-time when an event was last associated with this OSPF interface.";
                    }

                    container state-ipv6-authentication {
                        description "IPV6 authentication information";

                        leaf oper-inb-sa-name {
                            type types-sros:named-item-or-empty;
                            description "the value of oper-inb-sa-name indicates the name of the operational inbound manual I-psec security association, used for authenticating inbound ospfv3 traffic.";
                        }

                        leaf oper-inb-sa-name-temp {
                            type types-sros:named-item-or-empty;
                            description "the value of oper-inb-sa-name-temp indicates the name of a temporary operational inbound manual I-psec security association, used for authenticating inbound ospfv3 traffic. this field can only contain a value when the key-rollover mechanism is ongoing.";
                        }

                        leaf oper-outb-sa-name {
                            type types-sros:named-item-or-empty;
                            description "the value of oper-outb-sa-name indicates the name of the operational outbound manual I-psec security association, used for authenticating outbound ospfv3 traffic. when the key-rollover mechanism is ongoing, the value can temporarily be different from the value of the outbound-sa-name field.";
                        }

                    } // container state-ipv6-authentication

                    container packets {
                        description "Packet counters";

                        leaf tx-total {
                            type yang:counter32;
                            description "The total number of OSPF packets transmitted since admin-state was last set to 'enabled'.";
                        }

                        leaf tx-hello {
                            type yang:counter32;
                            description "The total number of OSPF hello packets transmitted since admin-state was last set to 'enabled'.";
                        }

                        leaf tx-db-description {
                            type yang:counter32;
                            description "The total number of OSPF database description packets transmitted since admin-state was last set to 'enabled'.";
                        }

                        leaf tx-ls-request {
                            type yang:counter32;
                            description "The total number of OSPF link state requests (LS-rs)transmitted since admin-state was last set to 'enabled'.";
                        }

                        leaf tx-ls-update {
                            type yang:counter32;
                            description "The total number of OSPF link state updates (LS-us) transmitted since admin-state was last set to 'enabled'.";
                        }

                        leaf tx-ls-ack {
                            type yang:counter32;
                            description "The total number of OSPF link state acknowledgements transmitted since admin-state was last set to 'enabled'.";
                        }

                        leaf rx-total {
                            type yang:counter32;
                            description "The total number of OSPF packets received since admin-state was last set to 'enabled'.";
                        }

                        leaf rx-hello {
                            type yang:counter32;
                            description "The total number of OSPF hello packets received since admin-state was last set to 'enabled'.";
                        }

                        leaf rx-db-description {
                            type yang:counter32;
                            description "The total number of OSPF database description packets received since admin-state was last set to 'enabled'.";
                        }

                        leaf rx-ls-request {
                            type yang:counter32;
                            description "The total number of link state requests (LS-rs) received since admin-state was last set to 'enabled'.";
                        }

                        leaf rx-ls-update {
                            type yang:counter32;
                            description "The total number of link state updates (LS-us) received since admin-state was last set to 'enabled'.";
                        }

                        leaf rx-ls-ack {
                            type yang:counter32;
                            description "The total number of link state acknowledgements received since admin-state was last set to 'enabled'.";
                        }

                        leaf discarded {
                            type yang:counter32;
                            description "The total number of OSPF packets discarded since admin-state was last set to 'enabled'.";
                        }

                        leaf retransmits {
                            type yang:counter32;
                            description "The total number of OSPF retransmits since admin-state was last set to 'enabled'.";
                        }

                        leaf bad-version {
                            type yang:counter32;
                            description "The total number of OSPF packets received with bad OSPF version numbers since admin-state was last set to 'enabled'.";
                        }

                        leaf bad-network {
                            type yang:counter32;
                            description "The total number of OSPF packets received with invalid network or mask since admin-state was last set to 'enabled'.";
                        }

                        leaf bad-area {
                            type yang:counter32;
                            description "The total number of OSPF packets received with an area mismatch since admin-state was last set to 'enabled'.";
                        }

                        leaf bad-dest-address {
                            type yang:counter32;
                            description "The total number of OSPF packets received with the incorrect IP destination address since admin-state was last set to 'enabled'.";
                        }

                        leaf bad-neighbors {
                            type yang:counter32;
                            description "The total number of OSPF packets received where the neighbor information does not match the information this router has for the neighbor since admin-state was last set to 'enabled'.";
                        }

                        leaf bad-packet-type {
                            type yang:counter32;
                            description "The total number of OSPF packets received with an invalid OSPF packet type since admin-state was last set to 'enabled'.";
                        }

                        leaf bad-length {
                            type yang:counter32;
                            description "The total number of OSPF packets received with a total length not equal to the length given in the packet itself since admin-state was last set to 'enabled'.";
                        }

                        leaf bad-hello-interval {
                            type yang:counter32;
                            description "the value of bad-hello-intervals indicates the total number of OSPF packets received where the hello interval given in packet was not equal to that configured on this interface since admin-state was last set to 'enabled'.";
                        }

                        leaf bad-dead-interval {
                            type yang:counter32;
                            description "The total number of OSPF packets received where the dead interval given in the packet was not equal to that configured on this interface since admin-state was last set to 'enabled'.";
                        }

                        leaf bad-options {
                            type yang:counter32;
                            description "The total number of OSPF packets received with an option that does not match those configured for this interface or area since admin-state was last set to 'enabled'.";
                        }

                        leaf rx-bad-checksum {
                            type yang:counter32;
                            description "The count of LS-as received with bad checksums.";
                        }

                        leaf bad-auth-type {
                            type yang:counter32;
                            description "The total number of OSPF packets received with an invalid authorization type since admin-state was last set to 'enabled'.";
                        }

                        leaf auth-failures {
                            type yang:counter32;
                            description "The total number of OSPF packets received with an invalid authorization key since admin-state was last set to 'enabled'.";
                        }

                        leaf bad-virtual-link {
                            type yang:counter32;
                            description "The total number of OSPF packets received that are destined to a virtual link that does not exist since admin-state was last set to 'enabled'.";
                        }

                    } // container packets

                    list neighbor {
                        key "address";
                        description "Enter the neighbor context";

                        leaf address {
                            type types-sros:ip-address;
                            description "Neighbor link local address";
                        }

                        leaf priority {
                            type int32 {
                                range "0..255";
                            }
                            description
                                "Specifies the priority of this neighbor in the designated router election algorithm.

                                 The value 0 signifies that the neighbor is not eligible to become
                                 the designated router on this particular network.";
                        }

                        leaf router-id {
                            type types-sros:ipv4-address;
                            description
                                "Indicates a 32-bit integer uniquely identifying the neighboring router in the Autonomous System.

                                 A value of 0 is returned until a Hello is received from the configured neighbor.";
                        }

                        leaf oper-state {
                            type types-ospf:neighbor-oper-state-type;
                            description "Indicates the State of the relationship with this Neighbor.";
                        }

                    } // list neighbor

                    list neighbor-state {
                        key "router-id";
                        description "State information of all neighbors, static and dynamic.";

                        leaf router-id {
                            type types-sros:ipv4-address;
                            description "Router ID of the neighbor.";
                        }

                        leaf address {
                            type types-sros:ip-address-with-zone;
                            description "the value of address indicates the IP address of the neighbor associated with the local link.";
                        }

                        leaf priority {
                            type int32 {
                                range "0..255";
                            }
                            description
                                "Specifies the priority of this neighbor in the designated router election algorithm.

                                 The value 0 signifies that the neighbor is not eligible to become
                                 the designated router on this particular network.";
                        }

                        leaf bfd-tracking {
                            type boolean;
                            description "the value of bfd-tracking indicates whether a BFD session is being maintained to track the forwarding path to this neighbor or not.";
                        }

                        leaf dr-id {
                            type types-sros:ipv4-address;
                            description "the value of dr-id indicates the DR value advertised in the HELLO packets received from the OSPF neighbor. if it is not a broadcast interface dr-id will be zero.";
                        }

                        leaf bdr-id {
                            type types-sros:ipv4-address;
                            description "the value of bdr-id indicates the BDR value advertised in the HELLO packets received from the OSPF neighbor. if it is not a broadcast interface bdr-id will be zero.";
                        }

                        leaf oper-state {
                            type enumeration {
                                enum "down"                         { value 1; }
                                enum "attempt"                      { value 2; }
                                enum "init"                         { value 3; }
                                enum "two-way"                      { value 4; }
                                enum "exchange-start"               { value 5; }
                                enum "exchange"                     { value 6; }
                                enum "loading"                      { value 7; }
                                enum "full"                         { value 8; }
                            }
                            description "Indicates the State of the relationship with this Neighbor.";
                        }

                        leaf options {
                            type int32;
                            description "the value of options indicates a bit mask corresponding to the neighbor's options field.";
                        }

                        leaf hello-suppressed {
                            type boolean;
                            description "the value of hello-suppressed indicates whether hellos are being suppressed to the neighbor.";
                        }

                        leaf if-id {
                            type int32 {
                                range "0..2147483647";
                            }
                            description "the value of if-id indicates the interface ID that the neighbor advertises in its hello packets on this link, that is, the neighbor's local interface index.";
                        }

                        leaf restart-helper-status {
                            type enumeration {
                                enum "not-helping"                  { value 1; }
                                enum "helping"                      { value 2; }
                            }
                            description "the value of restart-helper-status indicates whether the router is acting as a graceful restart helper for the neighbor.";
                        }

                        leaf restart-helper-age {
                            type int32 {
                                range "0..1800";
                            }
                            units "seconds";
                            description "the value of restart-helper-age indicates the remaining time in the current OSPF graceful restart interval, if the router is acting as a restart helper for the neighbor.";
                        }

                        leaf restart-helper-exit-rc {
                            type enumeration {
                                enum "none"                         { value 1; }
                                enum "in-progress"                  { value 2; }
                                enum "completed"                    { value 3; }
                                enum "timed-out"                    { value 4; }
                                enum "topology-changed"             { value 5; }
                            }
                            description "the value of restart-helper-exit-rc indicates the outcome of the last attempt at acting as a graceful restart helper for the neighbor. none no restart has yet been attempted. in-progress A restart attempt is currently underway. completed the last restart completed successfully. timed-out the last restart timed out. topology-changed the last restart was aborted due to a topology change.";
                        }

                        leaf last-restart-time {
                            type yang:date-and-time;
                            description "the value of last-restart-time indicates the last time the neighbor attempted restart.";
                        }

                        leaf restart-reason {
                            type types-ospf:restart-reason-type;
                            description "the value of restart-reason indicates the OSPF neighbor's graceful restart reason.";
                        }

                        leaf up-time {
                            type int32 {
                                range "0..2147483647";
                            }
                            description "the value of up-time indicates the uninterrupted time, in hundredths of seconds, the adjacency to this neighbour has been up.";
                        }

                        leaf last-event-time {
                            type yang:date-and-time;
                            description "the value of last-event-time indicates the value of sys-up-time when the last event occurred that affected the adjacency to the neighbour.";
                        }

                        leaf dead-time-outstanding {
                            type uint32 {
                                range "0..2147483647";
                            }
                            units "seconds";
                            description "the value of dead-time-outstanding indicates the amount of time in seconds until the dead-router interval expires. normally, this value should not be significantly smaller than the configured dead router interval minus one hello interval.";
                        }

                        container statistics {
                            description "Neighbor statistics";

                            leaf events {
                                type yang:counter32;
                                description "the value of events indicates the number of times this neighbor relationship has changed state, or an error has occurred.";
                            }

                            leaf ls-retrans-q-len {
                                type yang:gauge32;
                                description "the value of ls-retrans-Q-len indicates the current length of the retransmission queue.";
                            }

                            leaf bad-nbr-states {
                                type yang:counter32;
                                description "the value of bad-nbr-states indicates the total number of OSPF packets received when the neighbor state was not expecting to receive this packet type since admin-state was last set to 'enabled'.";
                            }

                            leaf lsa-install-failed {
                                type yang:counter32;
                                description "the value of lsa-install-failed indicates the total number of times an LSA could not be installed into the LSDB due to a resource allocation issue since admin-state was last set to 'enabled'.";
                            }

                            leaf bad-seq-nums {
                                type yang:counter32;
                                description "the value of bad-seq-nums indicates the total number of times when a database description packet was received with a sequence number mismatch since admin-state was last set to 'enabled'.";
                            }

                            leaf bad-mtu {
                                type yang:counter32;
                                description "the value of bad-MT-us indicates the total number of times when the MTU in a received database description packet was larger than the MTU of the receiving interface since admin-state was last set to 'enabled'.";
                            }

                            leaf bad-packets {
                                type yang:counter32;
                                description "the value of bad-packets indicates the total number of times when an LS update was received with an illegal LS type or an option mismatch since admin-state was last set to 'enabled'.";
                            }

                            leaf lsa-not-in-lsdbs {
                                type yang:counter32;
                                description "the value of lsa-not-in-lsdbs indicates the total number of times when an LS request was received for an LSA not installed in the LSDB of this router since admin-state was last set to 'enabled'.";
                            }

                            leaf option-mismatches {
                                type yang:counter32;
                                description "the value of option-mismatches indicates the total number of times when a LS update was received with an option mismatch since admin-state was last set to 'enabled'.";
                            }

                            leaf duplicates {
                                type yang:counter32;
                                description "the value of duplicates indicates the total number of times when a duplicate database description packet was received during the exchange state since admin-state was last set to 'enabled'.";
                            }

                            leaf num-restarts {
                                type yang:counter32;
                                description "the value of num-restarts indicates the number of times the neighbor has attempted restart.";
                            }

                        } // container statistics

                    } // list neighbor-state

                    list linkstate-database {
                        key "ls-type adv-rtr-id ls-id";
                        description "Contains all AS scope linkstate advertisements.";

                        leaf ls-type {
                            type uint32;
                            description "Link state type.";
                        }

                        leaf adv-rtr-id {
                            type types-sros:ipv4-address;
                            description "Router that originated the link state advertisement.";
                        }

                        leaf ls-id {
                            type types-sros:ipv4-address;
                            description "Link state advertisement identity.";
                        }

                        leaf sequence-nr {
                            type uint32;
                        }

                        leaf age {
                            type int32;
                        }

                        leaf checksum {
                            type uint32;
                        }

                        leaf known-type {
                            type boolean;
                        }

                        leaf advertisement {
                            type string {
                                length "1..9190";
                            }
                            description "Contents of the link state advertisement.";
                        }

                    } // list linkstate-database

                    list capabilities {
                        key "ls-type adv-rtr-id ls-id";
                        description "Router capability information from area linkstate database";

                        leaf ls-type {
                            type uint32;
                            description "Link state type.";
                        }

                        leaf adv-rtr-id {
                            type types-sros:ipv4-address;
                            description "Router that originated the link state advertisement.";
                        }

                        leaf ls-id {
                            type types-sros:ipv4-address;
                            description "Link state advertisement identity.";
                        }

                        leaf sequence-nr {
                            type uint32;
                        }

                        leaf age {
                            type int32;
                        }

                        leaf checksum {
                            type uint32;
                        }

                        leaf advertisement {
                            type string {
                                length "1..9190";
                            }
                            description "Contents of the link state advertisement.";
                        }

                    } // list capabilities

                } // list interface

                list virtual-link {
                    key "router-id transit-area";
                    description "Enter the virtual-link context";

                    leaf router-id {
                        type types-sros:ipv4-address;
                        description "Router identity of the virtual link neighbor";
                    }

                    leaf transit-area {
                        type leafref {
                            path "../../area-id";
                        }
                        description "<IPv4-address> | [1..4294967295]";
                    }

                    leaf oper-state {
                        type enumeration {
                            enum "down"                         { value 1; }
                            enum "point-to-point"               { value 4; }
                        }
                        description "the value of state indicates the operational state of this virtual interface.";
                    }

                    leaf last-enabled-time {
                        type yang:date-and-time;
                        description "the value of last-enabled-time indicates the sys-up-time value when this entry row entry was enabled.";
                    }

                    leaf cost {
                        type int32 {
                            range "0..65535";
                        }
                        description "the value of cost indicates the OSPF virtual interface cost represents the cost to traverse the transit area to the adjacent router. if multiple routes are available the lowest cost link will be used to maintain the adjacency and route traffic across the transit area.";
                    }

                    leaf link-lsa-count {
                        type yang:gauge32;
                        description "the value of link-lsa-count indicates the total number of link-scope link-state advertisements in this virtual link's link-state database.";
                    }

                    leaf link-lsa-cksum-sum {
                        type int32;
                        description "the value of link-lsa-cksum-sum indicates the 32-bit unsigned sum of the link-scope link-state advertisements' LS checksums contained in this virtual link's link-state database. the sum can be used to determine if there has been a change in a router's link-state database, and to compare the link-state database of two routers.";
                    }

                    leaf link-unk-lsa-count {
                        type yang:gauge32;
                        description "the value of link-unk-lsa-count indicates the total number of unknown link-scope link-state advertisements in this virtual link's link-state database.";
                    }

                    leaf link-unk-lsa-cksum-sum {
                        type int32;
                        description "the value of link-unk-lsa-cksum-sum indicates the 32-bit unsigned sum of the unknown link-scope link-state advertisements' LS checksums contained in this virtual link's link-state database. the sum can be used to determine if there has been a change in a router's link state database, and to compare the link-state database of two routers.";
                    }

                    leaf local-ip-address {
                        type types-sros:ip-address;
                        description "the value of local-ip-address indicates the IP address of the local egress interface that is used to maintain the adjacency to reach this virtual neighbor.";
                    }

                    leaf events {
                        type yang:counter32;
                        description "the value of events indicates the number of times this OSPF interface has changed its state, or an error has occurred.";
                    }

                    leaf last-event-time {
                        type yang:date-and-time;
                        description "the value of last-event-time indicates the value of sys-up-time when an event was last associated with this OSPF interface.";
                    }

                    container state-ipv6-authentication {

                        leaf oper-inb-sa-name {
                            type types-sros:named-item-or-empty;
                            description "the value of oper-inb-sa-name indicates the name of the operational inbound manual I-psec security association, used for authenticating inbound ospfv3 traffic.";
                        }

                        leaf oper-inb-sa-name-temp {
                            type types-sros:named-item-or-empty;
                            description "the value of oper-inb-sa-name-temp indicates the name of a temporary operational inbound manual I-psec security association, used for authenticating inbound ospfv3 traffic. this field can only contain a value when the key-rollover mechanism is ongoing.";
                        }

                        leaf oper-outb-sa-name {
                            type types-sros:named-item-or-empty;
                            description "the value of oper-outb-sa-name indicates the name of the operational outbound manual I-psec security association, used for authenticating outbound ospfv3 traffic. when the key-rollover mechanism is ongoing, the value can temporarily be different from the value of the outbound-sa-name field.";
                        }

                    } // container state-ipv6-authentication

                    container packets {
                        description "Packet counters";

                        leaf tx-total {
                            type yang:counter32;
                            description "The total number of OSPF packets transmitted since admin-state was last set to 'enabled'.";
                        }

                        leaf tx-hello {
                            type yang:counter32;
                            description "The total number of OSPF hello packets transmitted since admin-state was last set to 'enabled'.";
                        }

                        leaf tx-db-description {
                            type yang:counter32;
                            description "The total number of OSPF database description packets transmitted since admin-state was last set to 'enabled'.";
                        }

                        leaf tx-ls-request {
                            type yang:counter32;
                            description "The total number of OSPF link state requests (LS-rs)transmitted since admin-state was last set to 'enabled'.";
                        }

                        leaf tx-ls-update {
                            type yang:counter32;
                            description "The total number of OSPF link state updates (LS-us) transmitted since admin-state was last set to 'enabled'.";
                        }

                        leaf tx-ls-ack {
                            type yang:counter32;
                            description "The total number of OSPF link state acknowledgements transmitted since admin-state was last set to 'enabled'.";
                        }

                        leaf rx-total {
                            type yang:counter32;
                            description "The total number of OSPF packets received since admin-state was last set to 'enabled'.";
                        }

                        leaf rx-hello {
                            type yang:counter32;
                            description "The total number of OSPF hello packets received since admin-state was last set to 'enabled'.";
                        }

                        leaf rx-db-description {
                            type yang:counter32;
                            description "The total number of OSPF database description packets received since admin-state was last set to 'enabled'.";
                        }

                        leaf rx-ls-request {
                            type yang:counter32;
                            description "The total number of link state requests (LS-rs) received since admin-state was last set to 'enabled'.";
                        }

                        leaf rx-ls-update {
                            type yang:counter32;
                            description "The total number of link state updates (LS-us) received since admin-state was last set to 'enabled'.";
                        }

                        leaf rx-ls-ack {
                            type yang:counter32;
                            description "The total number of link state acknowledgements received since admin-state was last set to 'enabled'.";
                        }

                        leaf discarded {
                            type yang:counter32;
                            description "The total number of OSPF packets discarded since admin-state was last set to 'enabled'.";
                        }

                        leaf retransmits {
                            type yang:counter32;
                            description "The total number of OSPF retransmits since admin-state was last set to 'enabled'.";
                        }

                        leaf bad-version {
                            type yang:counter32;
                            description "The total number of OSPF packets received with bad OSPF version numbers since admin-state was last set to 'enabled'.";
                        }

                        leaf bad-network {
                            type yang:counter32;
                            description "The total number of OSPF packets received with invalid network or mask since admin-state was last set to 'enabled'.";
                        }

                        leaf bad-area {
                            type yang:counter32;
                            description "The total number of OSPF packets received with an area mismatch since admin-state was last set to 'enabled'.";
                        }

                        leaf bad-dest-address {
                            type yang:counter32;
                            description "The total number of OSPF packets received with the incorrect IP destination address since admin-state was last set to 'enabled'.";
                        }

                        leaf bad-neighbors {
                            type yang:counter32;
                            description "The total number of OSPF packets received where the neighbor information does not match the information this router has for the neighbor since admin-state was last set to 'enabled'.";
                        }

                        leaf bad-packet-type {
                            type yang:counter32;
                            description "The total number of OSPF packets received with an invalid OSPF packet type since admin-state was last set to 'enabled'.";
                        }

                        leaf bad-length {
                            type yang:counter32;
                            description "The total number of OSPF packets received with a total length not equal to the length given in the packet itself since admin-state was last set to 'enabled'.";
                        }

                        leaf bad-hello-interval {
                            type yang:counter32;
                            description "the value of bad-hello-intervals indicates the total number of OSPF packets received where the hello interval given in packet was not equal to that configured on this interface since admin-state was last set to 'enabled'.";
                        }

                        leaf bad-dead-interval {
                            type yang:counter32;
                            description "The total number of OSPF packets received where the dead interval given in the packet was not equal to that configured on this interface since admin-state was last set to 'enabled'.";
                        }

                        leaf bad-options {
                            type yang:counter32;
                            description "The total number of OSPF packets received with an option that does not match those configured for this interface or area since admin-state was last set to 'enabled'.";
                        }

                        leaf rx-bad-checksum {
                            type yang:counter32;
                            description "The count of LS-as received with bad checksums.";
                        }

                        leaf bad-auth-type {
                            type yang:counter32;
                            description "The total number of OSPF packets received with an invalid authorization type since admin-state was last set to 'enabled'.";
                        }

                        leaf auth-failures {
                            type yang:counter32;
                            description "The total number of OSPF packets received with an invalid authorization key since admin-state was last set to 'enabled'.";
                        }

                    } // container packets

                } // list virtual-link

                list linkstate-database {
                    key "ls-type adv-rtr-id ls-id";
                    description "Contains all AS scope linkstate advertisements.";

                    leaf ls-type {
                        type uint32;
                        description "Link state type.";
                    }

                    leaf adv-rtr-id {
                        type types-sros:ipv4-address;
                        description "Router that originated the link state advertisement.";
                    }

                    leaf ls-id {
                        type types-sros:ipv4-address;
                        description "Link state advertisement identity.";
                    }

                    leaf sequence-nr {
                        type uint32;
                    }

                    leaf age {
                        type int32;
                    }

                    leaf checksum {
                        type uint32;
                    }

                    leaf known-type {
                        type boolean;
                    }

                    leaf advertisement {
                        type string {
                            length "1..9190";
                        }
                        description "Contents of the link state advertisement.";
                    }

                    leaf import-filtered {
                        type boolean;
                    }

                    leaf export-filtered {
                        type boolean;
                    }

                } // list linkstate-database

                list capabilities {
                    key "ls-type adv-rtr-id ls-id";
                    description "Router capability information from area linkstate database";

                    leaf ls-type {
                        type uint32;
                        description "Link state type.";
                    }

                    leaf adv-rtr-id {
                        type types-sros:ipv4-address;
                        description "Router that originated the link state advertisement.";
                    }

                    leaf ls-id {
                        type types-sros:ipv4-address;
                        description "Link state advertisement identity.";
                    }

                    leaf sequence-nr {
                        type uint32;
                    }

                    leaf age {
                        type int32;
                    }

                    leaf checksum {
                        type uint32;
                    }

                    leaf advertisement {
                        type string {
                            length "1..9190";
                        }
                        description "Contents of the link state advertisement.";
                    }

                } // list capabilities

            } // list area

            list virtual-neighbor {
                key "router-id transit-area";
                description "virtual neighbor information.";

                leaf router-id {
                    type types-sros:ipv4-address;
                    description "Router identity of the virtual link neighbor";
                }

                leaf transit-area {
                    type leafref {
                        path "../../../../../router/ospf/area/area-id";
                    }
                    description "The area used to reach the other router";
                }

                leaf if-index {
                    type int32 {
                        range "1..2147483647";
                    }
                    description "the value of if-index indicates the local interface ID for the virtual link over which the neighbor can be reached.";
                }

                leaf address {
                    type types-sros:ip-address;
                    description "the value of address indicates the IP address of the neighbor associated with the local link.";
                }

                leaf oper-state {
                    type enumeration {
                        enum "down"                         { value 1; }
                        enum "attempt"                      { value 2; }
                        enum "init"                         { value 3; }
                        enum "two-way"                      { value 4; }
                        enum "exchange-start"               { value 5; }
                        enum "exchange"                     { value 6; }
                        enum "loading"                      { value 7; }
                        enum "full"                         { value 8; }
                    }
                    description "Indicates the State of the relationship with this Neighbor.";
                }

                leaf options {
                    type int32;
                    description "the value of options indicates a bit mask corresponding to the neighbor's options field.";
                }

                leaf hello-suppressed {
                    type boolean;
                    description "the value of hello-suppressed indicates whether hellos are being suppressed to the neighbor.";
                }

                leaf if-id {
                    type int32 {
                        range "0..2147483647";
                    }
                    description "the value of if-id indicates the interface ID that the neighbor advertises in its hello packets on this link, that is, the neighbor's local interface index.";
                }

                leaf restart-helper-status {
                    type enumeration {
                        enum "not-helping"                  { value 1; }
                        enum "helping"                      { value 2; }
                    }
                    description "the value of restart-helper-status indicates whether the router is acting as a graceful restart helper for the neighbor.";
                }

                leaf restart-helper-age {
                    type int32 {
                        range "0..1800";
                    }
                    units "seconds";
                    description "the value of restart-helper-age indicates the remaining time in the current OSPF graceful restart interval, if the router is acting as a restart helper for the neighbor.";
                }

                leaf restart-helper-exit-rc {
                    type enumeration {
                        enum "none"                         { value 1; }
                        enum "in-progress"                  { value 2; }
                        enum "completed"                    { value 3; }
                        enum "timed-out"                    { value 4; }
                        enum "topology-changed"             { value 5; }
                    }
                    description "the value of restart-helper-exit-rc indicates the outcome of the last attempt at acting as a graceful restart helper for the neighbor. none no restart has yet been attempted. in-progress A restart attempt is currently underway. completed the last restart completed successfully. timed-out the last restart timed out. topology-changed the last restart was aborted due to a topology change.";
                }

                leaf last-restart-time {
                    type yang:date-and-time;
                    description "the value of last-restart-time indicates the last time the neighbor attempted restart.";
                }

                leaf restart-reason {
                    type types-ospf:restart-reason-type;
                    description "the value of restart-reason indicates the OSPF neighbor's graceful restart reason.";
                }

                leaf up-time {
                    type int32 {
                        range "0..2147483647";
                    }
                    description "the value of up-time indicates the uninterrupted time, in hundredths of seconds, the adjacency to this neighbour has been up.";
                }

                leaf last-event-time {
                    type yang:date-and-time;
                    description "the value of last-event-time indicates the value of sys-up-time when the last event occurred that affected the adjacency to the neighbour.";
                }

                leaf dead-time-outstanding {
                    type uint32 {
                        range "0..2147483647";
                    }
                    units "seconds";
                    description "the value of dead-time-outstanding indicates the amount of time in seconds until the dead-router interval expires. normally, this value should not be significantly smaller than the configured dead router interval minus one hello interval.";
                }

                container statistics {
                    description "Virtual link neighbor statistics";

                    leaf events {
                        type yang:counter32;
                        description "the value of events indicates the number of times this neighbor relationship has changed state, or an error has occurred.";
                    }

                    leaf ls-retrans-q-len {
                        type yang:gauge32;
                        description "the value of ls-retrans-Q-len indicates the current length of the retransmission queue.";
                    }

                    leaf bad-nbr-states {
                        type yang:counter32;
                        description "the value of bad-nbr-states indicates the total number of OSPF packets received when the neighbor state was not expecting to receive this packet type since admin-state was last set to 'enabled'.";
                    }

                    leaf lsa-install-failed {
                        type yang:counter32;
                        description "the value of lsa-install-failed indicates the total number of times an LSA could not be installed into the LSDB due to a resource allocation issue since admin-state was last set to 'enabled'.";
                    }

                    leaf bad-seq-nums {
                        type yang:counter32;
                        description "the value of bad-seq-nums indicates the total number of times when a database description packet was received with a sequence number mismatch since admin-state was last set to 'enabled'.";
                    }

                    leaf bad-mtu {
                        type yang:counter32;
                        description "the value of bad-MT-us indicates the total number of times when the MTU in a received database description packet was larger than the MTU of the receiving interface since admin-state was last set to 'enabled'.";
                    }

                    leaf bad-packets {
                        type yang:counter32;
                        description "the value of bad-packets indicates the total number of times when an LS update was received with an illegal LS type or an option mismatch since admin-state was last set to 'enabled'.";
                    }

                    leaf lsa-not-in-lsdbs {
                        type yang:counter32;
                        description "the value of lsa-not-in-lsdbs indicates the total number of times when an LS request was received for an LSA not installed in the LSDB of this router since admin-state was last set to 'enabled'.";
                    }

                    leaf option-mismatches {
                        type yang:counter32;
                        description "the value of option-mismatches indicates the total number of times when a LS update was received with an option mismatch since admin-state was last set to 'enabled'.";
                    }

                    leaf duplicates {
                        type yang:counter32;
                        description "the value of duplicates indicates the total number of times when a duplicate database description packet was received during the exchange state since admin-state was last set to 'enabled'.";
                    }

                    leaf num-restarts {
                        type yang:counter32;
                        description "the value of num-restarts indicates the number of times the neighbor has attempted restart.";
                    }

                } // container statistics

            } // list virtual-neighbor

            list lfa-coverage {
                key "area-id";
                description "Represents information on LFA coverage per area.";

                leaf area-id {
                    type types-sros:ipv4-address;
                    description "Attribute area-id";
                }

                leaf nodes-covered {
                    type yang:gauge32;
                    description "The value of nodes-covered indicates in absolute numbers the number of nodes for which an LFA is found.";
                }

                leaf nodes-total {
                    type yang:gauge32;
                    description "The value of total-nodes indicates in absolute numbers the number of nodes eligible for LFA calculation.";
                }

                leaf nodes-coverage {
                    type yang:gauge32 {
                        range "0..100";
                    }
                    units "percent";
                    description "The value of coverage indicates how much LFA coverage is being obtained for the set of available LFA eligible nodes.";
                }

                leaf pfx-covered {
                    type yang:gauge32;
                    description "The value of pfx-covered indicates in absolute numbers the number of prefixes for which an LFA is found.";
                }

                leaf pfx-total {
                    type yang:gauge32;
                    description "The value of total-pfx indicates in absolute numbers the number of prefixes eligible for LFA calculation.";
                }

                leaf pfx-coverage {
                    type yang:gauge32 {
                        range "0..100";
                    }
                    units "percent";
                    description "The value of pfx-coverage indicates how much LFA prefix coverage is being obtained for the set of available LFA eligible prefixes.";
                }

            } // list lfa-coverage

            list as-linkstate-database {
                key "ls-type adv-rtr-id ls-id";
                description "Contains all AS scope linkstate advertisements.";

                leaf ls-type {
                    type uint32;
                    description "Link state type.";
                }

                leaf adv-rtr-id {
                    type types-sros:ipv4-address;
                    description "Router that originated the link state advertisement.";
                }

                leaf ls-id {
                    type types-sros:ipv4-address;
                    description "Link state advertisement identity.";
                }

                leaf sequence-nr {
                    type uint32;
                }

                leaf age {
                    type int32;
                }

                leaf checksum {
                    type uint32;
                }

                leaf known-type {
                    type boolean;
                }

                leaf advertisement {
                    type string {
                        length "1..9190";
                    }
                    description "Contents of the link state advertisement.";
                }

            } // list as-linkstate-database

            list as-capabilities {
                key "ls-type adv-rtr-id ls-id";
                description "Router capability information from AS linkstate database";

                leaf ls-type {
                    type uint32;
                    description "Link state type.";
                }

                leaf adv-rtr-id {
                    type types-sros:ipv4-address;
                    description "Router that originated the link state advertisement.";
                }

                leaf ls-id {
                    type types-sros:ipv4-address;
                    description "Link state advertisement identity.";
                }

                leaf sequence-nr {
                    type uint32;
                }

                leaf age {
                    type int32;
                }

                leaf checksum {
                    type uint32;
                }

                leaf advertisement {
                    type string {
                        length "1..9190";
                    }
                    description "Contents of the link state advertisement.";
                }

            } // list as-capabilities

            list route {
                key "route-type destination area";
                description "Contains OSPF route table.";

                leaf route-type {
                    type types-ospf:route-type;
                    description "The route type os this route, network or router.";
                }

                leaf destination {
                    type types-sros:ip-prefix;
                    description "The value specifies the IP address and mask of the route destination.";
                }

                leaf area {
                    type types-sros:ipv4-address;
                    description "Area through which the destination is reachable.";
                }

                leaf path-type {
                    type types-ospf:route-path-type;
                    description "Select path type for the destination.";
                }

                leaf dest-type {
                    type types-ospf:route-dest-type;
                }

                leaf rtm-status {
                    type types-ospf:rtm-status;
                    description "Indicates status in RTM.";
                }

                leaf cost {
                    type uint32;
                    description "The cost of this route, calculated during SPF.";
                }

                leaf type2-cost {
                    type uint32;
                    description "The external type2 cost of this route, calculated during SPF.";
                }

                list next-hop {
                    key "ecmp-index";
                    description "Stores a next hop for a given route.";

                    leaf ecmp-index {
                        type types-router:ip-ecmp;
                        description "ECMP index of this route next-hop.";
                    }

                    leaf type {
                        type enumeration {
                            enum "unknown"                      { value 0; }
                            enum "direct"                       { value 1; }
                            enum "rsvp"                         { value 2; }
                            enum "srte"                         { value 3; }
                            enum "shortcut"                     { value 4; }
                            enum "blackhole"                    { value 5; }
                            enum "unnumbered"                   { value 6; }
                            enum "ip"                           { value 7; }
                        }
                        description "Indicates the next hop type";
                    }

                    leaf ip-address {
                        type types-sros:ip-address;
                        description "The value specifies the IP address of the next hop for this route";
                    }

                    leaf interface {
                        type types-sros:interface-name;
                        description "The value specifies the interface of the next hop for this route";
                    }

                    leaf tunnel-id {
                        type uint32;
                        description "The tunnel-id given to this tunnelled next hop";
                    }

                    leaf area {
                        type types-sros:ipv4-address;
                        description "The value specifies the area the shortest path was found in";
                    }

                    container weight {
                        description "Weight information";

                        leaf configured {
                            type uint32;
                            description "The weight given to this next hop";
                        }

                        leaf normalised {
                            type uint32;
                            description "The normalised weight of this next hop for this route";
                        }

                    } // container weight

                } // list next-hop

            } // list route

        } // list ospf3

    } // grouping state-svc-vprn-ospf3

}
