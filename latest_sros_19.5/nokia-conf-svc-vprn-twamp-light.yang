submodule nokia-conf-svc-vprn-twamp-light {

    yang-version "1.1";

    belongs-to nokia-conf { prefix "conf"; }

    import nokia-sros-yang-extensions     { prefix "sros-ext"; }
    import nokia-types-sros               { prefix "types-sros"; }


    sros-ext:sros-major-release "rel19";

    organization "Nokia";

    contact
        "Nokia SR OS Support
         Web: <http://www.nokia.com>";

    description
        "Nokia YANG Data model to configure  OAM Performance Monitoring TWAMP-Light (Two-Way Active Measurement Protocol, Light) on SR OS based routers.

         Copyright 2016 Nokia. All rights reserved. Reproduction of this document
         is authorized on the condition that the foregoing copyright notice is included.

         This nokia-conf-svc-vprn-twamp-light YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2018-10-16";

    grouping conf-svc-vprn-twamp-light {
        container twamp-light {
            description "Enter the twamp-light context";

            container reflector {
                presence "reflector";
                description "Enter the reflector context";

                leaf admin-state {
                    type types-sros:admin-state;
                    default "disable";
                    description "Administratively enable or disable TWAMP-Light reflector";
                }

                leaf description {
                    type types-sros:description;
                    description "Descriptive text for the specified TWAMP-Light reflector";
                }

                leaf udp-port {
                    type types-sros:tcp-udp-port-non-zero {
                        range "862|64364..64373";
                    }
                    sros-ext:auto-restart-to-modify;
                    mandatory true;
                    description "UDP port on which the specified TWAMP-Light reflector listens for TWAMP PDUs";
                }

                list prefix {
                    key "ip-prefix";
                    max-elements 50;
                    description "Enter the prefix context";

                    leaf ip-prefix {
                        type types-sros:ip-unicast-prefix;
                        description "Source prefix for the TWAMP-Light reflector";
                    }

                    leaf description {
                        type types-sros:description;
                        description "Descriptive text for the specified TWAMP-Light reflector prefix";
                    }

                } // list prefix

            } // container reflector

        } // container twamp-light

    } // grouping conf-svc-vprn-twamp-light

}
