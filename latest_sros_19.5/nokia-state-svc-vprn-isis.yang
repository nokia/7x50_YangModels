submodule nokia-state-svc-vprn-isis {

    yang-version "1.1";

    belongs-to nokia-state { prefix "state"; }

    import ietf-inet-types                { prefix "inet"; }
    import ietf-yang-types                { prefix "yang"; }
    import nokia-sros-yang-extensions     { prefix "sros-ext"; }
    import nokia-types-igp                { prefix "types-igp"; }
    import nokia-types-isis               { prefix "types-isis"; }
    import nokia-types-router             { prefix "types-router"; }
    import nokia-types-sros               { prefix "types-sros"; }

    include nokia-state-router;
    include nokia-state-router-isis;

    sros-ext:sros-major-release "rel19";

    organization "Nokia";

    contact
        "Nokia SR OS Support
         Web: <http://www.nokia.com>";

    description
        "Nokia YANG Data model with operational state for vprn isis protocol attributes on SR OS based routers.

         Copyright 2016 Nokia. All rights reserved. Reproduction of this document
         is authorized on the condition that the foregoing copyright notice is included.

         This nokia-state-svc-vprn-isis YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-03-18";

    grouping state-svc-vprn-isis {
        list isis {
            key "isis-instance";
            description "Enter the isis context";

            leaf isis-instance {
                type int32 {
                    range "0..31";
                }
                description "Instance ID for IS-IS instance";
            }

            leaf oper-system-id {
                type types-igp:system-id;
                description "The ID for this instance of the Integrated IS-IS protocol.";
            }

            leaf oper-router-id {
                type types-sros:ipv4-address;
                description "Indicates a ipv4-address uniquely identifying the router in the Autonomous System.";
            }

            leaf db-export-igp-asn {
                type inet:as-number;
                description "Indicates Autonomous System Number the IGP is using during its database export.";
            }

            leaf oper-state {
                type types-sros:oper-state;
                description
                    "The value of the this object indicates the operational
                     state of the destination.";
            }

            leaf last-enabled-time {
                type yang:date-and-time;
                description "Indicates the last system up time when the current IS-IS protocol instance was run.";
            }

            leaf last-spf {
                type yang:date-and-time;
                description
                    "Indicates the system up time when the last SPF run was performed for this
                     instance of the IS-IS protocol in the router.";
            }

            leaf prefix-limit-overload-time-left {
                type int32 {
                    range "0..1800";
                }
                description
                    "Indicates the remaining time in seconds before IS-IS will attempt to enter its
                     normal state to recover from the overload state due to prefix limit exceeded.

                     The value of 0 implies that the system is either not in overload or indefinitely in overload state.";
            }

            leaf version {
                type string;
                description "Indicates the version number of the IS-IS protocol to which this instance conforms.";
            }

            leaf l1-state {
                type types-isis:level-state;
                description "Indicates the state of the Level 1 database.";
            }

            leaf l2-state {
                type types-isis:level-state;
                description "Indicates the state of the Level 2 database.";
            }

            leaf spf-hold-time {
                type int32 {
                    range "0..65535";
                }
                units "seconds";
                description "Indicates the time interval at which SPF is run.";
            }

            container loopfree-alternate {
                description "Enter the loopfree-alternate context";

                container statistics {
                    description "LFA,TI-LFA and remote-LFA SPF run information";

                    container lfa {
                        description "LFA SPF run information";

                        leaf runs {
                            type yang:counter32;
                            description "Indicates the number of times the calculations have been made.";
                        }

                        leaf time {
                            type yang:date-and-time;
                            description "Indicates the time when the last lfa was scheduled.";
                        }

                        container partial {
                            description "Partial LFA SPF run LFA SPF run information";

                            leaf runs {
                                type yang:counter32;
                                description "Indicates the number of times the calculations have been made.";
                            }

                            leaf time {
                                type yang:date-and-time;
                                description "Indicates the time when the last lfa was scheduled.";
                            }

                        } // container partial

                    } // container lfa

                    container remote-lfa {
                        description "Remote LFA SPF run information";

                        leaf runs {
                            type yang:counter32;
                            description "Indicates the number of times the calculations have been made.";
                        }

                        leaf time {
                            type yang:date-and-time;
                            description "Indicates the time when the last lfa was scheduled.";
                        }

                    } // container remote-lfa

                    container ti-lfa {
                        description "TI-LFA SPF run information";

                        leaf runs {
                            type yang:counter32;
                            description "Indicates the number of times the calculations have been made.";
                        }

                        leaf time {
                            type yang:date-and-time;
                            description "Indicates the time when the last lfa was scheduled.";
                        }

                    } // container ti-lfa

                } // container statistics

            } // container loopfree-alternate

            container statistics {
                description "Holds statistics for an instance of IS-IS protocol.";

                leaf lsp-regenerations {
                    type yang:counter32;
                    description "Indicates the count of LSP regenerations.";
                }

                leaf initiated-purges {
                    type yang:counter32;
                    description "Indicates the number of times purges have been initiated.";
                }

                leaf corrupted-lsps {
                    type yang:counter32;
                    description "Indicates the number of corrupted LSPs detected.";
                }

                leaf lsp-l1-db-overloads {
                    type yang:counter32;
                    description "Indicates the number of times the LSP L1 database has become overloaded.";
                }

                leaf lsp-l2-db-overloads {
                    type yang:counter32;
                    description "Indicates the number of times the Level 2 LSP database has become overloaded.";
                }

                leaf manual-address-dropped-from-areas {
                    type yang:counter32;
                    description "Indicates the number of times a manual address has been dropped from the area.";
                }

                leaf attempt-to-exceed-max-sequence-numbers {
                    type yang:counter32;
                    description "Indicates the number of times the IS has attempted to exceed the maximum sequence number.";
                }

                leaf sequence-number-skips {
                    type yang:counter32;
                    description "Indicates the number of times a sequence number skip has occurred.";
                }

                leaf own-lsp-purges {
                    type yang:counter32;
                    description
                        "Indicates the number of times a zero-aged copy of the system's own LSP
                         is received from some other node.";
                }

                leaf id-field-length-mismatches {
                    type yang:counter32;
                    description
                        "Indicates the number of times a PDU is received with a different value
                         for ID field length to that of the receiving system.";
                }

                leaf max-area-address-mismatches {
                    type yang:counter32;
                    description
                        "Indicates the number of times a PDU is received with a different value
                         for maximum area addresses from that of the receiving system.";
                }

                leaf authentication-failures {
                    type yang:counter32;
                    description "Indicates the number of authentication failures recognized by this instance of the protocol.";
                }

                leaf partition-changes {
                    type yang:counter32;
                    description "indicates the number of partition changes.";
                }

                container sid {
                    description "SID related statistics";

                    leaf srgb-errors {
                        type yang:counter32;
                        description "Indicates the total number of errors for SIDs that are not within the label-range of the router.";
                    }

                    leaf duplicated-errors {
                        type yang:counter32;
                        description "Indicates the total number of errors for SIDs which are already assigned to another prefix.";
                    }

                } // container sid

                container spf {
                    description "SPF related statistics";

                    leaf runs {
                        type yang:counter32;
                        description "Indicates the number of times the calculations have been made.";
                    }

                    leaf time {
                        type yang:date-and-time;
                        description "Indicates the time when the last lfa was scheduled.";
                    }

                    container partial {
                        description "Partial SPF related statistics";

                        leaf runs {
                            type yang:counter32;
                            description "Indicates the number of times the calculations have been made.";
                        }

                        leaf time {
                            type yang:date-and-time;
                            description "Indicates the time when the last lfa was scheduled.";
                        }

                    } // container partial

                } // container spf

                container cspf {

                    leaf requests {
                        type yang:counter32;
                        description "Indicates the number of CSPF requests made to the protocol.";
                    }

                    leaf dropped-requests {
                        type yang:counter32;
                        description "Indicates the number of dropped CSPF requests by the protocol.";
                    }

                    leaf paths-found {
                        type yang:counter32;
                        description
                            "Indicates the number of responses to CSPF requests for which paths satisfying
                             the constraints were found.";
                    }

                    leaf paths-not-found {
                        type yang:counter32;
                        description
                            "Indicates the number of responses to CSPF requests for which no paths satisfying
                             the constraints were found.";
                    }

                } // container cspf

                container lsp {
                    description "CSPF related statistics";

                    leaf received {
                        type yang:counter32;
                        description "Indicates the count of link state PDUs received by this instance of the protocol.";
                    }

                    leaf dropped {
                        type yang:counter32;
                        description "Indicates the count of link state PDUs dropped by this instance of the protocol.";
                    }

                    leaf sent {
                        type yang:counter32;
                        description "Indicates the count of link state PDUs sent out by this instance of the protocol.";
                    }

                    leaf retransmitted {
                        type yang:counter32;
                        description
                            "Indicates the count of link state PDUs that had to be retransmitted by this
                             instance of the protocol.";
                    }

                } // container lsp

                container iih {
                    description "IIH related statistics";

                    leaf received {
                        type yang:counter32;
                        description "Indicates the count of link state PDUs received by this instance of the protocol.";
                    }

                    leaf dropped {
                        type yang:counter32;
                        description "Indicates the count of link state PDUs dropped by this instance of the protocol.";
                    }

                    leaf sent {
                        type yang:counter32;
                        description "Indicates the count of link state PDUs sent out by this instance of the protocol.";
                    }

                    leaf retransmitted {
                        type yang:counter32;
                        description
                            "Indicates the count of link state PDUs that had to be retransmitted by this
                             instance of the protocol.";
                    }

                } // container iih

                container csnp {
                    description "CSNP related statistics";

                    leaf received {
                        type yang:counter32;
                        description "Indicates the count of link state PDUs received by this instance of the protocol.";
                    }

                    leaf dropped {
                        type yang:counter32;
                        description "Indicates the count of link state PDUs dropped by this instance of the protocol.";
                    }

                    leaf sent {
                        type yang:counter32;
                        description "Indicates the count of link state PDUs sent out by this instance of the protocol.";
                    }

                    leaf retransmitted {
                        type yang:counter32;
                        description
                            "Indicates the count of link state PDUs that had to be retransmitted by this
                             instance of the protocol.";
                    }

                } // container csnp

                container psnp {
                    description "PSNP related statistics";

                    leaf received {
                        type yang:counter32;
                        description "Indicates the count of link state PDUs received by this instance of the protocol.";
                    }

                    leaf dropped {
                        type yang:counter32;
                        description "Indicates the count of link state PDUs dropped by this instance of the protocol.";
                    }

                    leaf sent {
                        type yang:counter32;
                        description "Indicates the count of link state PDUs sent out by this instance of the protocol.";
                    }

                    leaf retransmitted {
                        type yang:counter32;
                        description
                            "Indicates the count of link state PDUs that had to be retransmitted by this
                             instance of the protocol.";
                    }

                } // container psnp

                container unknown {
                    description "Unknown PDU related statistics";

                    leaf received {
                        type yang:counter32;
                        description "Indicates the count of link state PDUs received by this instance of the protocol.";
                    }

                    leaf dropped {
                        type yang:counter32;
                        description "Indicates the count of link state PDUs dropped by this instance of the protocol.";
                    }

                    leaf sent {
                        type yang:counter32;
                        description "Indicates the count of link state PDUs sent out by this instance of the protocol.";
                    }

                    leaf retransmitted {
                        type yang:counter32;
                        description
                            "Indicates the count of link state PDUs that had to be retransmitted by this
                             instance of the protocol.";
                    }

                } // container unknown

            } // container statistics

            list interface {
                key "interface-name";
                description "Enter the interface context";

                leaf interface-name {
                    type types-sros:interface-name;
                    description "Router interface name.";
                }

                leaf oper-state {
                    type types-sros:oper-state;
                    description "Indicates the current operational state of IS-IS protocol on this interface.";
                }

                leaf circuit-index {
                    type uint32 {
                        range "1..2000000000";
                    }
                    description "Indicates a cross reference index to the isis circ table.";
                }

                leaf oper-type {
                    type types-isis:interface-type;
                    description "Indicates the operational type on this IS-IS interface.";
                }

                leaf ber-state {
                    type enumeration {
                        enum "none"                         { value 0; }
                        enum "sd"                           { value 1; }
                        enum "sf"                           { value 2; }
                    }
                    description "Indicates the Bit Error Rate (BER) state of this interface.";
                }

                leaf te-metric {
                    type types-isis:oper-metric;
                    description
                        "Indicates the MPLS TE metric configured for this interface.
                         This metric is flooded out in the TE metric sub-tlv in the IS-IS LSPs.
                         Depending on the configuration, either the TE metric value or the
                         native IS-IS metric values are used in CSPF computations.";
                }

                leaf te-state {
                    type types-sros:oper-state;
                    description "Indicates the MPLS interface TE status from the IS-IS standpoint.";
                }

                leaf point-to-point-circuit-id {
                    type types-isis:circuit-id;
                    description "Indicates the ID of the circuit allocated during initialization.";
                }

                leaf up-time {
                    type int32;
                    description
                        "If the circuit is up, indicates the amount of time in seconds since this circuit entered state 'up'.

                         If the circuit is not up, indicates the number of seconds since the circuit was up,
                         or since the system started, if the circuit has never been up.";
                }

                container statistics {
                    description "Interface statistics";

                    leaf initialization-failures {
                        type yang:counter32;
                        description "Indicates the number of times initialization of this circuit has failed.";
                    }

                    leaf adjacency-state-change {
                        type yang:counter32;
                        description "Indicates the number of times an adjacency state change has occurred on this circuit.";
                    }

                    leaf adjacency-rejection {
                        type yang:counter32;
                        description "Indicates the number of times an adjacency has been rejected on this circuit.";
                    }

                    leaf control-pdu-sent {
                        type yang:counter32;
                        description "Indicates the number of IS-IS control PDUs sent on this circuit.";
                    }

                    leaf control-pdu-received {
                        type yang:counter32;
                        description "Indicates the number of IS-IS control PDUs received on this circuit.";
                    }

                    leaf control-pdu-id-length-mismatch-received {
                        type yang:counter32;
                        description
                            "Indicates the number an IS-IS control PDU with an ID
                             field length different to that for this system has been received.";
                    }

                } // container statistics

                list level {
                    key "level-number";
                    description "Enter the level context";

                    leaf level-number {
                        type enumeration {
                            enum "1"                            { value 1; }
                            enum "2"                            { value 2; }
                        }
                        description "IS-IS protocol level to which these attributes apply";
                    }

                    leaf adjacencies-number {
                        type uint32;
                        description "Indicates the number of adjacencies on this particular level of the interface.";
                    }

                    leaf designated-intermediate-system {
                        type types-igp:system-id;
                        description "Indicates the ID of the LAN Designated Intermediate System on this circuit at this level.";
                    }

                    leaf lsp-transmit-queue-count {
                        type uint32;
                        description "Indicates how many LSPs are in the transmit queue of this interface for this IS-IS level.";
                    }

                    leaf circuit-id {
                        type types-isis:circuit-id;
                        description "Indicates the ID of the circuit allocated during initialization.";
                    }

                    container oper-metric {
                        description "Operational metic";

                        leaf ipv4-unicast {
                            type types-isis:oper-metric;
                            description "Indicates the operational value of the IPv4 unicast metric being used with this interface level.";
                        }

                        leaf ipv6-unicast {
                            type types-isis:oper-metric;
                            description "Indicates the operational value of the IPv6 unicast metric being used with this interface level.";
                        }

                        leaf ipv4-multicast {
                            type types-isis:oper-metric;
                            description "Indicates the operational value of the interface level metric for IPv4 multicast.";
                        }

                        leaf ipv6-multicast {
                            type types-isis:oper-metric;
                            description "Indicates the operational value of the interface level metric for IPv6 multicast.";
                        }

                    } // container oper-metric

                    container statistics {
                        description "Interface level statistics";

                        leaf designated-intermediate-system-changes {
                            type yang:counter32;
                            description "Indicates the number of times the LAN Designated Intermediate System has changed at this level.";
                        }

                        list packets {
                            key "direction";
                            description
                                "Information about IS-IS protocol traffic at one level
                                 on one circuit in one direction";

                            leaf direction {
                                type enumeration {
                                    enum "sending"                      { value 1; }
                                    enum "receiving"                    { value 2; }
                                }
                                description "Were we sending or receiving these PDUs?";
                            }

                            leaf hello {
                                type yang:counter32;
                                description
                                    "The number of IS-IS Hello PDUs seen in this
                                     direction at this level.";
                            }

                            leaf lsp {
                                type yang:counter32;
                                description
                                    "The number of IS-IS LSPs seen in this
                                     direction at this level.";
                            }

                            leaf csnp {
                                type yang:counter32;
                                description
                                    "The number of IS-IS CSNPs seen in this
                                     direction at this level.";
                            }

                            leaf psnp {
                                type yang:counter32;
                                description
                                    "The number of IS-IS PSNPs seen in this
                                     direction at this level.";
                            }

                        } // list packets

                    } // container statistics

                } // list level

                list adjacency {
                    key "adjacency-index";
                    description "Adjacencies to Intermediate Systems and their operational status information.";

                    leaf adjacency-index {
                        type int32 {
                            range "1..2000000000";
                        }
                        description
                            "A unique value identifying the IS adjacency from all
                             other such adjacencies on this circuit. This value is
                             assigned by the system when the adjacency is created
                             automatically.";
                    }

                    leaf oper-state {
                        type enumeration {
                            enum "initializing"                 { value 1; }
                            enum "up"                           { value 2; }
                            enum "failed"                       { value 3; }
                            enum "down"                         { value 4; }
                        }
                        description "The state of the adjacency";
                    }

                    leaf usage {
                        type enumeration {
                            enum "undefined"                    { value 1; }
                            enum "level1"                       { value 2; }
                            enum "level2"                       { value 3; }
                            enum "level1and2"                   { value 4; }
                        }
                        description
                            "An adjacency of type level1 is used for level 1
                             traffic only. An adjacency of type level2 is used
                             for level 2 traffic only. An adjacency of type level1and2
                             is used for both level 1 and level 2 traffic. There
                             may be two adjacencies (of types level1 and level2)
                             between the same pair of Intermediate Systems.";
                    }

                    leaf hold-timer {
                        type int32 {
                            range "1..65535";
                        }
                        description
                            "The holding time for this adjacency updated from
                             received IIH PDUs.";
                    }

                    leaf uptime {
                        type int32;
                        units "seconds";
                        description
                            "If the adjacency is up, the amount of time in seconds
                             since this adjacency entered state 'up'.  If the adjacency
                             is not up, the number of seconds since the adjacency was
                             up, or since the system started, if the adjacency has
                             never been up.

                             Note: This can be implemented as start time less
                             the current time.";
                    }

                    leaf expires-in {
                        type int32 {
                            range "0..65535";
                        }
                        units "seconds";
                        description "The value indicates the time in which the adjacency will expire if no hello packets are received.";
                    }

                    leaf level {
                        type enumeration {
                            enum "level1"                       { value 1; }
                            enum "level2"                       { value 2; }
                            enum "level1-l2"                    { value 3; }
                            enum "unknown"                      { value 4; }
                        }
                        description "The value indicates the circuit type of the adjacency as advertised.";
                    }

                    container restart {
                        description "Adjacency restart information";

                        leaf support {
                            type boolean;
                            description
                                "The value indicates whether adjacency supports ISIS graceful restart.

                                 If support has a value of 'true' the adjacency
                                 supports graceful restart.";
                        }

                        leaf status {
                            type enumeration {
                                enum "not-helping"                  { value 1; }
                                enum "restarting"                   { value 2; }
                                enum "restart-complete"             { value 3; }
                                enum "helping"                      { value 4; }
                            }
                            description "The value indicates the graceful restart status of the adjacency.";
                        }

                        leaf suppressed {
                            type boolean;
                            description
                                "The value indicates if the adjacency has requested this router to suppress advertisement of
                                 the adjacency in this router's LSPs.

                                 If suppressed has a value of 'true' the adjacency
                                 has requested to suppress advertisement of the LSPs.";
                        }

                        leaf num-restarts {
                            type uint32;
                            description "The value indicates the number of times the adjacency has attempted restart.";
                        }

                        leaf last-restart {
                            type yang:date-and-time;
                            description "The value indicates the last time the adjacency attempted restart.";
                        }

                    } // container restart

                    container neighbor {
                        description "Neighbor information";

                        leaf snpa-address {
                            type types-isis:snpa-address;
                            description "The SNPA address of the neighboring system.";
                        }

                        leaf system-type {
                            type enumeration {
                                enum "l1-is"                        { value 1; }
                                enum "l2-is"                        { value 2; }
                                enum "l1-l2-is"                     { value 3; }
                                enum "unknown"                      { value 4; }
                            }
                            description "The type of the neighboring system.";
                        }

                        leaf system-id {
                            type string {
                                length "0..24";
                            }
                            description
                                "The system ID and 4 byte circuit ID of the
                                 neighboring Intermediate System set from
                                 the source ID field of the Three-Way-Handshake
                                 information from the neighbor's IIH PDUs.";
                        }

                        leaf priority {
                            type int32 {
                                range "0..127";
                            }
                            description
                                "Priority of the neighboring Intermediate System for
                                 becoming the LAN Level 1 Designated Intermediate System
                                 if the value of isisISAdjNeighSysType is
                                 L1IntermediateSystem or LAN Level 2 Designated
                                 Intermediate System if the value of
                                 isisISAdjNeighSysType is L2IntermediateSystem.";
                        }

                        leaf ipv4 {
                            type types-sros:ipv4-address;
                            description "The value indicates the ip-address of the neighbor with which adjacency is formed.";
                        }

                        leaf ipv6 {
                            type types-sros:ipv6-address;
                            description
                                "The value indicates the IP address of the neighbor with which an IPv6-adjacency is formed
                                 this will always be an IPv6 address.";
                        }

                    } // container neighbor

                    container multi-topology {
                        description "Multi topology related information";

                        leaf enabled {
                            type boolean;
                            description
                                "The value indicates if the ISIS multi-topology protocol is supported on the neighbor.

                                 If the value is 'true', ISIS multi-topology
                                 protocol is enabled on the neighbor.";
                        }

                        container id0 {
                            description "Multi topology 0 information";

                            leaf enabled {
                                type boolean;
                                description
                                    "The value indicates if the MT x IPvx topology is supported on the neighbor.

                                     If the value of enable is 'true', MT x IPvx topology is
                                     supported on the neighbor.";
                            }

                            leaf bfd-required {
                                type boolean;
                                description
                                    "The value indicates if BFD session is required for this Multi Topology before bringing the
                                     adjacency to FULL state, as described in RFC6213.";
                            }

                            leaf bfd-usable {
                                type boolean;
                                description
                                    "The value indicates if BFD session for this Multi Topology is usable, that is either not
                                     required or in state UP, as described in RFC6213.";
                            }

                        } // container id0

                        container id2 {
                            description "Multi topology 2 information";

                            leaf enabled {
                                type boolean;
                                description
                                    "The value indicates if the MT x IPvx topology is supported on the neighbor.

                                     If the value of enable is 'true', MT x IPvx topology is
                                     supported on the neighbor.";
                            }

                            leaf bfd-required {
                                type boolean;
                                description
                                    "The value indicates if BFD session is required for this Multi Topology before bringing the
                                     adjacency to FULL state, as described in RFC6213.";
                            }

                            leaf bfd-usable {
                                type boolean;
                                description
                                    "The value indicates if BFD session for this Multi Topology is usable, that is either not
                                     required or in state UP, as described in RFC6213.";
                            }

                        } // container id2

                        container id3 {
                            description "Multi topology 3 information";

                            leaf enabled {
                                type boolean;
                                description
                                    "The value indicates if the MT x IPvx topology is supported on the neighbor.

                                     If the value of enable is 'true', MT x IPvx topology is
                                     supported on the neighbor.";
                            }

                            leaf bfd-required {
                                type boolean;
                                description
                                    "The value indicates if BFD session is required for this Multi Topology before bringing the
                                     adjacency to FULL state, as described in RFC6213.";
                            }

                            leaf bfd-usable {
                                type boolean;
                                description
                                    "The value indicates if BFD session for this Multi Topology is usable, that is either not
                                     required or in state UP, as described in RFC6213.";
                            }

                        } // container id3

                        container id4 {
                            description "Multi topology 4 information";

                            leaf enabled {
                                type boolean;
                                description
                                    "The value indicates if the MT x IPvx topology is supported on the neighbor.

                                     If the value of enable is 'true', MT x IPvx topology is
                                     supported on the neighbor.";
                            }

                            leaf bfd-required {
                                type boolean;
                                description
                                    "The value indicates if BFD session is required for this Multi Topology before bringing the
                                     adjacency to FULL state, as described in RFC6213.";
                            }

                            leaf bfd-usable {
                                type boolean;
                                description
                                    "The value indicates if BFD session for this Multi Topology is usable, that is either not
                                     required or in state UP, as described in RFC6213.";
                            }

                        } // container id4

                    } // container multi-topology

                    list area-address {
                        key "area-address";
                        description
                            "Each entry contains one Area Address reported by a
                             neighboring Intermediate System in its IIH PDUs.";

                        leaf area-address {
                            type types-isis:area-address;
                            description
                                "An area address reported in a Level 1 LSP received by
                                 this instance of the protocol.";
                        }

                    } // list area-address

                    list supported-protocol {
                        key "protocol";
                        description
                            "Each entry contains one protocol supported by a
                             neighboring Intermediate System as reported in its IIH PDUs.";

                        leaf protocol {
                            type enumeration {
                                enum "iso8473"                      { value 129; }
                                enum "ipv6"                         { value 142; }
                                enum "ip"                           { value 204; }
                            }
                            description
                                "One supported protocol as reported in IIH PDUs received
                                 from the neighbor.";
                        }

                    } // list supported-protocol

                } // list adjacency

                list admin-group {
                    key "group-name";
                    description
                        "Indicates the admin groups inherited from MPLS interface that identifies
                         the admin groups to which the interface belongs.";

                    leaf group-name {
                        type types-sros:named-item;
                        description
                            "Indicates the interface admin-goup inherited from MPLS interface.
                             It identifies the admin groups to which the interface belongs.";
                    }

                } // list admin-group

            } // list interface

            list level {
                key "level-number";
                description "Enter the level context";

                leaf level-number {
                    type enumeration {
                        enum "1"                            { value 1; }
                        enum "2"                            { value 2; }
                    }
                    description "IS-IS protocol level to which these attributes apply";
                }

                leaf oper-lsp-mtu-size {
                    type types-isis:lsp-buffer-size;
                    description "Indicates the operational size of Level 1 LSPs and SNPs originated by this instance.";
                }

                leaf total-exported-routes {
                    type yang:counter32;
                    description
                        "Indicates the total number of routes exported into ISIS level 1 from the route table manager
                         when an export policy is configured";
                }

                leaf lsps {
                    type uint32;
                    description "Indicates the number of LSPs existing in the system for the particular level.";
                }

                leaf max-oper-lsp-mtu-size {
                    type types-isis:lsp-buffer-size;
                    description
                        "Indicates the maximum size of LSPs and SNPs that can be originated on
                         any circuit by this instance for the particular level.";
                }

                container overload {
                    description "Overload state";

                    leaf status {
                        type types-isis:overload-status;
                        description "Indicates whether or not this level is in overload state.";
                    }

                    leaf time-left {
                        type types-sros:time-interval;
                        units "deciseconds";
                        description
                            "Indicates the remaining time, measured in units of deciseconds, before this level
                             will attempt to enter its normal state.";
                    }

                } // container overload

            } // list level

            list link-group {
                key "link-group-name";
                description "Enter the link-group context";

                leaf link-group-name {
                    type types-sros:named-item;
                    description "Link group name for the IS-IS protocol";
                }

                list level {
                    key "level-number";
                    description "Enter the level context";

                    leaf level-number {
                        type enumeration {
                            enum "1"                            { value 1; }
                            enum "2"                            { value 2; }
                        }
                        description "IS-IS protocol level to which these attributes apply";
                    }

                    leaf oper-state {
                        type enumeration {
                            enum "normal"                       { value 1; }
                            enum "offset-applied"               { value 2; }
                        }
                        description "The value indicates the state of the link group at this IS-IS level.";
                    }

                    leaf oper-oper-members {
                        type uint32;
                        description
                            "The value indicates the operational value of the number of operational links below which the
                             metric of the member interfaces is increased by the configured offsets.";
                    }

                    leaf oper-revert-members {
                        type uint32;
                        description
                            "The value indicates the operational value of the minimum number of links that must be
                             operational after the offsets were applied in order for the metrics of
                             the member interfaces to be returned to normal.";
                    }

                    leaf members-count {
                        type uint32;
                        description
                            "The value indicates the number of interfaces that are a member of the
                             link group indicated by name at this IS-IS level.";
                    }

                    leaf active-members {
                        type uint32;
                        description
                            "The value indicates the number of active interfaces that are a member
                             of the link group indicated by name at this IS-IS level.";
                    }

                    list member {
                        key "interface-name";
                        description "Enter the member context";

                        leaf interface-name {
                            type leafref {
                                path "../../../../interface/interface-name";
                            }
                            description "The router interface name assigned to this link group.";
                        }

                        leaf oper-state {
                            type enumeration {
                                enum "up"                           { value 1; }
                                enum "down"                         { value 2; }
                                enum "bit-error-rate"               { value 3; }
                            }
                            description
                                "The value indicates the state of this interface at this IS-IS level associated
                                 with the link group indicated by name.";
                        }

                    } // list member

                } // list level

            } // list link-group

            list lfa-coverage {
                key "level-number family-coverage";
                description "Represents information on LFA coverage for various topologies of the system.";

                leaf level-number {
                    type enumeration {
                        enum "1"                            { value 1; }
                        enum "2"                            { value 2; }
                    }
                    description "IS-IS protocol level to which these attributes apply";
                }

                leaf family-coverage {
                    type enumeration {
                        enum "ipv4"                         { value 0; }
                        enum "ipv6"                         { value 1; }
                        enum "ipv4-mcast"                   { value 2; }
                        enum "ipv6-mcast"                   { value 3; }
                    }
                    description
                        "The value of the object tmnxIsisLfaFamilyCoverage specifies the
                         multi topology (MT's) for which LFA coverage has been computed.

                         Possible values are:

                         ipv4(0)      - indicates MT0 or standard topology
                         ipv6(1)      - indicates MT2 or IPv6 routing topology
                         ipv4-mcast(2) - indicates MT3 or IPv4 multicast routing topology
                         ipv6-mcast(3) - indicates MT4 or IPv6 multicast routing topology.";
                }

                container nodes {
                    description "LFA node coverage";

                    leaf covered {
                        type uint32;
                        description
                            "The value indicates in absolute numbers how much LFA coverage
                             is being obtained for the available routes.";
                    }

                    leaf total {
                        type uint32;
                        description
                            "The value indicates in absolute numbers how much LFA coverage
                             can be obtained for the available routes.";
                    }

                    leaf coverage {
                        type types-sros:percent;
                        description
                            "The value indicates how much LFA coverage is being obtained
                             for the set of available nodes.";
                    }

                } // container nodes

                container ipv4 {
                    description "LFA IPV4 coverage";

                    leaf covered {
                        type uint32;
                        description
                            "The value indicates in absolute numbers how much LFA coverage
                             is being obtained for the available routes.";
                    }

                    leaf total {
                        type uint32;
                        description
                            "The value indicates in absolute numbers how much LFA coverage
                             can be obtained for the available routes.";
                    }

                    leaf coverage {
                        type types-sros:percent;
                        description
                            "The value indicates how much LFA coverage is being obtained
                             for the set of available nodes.";
                    }

                } // container ipv4

                container ipv6 {
                    description "LFA IPV6 coverage";

                    leaf covered {
                        type uint32;
                        description
                            "The value indicates in absolute numbers how much LFA coverage
                             is being obtained for the available routes.";
                    }

                    leaf total {
                        type uint32;
                        description
                            "The value indicates in absolute numbers how much LFA coverage
                             can be obtained for the available routes.";
                    }

                    leaf coverage {
                        type types-sros:percent;
                        description
                            "The value indicates how much LFA coverage is being obtained
                             for the set of available nodes.";
                    }

                } // container ipv6

            } // list lfa-coverage

            list database {
                key "level-number lsp-id";
                description "Represents an LSP in the LSP database.";

                leaf level-number {
                    type enumeration {
                        enum "1"                            { value 1; }
                        enum "2"                            { value 2; }
                    }
                    description "IS-IS protocol level to which these attributes apply";
                }

                leaf lsp-id {
                    type types-isis:lsp-id;
                    description
                        "The value specifies the LSP Id and is given in the format as 6 octets of adjacency system-id followed by
                         1 octet Lan-ID and 1 octet LSP Number.";
                }

                leaf seq {
                    type yang:counter32;
                    description
                        "The value indicates the sequence number of
                         an LSP and is a four byte quantity that represents the version of an LSP.

                         The higher the sequence number, the more up to date the information.

                         The sequence number is always incremented by the system that originated
                         the LSP and ensures that there is only one version of that LSP in the
                         entire network.";
                }

                leaf checksum {
                    type int32 {
                        range "0..65535";
                    }
                    description
                        "The value indicates the checksum of
                         contents of LSP from the SourceID field in the LSP till the end.

                         The checksum is computed using the Fletcher checksum algorithm. ";
                }

                leaf zero-rtl {
                    type boolean;
                    description
                        "The value indicates the LSP state if
                         it has once reached zero remaining lifetime.

                         If this object is 'true' then the object lifetime-remain will
                         maintain the time remaining after which this LSP will be discarded.";
                }

                leaf lifetime-remain {
                    type int32 {
                        range "0..65535";
                    }
                    units "seconds";
                    description
                        "The value indicates the
                         Remaining lifetime of this LSP and is a decrementing counter that
                         decrements in seconds starting from the value as received in the
                         LSP if not self-originated OR from lsp-life-time for self
                         originated LSPs.

                         When the remaining lifetime becomes zero, the contents of the LSP
                         should not be considered for SPF calculation.";
                }

                leaf version {
                    type int32;
                    description
                        "The value indicates the version of
                         the ISIS protocol that has generated the LSP";
                }

                leaf pkt-type {
                    type int32;
                    description
                        "The value indicates the packet type
                         for instance Hello PDUs, LSPs, CSNPs OR PSNPs at both IS-IS protocol
                         levels i.e. L1 and L2 as maintained in of the object packet-type.";
                }

                leaf pkt-version {
                    type int32;
                    description
                        "The value indicates the version of
                         the ISIS protocol that has generated the Packet.";
                }

                leaf attributes {
                    type int32;
                    description
                        "The value indicates the attributes
                         associated with the LSP and these include the attached bit,
                         overload bit, IS type of the system originating the LSP and the
                         partition repair capability.

                         The attached bit and the overload bit are of significance only when
                         present in the LSP numbered zero and should be ignored on receipt in
                         any other LSP.";
                }

                leaf max-area {
                    type int32;
                    description
                        "The value indicates the maximum number
                         of areas supported by the originator of the LSP.

                         A value of 0 indicates a default of 3 areas. ";
                }

                leaf alloc-len {
                    type int32;
                    description
                        "The value indicates the length
                         allocated for the LSP to be stored.";
                }

                leaf system-id {
                    type types-igp:system-id;
                    description "The value indicates the system-id as part of lsp-id used by the originator.";
                }

                leaf system-id-len {
                    type int32;
                    description
                        "The value indicates the length of
                         the system-id as used by the originator.";
                }

                leaf used-len {
                    type int32;
                    description
                        "The value indicates the used length
                         for the LSP.

                         For an LSP that is not self originated, the used length is always equal
                         to alloc-len for self originated LSPs, the used length is
                         less than or equal to alloc-len.";
                }

                leaf value {
                    type string {
                        length "27..9190";
                    }
                    description "Contents of the LSP.";
                }

            } // list database

            list capabilities {
                key "level-number lsp-id";
                description "Represents an LSP in the LSP database.";

                leaf level-number {
                    type enumeration {
                        enum "1"                            { value 1; }
                        enum "2"                            { value 2; }
                    }
                    description "IS-IS protocol level to which these attributes apply";
                }

                leaf lsp-id {
                    type leafref {
                        path "../../../../../router/isis/database/lsp-id";
                    }
                    description
                        "The value specifies the LSP Id and is given in the format as 6 octets of adjacency system-id followed by
                         1 octet Lan-ID and 1 octet LSP Number.";
                }

                leaf tlv-buffer {
                    type string {
                        length "0..9190";
                    }
                    description "The capability TLV.";
                }

                leaf router-id {
                    type types-sros:ipv4-address;
                    description "IPv4 router-id.";
                }

                leaf s-flag {
                    type boolean;
                    description " Value of the S-flag in the router capability TLV.";
                }

                leaf d-flag {
                    type boolean;
                    description " Value of the D-flag in the router capability TLV.";
                }

            } // list capabilities

            list hostname {
                key "system-id";
                description "Stores the mapping of a system-id to a hostname.";

                leaf system-id {
                    type types-igp:system-id;
                    description "Specifies the ID for this instance of the Integrated IS-IS protocol.";
                }

                leaf host-name {
                    type types-sros:display-string;
                    description "The value indicates the mapping hostname for the corresponding system-id.";
                }

            } // list hostname

            list route {
                key "multi-topology-id destination";
                description "Stores a route for a given instance of the IS-IS protocol for a specific multi topology id.";

                leaf multi-topology-id {
                    type uint32;
                    description
                        "The value specifies the multi-topology id number for the path.

                         If multi-topology is not supported for the path then
                         the value should be 0.";
                }

                leaf destination {
                    type types-sros:ip-prefix;
                    description "The value specifies the IP address and mask of the route destination.";
                }

                leaf level {
                    type types-isis:level;
                    description "The value indicates the IS-IS Level at which the prefix was learned.";
                }

                leaf status {
                    type enumeration {
                        enum "active"                       { value 0; }
                        enum "rtm-add-failed"               { value 1; }
                        enum "fib-add-failed"               { value 2; }
                    }
                    description "The value indicates the reason why a route is not active.";
                }

                leaf metric {
                    type uint32;
                    description
                        "The value indicates the routing metric for a backup route.

                         The semantics of this metric are determined by the routing-protocol
                         specified in the route's ipCidrRouteProto value.

                         The value is only valid when backup-flags has a value of 'has-lfa'.";
                }

                leaf type {
                    type enumeration {
                        enum "internal"                     { value 1; }
                        enum "external"                     { value 2; }
                    }
                    description "The value indicates the type of route represented by this row entry.";
                }

                leaf tag {
                    type uint32;
                    description
                        "The value indicates a 32-bit integer route tag for this route.

                         A value of 0 indicates that the tag has not been set.";
                }

                container backup {
                    description "Backup route";

                    leaf next-hop-ip {
                        type types-sros:ip-address-with-zone;
                        description "The value specifies the IP address of the next hop for this route.";
                    }

                    leaf next-hop-type {
                        type types-isis:cidr-next-hop-type;
                        description "The value indicates the type of next hop for this backup route.";
                    }

                    leaf next-hop-owner {
                        type types-isis:cidr-next-hop-owner;
                        description "The value indicates the owner of next hop for this backup route.";
                    }

                    leaf next-hop-tunnel-id {
                        type uint32;
                        description
                            "The value indicates the auxiliary information, for next hop owner as indicated by
                             backup-next-hop-owner.

                             The value of indicates the tunnel-id existing for this backup next hop type and owner.";
                    }

                    leaf type {
                        type enumeration {
                            enum "node-protection"              { value 1; }
                            enum "link-protection"              { value 2; }
                        }
                        description
                            "The value indicates the type of protection used by the backup next-hop.

                             The value 'not-applicable' indicates that the backup next hop type
                             is not applicable
                             the value 'node-protection' indicates that the backup next hop uses a
                             node-protection mechanism
                             the value 'link-protection' indicates that the backup next hop uses
                             link-protection mechanism.";
                    }

                    leaf metric {
                        type uint32;
                        description
                            "The value indicates the routing metric for a backup route.

                             The semantics of this metric are determined by the routing-protocol
                             specified in the route's ipCidrRouteProto value.

                             The value is only valid when backup-flags has a value of 'has-lfa'.";
                    }

                    leaf flags {
                        type enumeration {
                            enum "none"                         { value 0; }
                            enum "has-lfa"                      { value 1; }
                        }
                        description
                            "The value indicates the presence or absence of LFA next-hops.

                             The value 'none' indicates that no next hop is present
                             the value 'has-lfa' indicates that an LFA next hop is present in addition
                             to the regular next-hop.";
                    }

                } // container backup

                list next-hop {
                    key "ecmp-index";
                    description "Stores a next hop for a given instance of the IS-IS protocol for a specific multi topology id and route destination.";

                    leaf ecmp-index {
                        type types-router:ip-ecmp;
                        description "ECMP index of this route next-hop.";
                    }

                    leaf next-hop-ip {
                        type types-sros:ip-address-with-zone;
                        description "The value specifies the IP address of the next hop for this route.";
                    }

                    leaf next-hop-type {
                        type types-isis:cidr-next-hop-type;
                        description "The value indicates the type of next hop for this backup route.";
                    }

                    leaf next-hop-owner {
                        type types-isis:cidr-next-hop-owner;
                        description "The value indicates the owner of next hop for this backup route.";
                    }

                    leaf next-hop-tunnel-id {
                        type uint32;
                        description
                            "The value indicates the auxiliary information, for next hop owner as indicated by
                             backup-next-hop-owner.

                             The value of indicates the tunnel-id existing for this backup next hop type and owner.";
                    }

                    leaf spf-version {
                        type yang:counter32;
                        description "The value indicates the run of SPF calculation in which this route was selected.";
                    }

                    leaf next-hop-system-id {
                        type types-igp:system-id;
                        description
                            "The value indicates the system-id of the next hop IS through
                             which this route is reachable.";
                    }

                } // list next-hop

            } // list route

            list spf-log {
                key "time-stamp";
                description
                    "Each entry maintains log information about a specific SPF run
                     made on a particular IS-IS protocol instance.";

                leaf time-stamp {
                    type yang:timeticks;
                    description "The value specifies the time (in centiseconds) since system-up when the SPF was ran.";
                }

                leaf duration {
                    type yang:timeticks;
                    description "The value indicates the time (in centiseconds) required to complete the SPF run.";
                }

                leaf l1-nodes {
                    type uint32;
                    description "The value indicates the number of L1 nodes involved in the SPF run.";
                }

                leaf l2-nodes {
                    type uint32;
                    description "The value indicates the number of L2 nodes involved in the SPF run.";
                }

                leaf trigger-lsp-id {
                    type types-isis:lsp-id;
                    description "The value indicates the LSP-Id of the last LSP processed before the SPF run.";
                }

                leaf event-count {
                    type uint32;
                    description "The value indicates the number of SPF events that triggered the SPF calculation.";
                }

                leaf type {
                    type enumeration {
                        enum "regular"                      { value 0; }
                        enum "lfa"                          { value 1; }
                        enum "partial-spf"                  { value 2; }
                        enum "partial-lfa"                  { value 3; }
                        enum "remote-lfa"                   { value 4; }
                        enum "ti-lfa"                       { value 5; }
                    }
                    description "The value indicates the type of SPF calculation.";
                }

                leaf trigger-reason {
                    type bits {
                        bit new-adjacency                  { position 0; }
                        bit new-lsp                        { position 1; }
                        bit new-area                       { position 2; }
                        bit reach                          { position 3; }
                        bit ecmp-changed                   { position 4; }
                        bit new-metric                     { position 5; }
                        bit te-changed                     { position 6; }
                        bit restart                        { position 7; }
                        bit lsp-expired                    { position 8; }
                        bit lsp-db-changed                 { position 9; }
                        bit lsp-changed                    { position 10; }
                        bit new-preference                 { position 11; }
                        bit new-nlp-id                     { position 12; }
                        bit manual-run                     { position 13; }
                        bit admin-tag-changed              { position 14; }
                        bit tunnel-changed                 { position 15; }
                        bit throttle-end                   { position 16; }
                        bit lfa-changed                    { position 17; }
                    }
                    description
                        "The value indicates the reasons that triggered this SPF run.

                         new-sdjacency (0)      - a new adjacency was formed.
                         new-ldp (1)            - a new LSP was received.
                         new-srea (2)           - a new area was joined.
                         reach (3)              - a new prefix can be reached.
                         ecmp-changed (4)       - the number of ecmp routes to a destination changed.
                         new-metric (5)         - a route has a new metric.
                         te-changed (6)         - traffic engineering changed.
                         restart (7)            - the IS-IS router was restarted.
                         lsp-expired (8)        - an LSP expired.
                         lsp-db-changed (9)     - the IS-IS LSP database was cleared.
                         lsp-changed (10)       - an LSP changed.
                         new-preference (11)    - a route preference changed.
                         new-nlp-id (12)        - a Network Layer Protocol was added to the
                                                  IS-IS router protocol set.
                         manual-run (13)        - Manual request issued.
                         admin-tag-changed (14) - admin tag has changed.
                         tunnel-changed (15)    - list of tunnels has changed.
                         throttle-end (16)      - throttling of SPF ended.
                         lfa-changed (17)       - lfa changed.";
                }

            } // list spf-log

            list received-area-address {
                key "area-address";
                description
                    "Each entry contains one area address reported in a
                     Level 1 LSP received by this instance of the protocol.";

                leaf area-address {
                    type types-isis:area-address;
                    description
                        "An area address reported in a Level 1 LSP received by
                         this instance of the protocol.";
                }

            } // list received-area-address

            list topology {
                key "level-number multi-topology-id path-id";
                description "Represents the ISIS path for an instance, level, multi topology id and path identifier";

                leaf level-number {
                    type enumeration {
                        enum "1"                            { value 1; }
                        enum "2"                            { value 2; }
                    }
                    description "IS-IS protocol level to which these attributes apply";
                }

                leaf multi-topology-id {
                    type uint32;
                    description
                        "The value specifies the multi-topology id number for the path.

                         If multi-topology is not supported for the path then
                         the value should be 0.";
                }

                leaf path-id {
                    type string {
                        length "14";
                    }
                    description
                        "The value specifies the path identifier
                         and has first 6 octets as the system-id followed by one octet
                         of the Lan-ID.";
                }

                leaf metric {
                    type uint32;
                    description
                        "The value indicates the metric
                         assigned to this path entry after SPF calculations.

                         The lower the metric value, the shorter the path and hence more
                         preferred by the protocol.";
                }

                leaf route-type {
                    type enumeration {
                        enum "spf"                          { value 0; }
                        enum "lfa"                          { value 1; }
                    }
                    description "The value indicates whether a backup route exists for this row entry.";
                }

                container lfa {
                    description "Loop free alternative path";

                    leaf type {
                        type enumeration {
                            enum "none"                         { value 0; }
                            enum "node-link"                    { value 1; }
                            enum "path-link"                    { value 2; }
                        }
                        description "The value indicates the type of route represented by this row entry.";
                    }

                    leaf interface {
                        type types-sros:interface-name;
                        description
                            "The value indicates the
                             loopfree-alternate ifIndex of the outgoing interface for the path.";
                    }

                    leaf next-hop {
                        type types-igp:system-id;
                        description
                            "The value indicates the
                             loopfree-alternate next hop and is referenced by the system-id.";
                    }

                    leaf metric {
                        type uint32;
                        description
                            "The value indicates the metric assigned to this entry which are a result
                             of loopfree-alternate calculations.

                             The lower the metric value, the shorter is the path and hence more
                             preferred by the protocol.";
                    }

                } // container lfa

                list next-hop {
                    key "ecmp-index";
                    description "Stores a next hop for a given ISIS path for an instance, level, multi topology id and path identifier";

                    leaf ecmp-index {
                        type types-router:ip-ecmp;
                        description "ECMP index of this route next-hop.";
                    }

                    leaf interface {
                        type types-sros:interface-name;
                        description "The value specifies the outgoing interface for the path.";
                    }

                    leaf next-hop-system-id {
                        type types-igp:system-id;
                        description
                            "The value specifies the system-id of the next hop and is used to reference the
                             next hop for this route.";
                    }

                    leaf snpa {
                        type types-isis:snpa-address;
                        description "The value indicates the subnet point of attachment for this path.";
                    }

                } // list next-hop

            } // list topology

        } // list isis

    } // grouping state-svc-vprn-isis

}
