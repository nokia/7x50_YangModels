submodule nokia-conf-router-origin-validation {

    yang-version "1.1";

    belongs-to nokia-conf { prefix "conf"; }

    import ietf-inet-types                { prefix "inet"; }
    import nokia-sros-yang-extensions     { prefix "sros-ext"; }
    import nokia-types-sros               { prefix "types-sros"; }


    sros-ext:sros-major-release "rel19";

    organization "Nokia";

    contact
        "Nokia SR OS Support
         Web: <http://www.nokia.com>";

    description
        "Nokia YANG Data model to configure origin-validation on SR OS based routers.

         Copyright 2016 Nokia. All rights reserved. Reproduction of this document
         is authorized on the condition that the foregoing copyright notice is included.

         This nokia-conf-router-origin-validation YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-04-12";

    grouping conf-router-origin-validation {
        container origin-validation {
            when "../router-name = 'Base' or ../router-name = 'management'";
            description "Origin validation.";

            list static-entry {
                key "ip-prefix upto origin-as";
                description "Static entry for this router instance.";

                leaf ip-prefix {
                    type types-sros:ip-prefix;
                    description "IP address prefix to match for the origin validation.";
                }

                leaf upto {
                    type uint32 {
                        range "1..128";
                    }
                    description "The max value of the prefix length for ip-prefix address.";
                }

                leaf origin-as {
                    type inet:as-number;
                    description "The autonomous system number to be advertised to this peer.";
                }

                leaf valid {
                    type boolean;
                    default "true";
                    description
                        "Specifies whether the route entry corresponding to the autonomous
                         number is valid (true) or invalid (false).";
                }

            } // list static-entry

            list rpki-session {
                key "ip-address";
                description "Rpki session for origin-validation.";

                leaf ip-address {
                    type types-sros:ip-address;
                    description "IPv4, IPv6 or link local address of a local cache server.";
                }

                leaf connect-retry {
                    type uint32 {
                        range "1..65535";
                    }
                    units "seconds";
                    default "120";
                    description "RPKI Connect Retry timer value (in seconds).";
                }

                leaf description {
                    type types-sros:description;
                    description "A textual description stored in the configuration file.";
                }

                leaf local-address {
                    type types-sros:ip-address;
                    sros-ext:auto-restart-to-modify;
                    description "Address of the local end of the RPKI session.";
                }

                leaf port {
                    type uint32 {
                        range "0..65535";
                    }
                    sros-ext:auto-restart-to-modify;
                    default "323";
                    description "Destination port number to be used to connect the cache server.";
                }

                leaf admin-state {
                    type types-sros:admin-state;
                    default "disable";
                    description "Administratively enable/disable RPKI session.";
                }

                leaf stale-time {
                    type uint32 {
                        range "60..3600";
                    }
                    units "seconds";
                    default "3600";
                    description
                        "Specifies the maximum length of time that prefix origin records learned
                         from the cache server remain valid after the session with the cache server goes down.";
                }

                container refresh-time {
                    description "RPKI refresh and hold time.";

                    leaf value {
                        type uint32 {
                            range "30..32767";
                        }
                        units "seconds";
                        default "300";
                        description "Triggers the sending of periodic Serial Query PDUs for purposes of liveness detection.";
                    }

                    leaf hold-time {
                        type uint32 {
                            range "60..65535";
                        }
                        units "seconds";
                        default "600";
                        description
                            "Specifies the length of time in seconds that the session is to be considered UP
                             without any indication that the cache server is alive and reachable.";
                    }

                } // container refresh-time

            } // list rpki-session

        } // container origin-validation

    } // grouping conf-router-origin-validation

}
