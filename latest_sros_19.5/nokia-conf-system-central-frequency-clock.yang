submodule nokia-conf-system-central-frequency-clock {

    yang-version "1.1";

    belongs-to nokia-conf { prefix "conf"; }

    import nokia-sros-yang-extensions     { prefix "sros-ext"; }
    import nokia-types-sros               { prefix "types-sros"; }
    import nokia-types-system             { prefix "types-system"; }

    include nokia-conf-groups;
    include nokia-conf-port;

    sros-ext:sros-major-release "rel19";

    organization "Nokia";

    contact
        "Nokia SR OS Support
         Web: <http://www.nokia.com>";

    description
        "Nokia YANG Data model to configure system central-frequency-clock parameters on SR OS based routers.

         Copyright 2016 Nokia. All rights reserved. Reproduction of this document
         is authorized on the condition that the foregoing copyright notice is included.

         This nokia-conf-system-central-frequency-clock YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-04-05";

    grouping conf-system-central-frequency-clock {
        container central-frequency-clock {
            description "Enter the central-frequency-clock context";

            leaf ql-minimum {
                type types-system:ref-ssm-quality-level-override;
                default "unused";
                description "Minimum acceptable QL value for signal to be considered for selection by system timing module";
            }

            leaf ql-selection {
                type boolean;
                default "false";
                description "System timing reference and BITS output timing reference";
            }

            leaf revert {
                type boolean;
                default "false";
                description "Higher priority re-validated reference source to revert";
            }

            leaf wait-to-restore {
                type uint32 {
                    range "1..12";
                }
                units "minutes";
                description "Time for failed input reference to be valid before using it for BITS output or central clock input";
            }

            container bits {
                description "Enter the bits context";

                leaf interface-type {
                    type types-system:bits-if-type;
                    default "ds1-esf";
                    description "Interface type of the BITS timing reference";
                }

                leaf ql-override {
                    type types-system:ssm-quality-level-override;
                    default "unused";
                    description "Quality level of a timing reference that overrides any value provided by the reference's SSM process";
                }

                leaf ssm-bit {
                    when "../interface-type = 'e1-pcm30crc' or ../interface-type = 'e1-pcm31crc'";
                    type uint32 {
                        range "4..8";
                    }
                    default "8";
                    description "SSM information conveyed by sa-bit";
                }

                container input {
                    description "Enter the input context";

                    leaf admin-state {
                        type types-sros:admin-state;
                        default "disable";
                        description "Administrative state of BITS input timing reference";
                    }

                } // container input

                container output {
                    description "Enter the output context";

                    leaf line-length {
                        type enumeration {
                            enum "length-not-applicable"        { value 0; }
                            enum "110"                          { value 1; }
                            enum "220"                          { value 2; }
                            enum "330"                          { value 3; }
                            enum "440"                          { value 4; }
                            enum "550"                          { value 5; }
                            enum "660"                          { value 6; }
                        }
                        description "Line length for the BITS output timing reference";
                    }

                    leaf ql-minimum {
                        type types-system:ref-ssm-quality-level-override;
                        default "unused";
                        description "Minimum acceptable QL value for signal to be considered for selection for the BITSout port";
                    }

                    leaf source {
                        type types-system:bits-out-source;
                        default "line-ref";
                        description "Source of the BITS output timing reference";
                    }

                    leaf squelch {
                        type boolean;
                        default "false";
                        description "Squelch the signal of the BITS output timing reference";
                    }

                    leaf admin-state {
                        type types-sros:admin-state;
                        description "Administrative state of the BITS output timing reference";
                    }

                } // container output

            } // container bits

            container ptp {
                description "Enter the ptp context";

                leaf admin-state {
                    type types-sros:admin-state;
                    default "disable";
                    description "Administrative state of the PTP timing reference";
                }

            } // container ptp

            container ref-order {
                description "Enter the ref-order context";

                leaf first {
                    type types-system:sets-ref-source;
                    description "Highly preferred timing reference source for the synchronous equipment timing subsystem";
                }

                leaf second {
                    type types-system:sets-ref-source;
                    description "Second preferred timing reference source for the synchronous equipment timing subsystem";
                }

                leaf third {
                    type types-system:sets-ref-source;
                    description "Third preferred timing reference source for the synchronous equipment timing subsystem";
                }

                leaf fourth {
                    type types-system:sets-ref-source;
                    description "Fourth preferred timing reference source for the synchronous equipment timing subsystem";
                }

            } // container ref-order

            container ref1 {
                description "Enter the ref1 context";

                leaf ql-override {
                    type types-system:ref-ssm-quality-level-override;
                    default "unused";
                    description "Quality level of a timing reference that overrides any value provided by the reference's SSM process";
                }

                leaf admin-state {
                    type types-sros:admin-state;
                    default "disable";
                    description "Administrative state of the first timing reference";
                }

                leaf source-port {
                    type leafref {
                        path "../../../../port/port-id";
                    }
                    description "Source port for the first timing reference";
                }

            } // container ref1

            container ref2 {
                description "Enter the ref2 context";

                leaf ql-override {
                    type types-system:ref-ssm-quality-level-override;
                    default "unused";
                    description "Quality level of a timing reference that overrides any value provided by the reference's SSM process";
                }

                leaf admin-state {
                    type types-sros:admin-state;
                    default "disable";
                    description "Administrative state of the second timing reference";
                }

                leaf source-port {
                    type leafref {
                        path "../../../../port/port-id";
                    }
                    description "Source port for the first timing reference";
                }

            } // container ref2

        } // container central-frequency-clock

    } // grouping conf-system-central-frequency-clock

}
