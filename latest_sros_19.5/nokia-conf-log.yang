submodule nokia-conf-log {

    yang-version "1.1";

    belongs-to nokia-conf { prefix "conf"; }

    import nokia-sros-yang-extensions     { prefix "sros-ext"; }
    import nokia-types-log                { prefix "types-log"; }
    import nokia-types-qos                { prefix "types-qos"; }
    import nokia-types-sros               { prefix "types-sros"; }

    include nokia-conf-groups;
    include nokia-conf-python;
    include nokia-conf-system;
    include nokia-conf-system-script-control;

    sros-ext:sros-major-release "rel19";

    organization "Nokia";

    contact
        "Nokia SR OS Support
         Web: <http://www.nokia.com>";

    description
        "Nokia YANG Data model to configure event stream logging on SR OS based routers.

         Copyright 2016 Nokia. All rights reserved. Reproduction of this document
         is authorized on the condition that the foregoing copyright notice is included.

         This nokia-conf-log YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-04-19";

    grouping conf-log {
        container log {
            description "Enter the log context";

            leaf event-damping {
                type boolean;
                default "true";
                description "Allow event damping algorithm to suppress QoS or filter change events";
            }

            list accounting-policy {
                key "policy-id";
                description "Enter the accounting-policy context";

                leaf policy-id {
                    type types-log:log-policy-id;
                    description "Accounting policy unique ID";
                }

                leaf admin-state {
                    type types-sros:admin-state;
                    default "disable";
                    description "Administrative state of this policy";
                }

                leaf description {
                    type types-sros:description;
                    description "Text description";
                }

                leaf collection-interval {
                    type int32 {
                        range "1..120";
                    }
                    units "minutes";
                    description "Accounting collection interval";
                }

                leaf default {
                    type boolean;
                    sros-ext:auto-restart-to-modify;
                    default "false";
                    description "Default accounting policy for all objects that do not have an accounting policy";
                }

                leaf include-system-info {
                    type boolean;
                    default "false";
                    description "Include system information in accounting policy records";
                }

                leaf record {
                    type types-log:accounting-record-type;
                    sros-ext:immutable;
                    sros-ext:auto-restart-to-modify;
                    description "Accounting record type that is forwarded to configured accounting file";
                }

                container custom-record {
                    description "Enter the custom-record context";

                    leaf significant-change {
                        type uint32 {
                            range "0..max";
                        }
                        description "Significant change required to generate the record";
                    }

                    container aa-specific {
                        description "Enter the aa-specific context";

                        container sub-attributes {
                            description "Enter the sub-attributes context";

                            leaf app-service-options {
                                type boolean;
                                default "false";
                                description "Include application service options";
                            }

                        } // container sub-attributes

                        container sub-counters {
                            description "Enter the sub-counters context";

                            leaf long-duration-flow-count {
                                type boolean;
                                default "false";
                                description "Include the long duration flow count";
                            }

                            leaf medium-duration-flow-count {
                                type boolean;
                                default "false";
                                description "Include the medium duration flow";
                            }

                            leaf short-duration-flow-count {
                                type boolean;
                                default "false";
                                description "Include the short duration flow count";
                            }

                            leaf total-flow-duration {
                                type boolean;
                                default "false";
                                description "Include the total flow duration count";
                            }

                            leaf total-flows-completed-count {
                                type boolean;
                                default "false";
                                description "Include the total of completed flows count";
                            }

                        } // container sub-counters

                        container from-sub-counters {
                            description "Enter the from-sub-counters context";

                            leaf flows-active-count {
                                type boolean;
                                default "false";
                                description "Include the active flows";
                            }

                            leaf flows-admitted-count {
                                type boolean;
                                default "false";
                                description "Include the admitted flows";
                            }

                            leaf flows-denied-count {
                                type boolean;
                                default "false";
                                description "Include the denied flows";
                            }

                            leaf forwarding-class {
                                type boolean;
                                default "false";
                                description "Include forwarding class";
                            }

                            leaf max-throughput-octet-count {
                                type boolean;
                                default "false";
                                description "Include maximum throughput as measured in octet count";
                            }

                            leaf max-throughput-packet-count {
                                type boolean;
                                default "false";
                                description "Include maximum throughput as measured in packet count";
                            }

                            leaf max-throughput-timestamp {
                                type boolean;
                                default "false";
                                description "Include timestamp of the maximum throughput";
                            }

                            leaf octets-admitted-count {
                                type boolean;
                                default "false";
                                description "Include the admitted octets count";
                            }

                            leaf octets-denied-count {
                                type boolean;
                                default "false";
                                description "Include the denied octets count";
                            }

                            leaf packets-admitted-count {
                                type boolean;
                                default "false";
                                description "Include the admitted packets count";
                            }

                            leaf packets-denied-count {
                                type boolean;
                                default "false";
                                description "Include the denied packets count";
                            }

                        } // container from-sub-counters

                        container to-sub-counters {
                            description "Enter the to-sub-counters context";

                            leaf flows-active-count {
                                type boolean;
                                default "false";
                                description "Include the active flows";
                            }

                            leaf flows-admitted-count {
                                type boolean;
                                default "false";
                                description "Include the admitted flows";
                            }

                            leaf flows-denied-count {
                                type boolean;
                                default "false";
                                description "Include the denied flows";
                            }

                            leaf forwarding-class {
                                type boolean;
                                default "false";
                                description "Include forwarding class";
                            }

                            leaf max-throughput-octet-count {
                                type boolean;
                                default "false";
                                description "Include maximum throughput as measured in octet count";
                            }

                            leaf max-throughput-packet-count {
                                type boolean;
                                default "false";
                                description "Include maximum throughput as measured in packet count";
                            }

                            leaf max-throughput-timestamp {
                                type boolean;
                                default "false";
                                description "Include timestamp of the maximum throughput";
                            }

                            leaf octets-admitted-count {
                                type boolean;
                                default "false";
                                description "Include the admitted octets count";
                            }

                            leaf octets-denied-count {
                                type boolean;
                                default "false";
                                description "Include the denied octets count";
                            }

                            leaf packets-admitted-count {
                                type boolean;
                                default "false";
                                description "Include the admitted packets count";
                            }

                            leaf packets-denied-count {
                                type boolean;
                                default "false";
                                description "Include the denied packets count";
                            }

                        } // container to-sub-counters

                    } // container aa-specific

                    list override-counter {
                        key "id";
                        description "Configure an override counter.";

                        leaf id {
                            type uint32 {
                                range "1..8";
                            }
                            description "Identification of a custom-record HSMDA override counter";
                        }

                        container e-counters {
                            description "Configure egress counters for this override.";

                            leaf in-profile-octets-discarded-count {
                                type boolean;
                                default "false";
                                description "Include the in-profile octets discarded count";
                            }

                            leaf in-profile-octets-forwarded-count {
                                type boolean;
                                default "false";
                                description "Include the in-profile octets forwarded count";
                            }

                            leaf in-profile-packets-discarded-count {
                                type boolean;
                                default "false";
                                description "Include the in-profile packets discarded count";
                            }

                            leaf in-profile-packets-forwarded-count {
                                type boolean;
                                default "false";
                                description "Include the in-profile packets forwarded count";
                            }

                            leaf out-profile-octets-discarded-count {
                                type boolean;
                                default "false";
                                description "Include the out-profile octets discarded count";
                            }

                            leaf out-profile-octets-forwarded-count {
                                type boolean;
                                default "false";
                                description "Include the out-of-profile octets forwarded count";
                            }

                            leaf out-profile-packets-discarded-count {
                                type boolean;
                                default "false";
                                description "Include the out-profile packets discarded count";
                            }

                            leaf out-profile-packets-forwarded-count {
                                type boolean;
                                default "false";
                                description "Include the out-of-profile packets forwarded count";
                            }

                        } // container e-counters

                        container i-counters {
                            description "Configure ingress counters for this override.";

                            leaf all-octets-offered-count {
                                type boolean;
                                default "false";
                                description "Include the all octets offered count";
                            }

                            leaf all-packets-offered-count {
                                type boolean;
                                default "false";
                                description "Include all packets offered count";
                            }

                            leaf high-octets-discarded-count {
                                type boolean;
                                default "false";
                                description "Include the high octets discarded count";
                            }

                            leaf high-packets-discarded-count {
                                type boolean;
                                default "false";
                                description "Include the high packets discarded count";
                            }

                            leaf in-profile-octets-forwarded-count {
                                type boolean;
                                default "false";
                                description "Include the in-profile octets forwarded count";
                            }

                            leaf in-profile-packets-forwarded-count {
                                type boolean;
                                default "false";
                                description "Include the in-profile packets forwarded count";
                            }

                            leaf low-octets-discarded-count {
                                type boolean;
                                default "false";
                                description "Include the low octets discarded count";
                            }

                            leaf low-packets-discarded-count {
                                type boolean;
                                default "false";
                                description "Include the low packets discarded count";
                            }

                            leaf out-profile-octets-forwarded-count {
                                type boolean;
                                default "false";
                                description "Include the out-of-profile octets forwarded count";
                            }

                            leaf out-profile-packets-forwarded-count {
                                type boolean;
                                default "false";
                                description "Include the out-of-profile packets forwarded count";
                            }

                        } // container i-counters

                    } // list override-counter

                    list queue {
                        key "id";
                        description "Enter the queue context";

                        leaf id {
                            type uint32 {
                                range "1..32";
                            }
                            description "Custom record queue ID";
                        }

                        container e-counters {
                            description "Enter the e-counters context";

                            leaf in-profile-octets-discarded-count {
                                type boolean;
                                default "false";
                                description "Include the in-profile octets discarded count";
                            }

                            leaf in-profile-octets-forwarded-count {
                                type boolean;
                                default "false";
                                description "Include the in-profile octets forwarded count";
                            }

                            leaf in-profile-packets-discarded-count {
                                type boolean;
                                default "false";
                                description "Include the in-profile packets discarded count";
                            }

                            leaf in-profile-packets-forwarded-count {
                                type boolean;
                                default "false";
                                description "Include the in-profile packets forwarded count";
                            }

                            leaf out-profile-octets-discarded-count {
                                type boolean;
                                default "false";
                                description "Include the out-profile octets discarded count";
                            }

                            leaf out-profile-octets-forwarded-count {
                                type boolean;
                                default "false";
                                description "Include the out-of-profile octets forwarded count";
                            }

                            leaf out-profile-packets-discarded-count {
                                type boolean;
                                default "false";
                                description "Include the out-profile packets discarded count";
                            }

                            leaf out-profile-packets-forwarded-count {
                                type boolean;
                                default "false";
                                description "Include the out-of-profile packets forwarded count";
                            }

                        } // container e-counters

                        container i-counters {
                            description "Enter the i-counters context";

                            leaf all-octets-offered-count {
                                type boolean;
                                default "false";
                                description "Include the all octets offered count";
                            }

                            leaf all-packets-offered-count {
                                type boolean;
                                default "false";
                                description "Include all packets offered count";
                            }

                            leaf high-octets-discarded-count {
                                type boolean;
                                default "false";
                                description "Include the high octets discarded count";
                            }

                            leaf high-packets-discarded-count {
                                type boolean;
                                default "false";
                                description "Include the high packets discarded count";
                            }

                            leaf in-profile-octets-forwarded-count {
                                type boolean;
                                default "false";
                                description "Include the in-profile octets forwarded count";
                            }

                            leaf in-profile-packets-forwarded-count {
                                type boolean;
                                default "false";
                                description "Include the in-profile packets forwarded count";
                            }

                            leaf low-octets-discarded-count {
                                type boolean;
                                default "false";
                                description "Include the low octets discarded count";
                            }

                            leaf low-packets-discarded-count {
                                type boolean;
                                default "false";
                                description "Include the low packets discarded count";
                            }

                            leaf out-profile-octets-forwarded-count {
                                type boolean;
                                default "false";
                                description "Include the out-of-profile octets forwarded count";
                            }

                            leaf out-profile-packets-forwarded-count {
                                type boolean;
                                default "false";
                                description "Include the out-of-profile packets forwarded count";
                            }

                            leaf high-octets-offered-count {
                                type boolean;
                                default "false";
                                description "Include the high octets offered count";
                            }

                            leaf high-packets-offered-count {
                                type boolean;
                                default "false";
                                description "Include the high packets offered count";
                            }

                            leaf low-octets-offered-count {
                                type boolean;
                                default "false";
                                description "Include the low octets offered count";
                            }

                            leaf low-packets-offered-count {
                                type boolean;
                                default "false";
                                description "Include the low packets offered count";
                            }

                            leaf uncoloured-octets-offered-count {
                                type boolean;
                                default "false";
                                description "Include the uncolored octets offered count";
                            }

                            leaf uncoloured-packets-offered-count {
                                type boolean;
                                default "false";
                                description "Include the uncolored packets offered count";
                            }

                        } // container i-counters

                    } // list queue

                    container ref-aa-specific-counter {
                        description "Enter the ref-aa-specific-counter context";

                        leaf any {
                            type boolean;
                            default "false";
                            description "Report a change to any counter";
                        }

                    } // container ref-aa-specific-counter

                    container ref-override-counter {
                        description "Enter the ref-override-counter context";

                        choice counter {
                            case id {

                                leaf id {
                                    type leafref {
                                        path "../../override-counter/id";
                                    }
                                    description "Override counter identity";
                                }

                            }
                            case all {

                                leaf all {
                                    type empty;
                                    description "Override counters that are referenced";
                                }

                            }
                        }
                        container e-counters {
                            description "Enter the e-counters context";

                            leaf in-profile-octets-discarded-count {
                                type boolean;
                                default "false";
                                description "Include the in-profile octets discarded count";
                            }

                            leaf in-profile-octets-forwarded-count {
                                type boolean;
                                default "false";
                                description "Include the in-profile octets forwarded count";
                            }

                            leaf in-profile-packets-discarded-count {
                                type boolean;
                                default "false";
                                description "Include the in-profile packets discarded count";
                            }

                            leaf in-profile-packets-forwarded-count {
                                type boolean;
                                default "false";
                                description "Include the in-profile packets forwarded count";
                            }

                            leaf out-profile-octets-discarded-count {
                                type boolean;
                                default "false";
                                description "Include the out-profile octets discarded count";
                            }

                            leaf out-profile-octets-forwarded-count {
                                type boolean;
                                default "false";
                                description "Include the out-of-profile octets forwarded count";
                            }

                            leaf out-profile-packets-discarded-count {
                                type boolean;
                                default "false";
                                description "Include the out-profile packets discarded count";
                            }

                            leaf out-profile-packets-forwarded-count {
                                type boolean;
                                default "false";
                                description "Include the out-of-profile packets forwarded count";
                            }

                        } // container e-counters

                        container i-counters {
                            description "Enter the i-counters context";

                            leaf all-octets-offered-count {
                                type boolean;
                                default "false";
                                description "Include the all octets offered count";
                            }

                            leaf all-packets-offered-count {
                                type boolean;
                                default "false";
                                description "Include all packets offered count";
                            }

                            leaf high-octets-discarded-count {
                                type boolean;
                                default "false";
                                description "Include the high octets discarded count";
                            }

                            leaf high-packets-discarded-count {
                                type boolean;
                                default "false";
                                description "Include the high packets discarded count";
                            }

                            leaf in-profile-octets-forwarded-count {
                                type boolean;
                                default "false";
                                description "Include the in-profile octets forwarded count";
                            }

                            leaf in-profile-packets-forwarded-count {
                                type boolean;
                                default "false";
                                description "Include the in-profile packets forwarded count";
                            }

                            leaf low-octets-discarded-count {
                                type boolean;
                                default "false";
                                description "Include the low octets discarded count";
                            }

                            leaf low-packets-discarded-count {
                                type boolean;
                                default "false";
                                description "Include the low packets discarded count";
                            }

                            leaf out-profile-octets-forwarded-count {
                                type boolean;
                                default "false";
                                description "Include the out-of-profile octets forwarded count";
                            }

                            leaf out-profile-packets-forwarded-count {
                                type boolean;
                                default "false";
                                description "Include the out-of-profile packets forwarded count";
                            }

                        } // container i-counters

                    } // container ref-override-counter

                    container ref-queue {
                        description "Enter the ref-queue context";

                        choice queue {
                            case id {

                                leaf id {
                                    type leafref {
                                        path "../../queue/id";
                                    }
                                    description "Queue ID";
                                }

                            }
                            case all {

                                leaf all {
                                    type empty;
                                    description "All referenced queues";
                                }

                            }
                        }
                        container e-counters {
                            description "Enter the e-counters context";

                            leaf in-profile-octets-discarded-count {
                                type boolean;
                                default "false";
                                description "Include the in-profile octets discarded count";
                            }

                            leaf in-profile-octets-forwarded-count {
                                type boolean;
                                default "false";
                                description "Include the in-profile octets forwarded count";
                            }

                            leaf in-profile-packets-discarded-count {
                                type boolean;
                                default "false";
                                description "Include the in-profile packets discarded count";
                            }

                            leaf in-profile-packets-forwarded-count {
                                type boolean;
                                default "false";
                                description "Include the in-profile packets forwarded count";
                            }

                            leaf out-profile-octets-discarded-count {
                                type boolean;
                                default "false";
                                description "Include the out-profile octets discarded count";
                            }

                            leaf out-profile-octets-forwarded-count {
                                type boolean;
                                default "false";
                                description "Include the out-of-profile octets forwarded count";
                            }

                            leaf out-profile-packets-discarded-count {
                                type boolean;
                                default "false";
                                description "Include the out-profile packets discarded count";
                            }

                            leaf out-profile-packets-forwarded-count {
                                type boolean;
                                default "false";
                                description "Include the out-of-profile packets forwarded count";
                            }

                        } // container e-counters

                        container i-counters {
                            description "Enter the i-counters context";

                            leaf all-octets-offered-count {
                                type boolean;
                                default "false";
                                description "Include the all octets offered count";
                            }

                            leaf all-packets-offered-count {
                                type boolean;
                                default "false";
                                description "Include all packets offered count";
                            }

                            leaf high-octets-discarded-count {
                                type boolean;
                                default "false";
                                description "Include the high octets discarded count";
                            }

                            leaf high-packets-discarded-count {
                                type boolean;
                                default "false";
                                description "Include the high packets discarded count";
                            }

                            leaf in-profile-octets-forwarded-count {
                                type boolean;
                                default "false";
                                description "Include the in-profile octets forwarded count";
                            }

                            leaf in-profile-packets-forwarded-count {
                                type boolean;
                                default "false";
                                description "Include the in-profile packets forwarded count";
                            }

                            leaf low-octets-discarded-count {
                                type boolean;
                                default "false";
                                description "Include the low octets discarded count";
                            }

                            leaf low-packets-discarded-count {
                                type boolean;
                                default "false";
                                description "Include the low packets discarded count";
                            }

                            leaf out-profile-octets-forwarded-count {
                                type boolean;
                                default "false";
                                description "Include the out-of-profile octets forwarded count";
                            }

                            leaf out-profile-packets-forwarded-count {
                                type boolean;
                                default "false";
                                description "Include the out-of-profile packets forwarded count";
                            }

                            leaf high-octets-offered-count {
                                type boolean;
                                default "false";
                                description "Include the high octets offered count";
                            }

                            leaf high-packets-offered-count {
                                type boolean;
                                default "false";
                                description "Include the high packets offered count";
                            }

                            leaf low-octets-offered-count {
                                type boolean;
                                default "false";
                                description "Include the low octets offered count";
                            }

                            leaf low-packets-offered-count {
                                type boolean;
                                default "false";
                                description "Include the low packets offered count";
                            }

                            leaf uncoloured-octets-offered-count {
                                type boolean;
                                default "false";
                                description "Include the uncolored octets offered count";
                            }

                            leaf uncoloured-packets-offered-count {
                                type boolean;
                                default "false";
                                description "Include the uncolored packets offered count";
                            }

                        } // container i-counters

                    } // container ref-queue

                } // container custom-record

                container destination {
                    description "Enter the destination context";

                    choice destination {
                        case file {

                            leaf file {
                                type leafref {
                                    path "../../../file/file-id";
                                }
                                sros-ext:immutable;
                                sros-ext:auto-restart-to-modify;
                                description "Unique file identifier when creating a log or accounting file";
                            }

                        }
                        case null {

                            leaf null {
                                type empty;
                                sros-ext:immutable;
                                sros-ext:auto-restart-to-modify;
                                description "Destination not specified for records of an accounting policy.";
                            }

                        }
                    }
                } // container destination

            } // list accounting-policy

            container app-route-notifications {
                description "Enter the app-route-notifications context";

                leaf cold-start-wait {
                    type uint32 {
                        range "1..300";
                    }
                    description "Time delay before notifying specific CPM applications for available route";
                }

                leaf route-recovery-wait {
                    type uint32 {
                        range "1..100";
                    }
                    description "Time delay before notifying specific CPM applications after route recovery or change";
                }

            } // container app-route-notifications

            container log-events {
                description "Enter the log-events context";

                list adp {
                    key "event";
                    description "Enter the adp context";

                    leaf event {
                        type types-log:adp-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list adp

                list application-assurance {
                    key "event";
                    description "Enter the application-assurance context";

                    leaf event {
                        type types-log:application-assurance-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list application-assurance

                list aps {
                    key "event";
                    description "Enter the aps context";

                    leaf event {
                        type types-log:aps-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list aps

                list atm {
                    key "event";
                    description "Enter the atm context";

                    leaf event {
                        type types-log:atm-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list atm

                list auto-prov {
                    key "event";
                    description "Enter the auto-prov context";

                    leaf event {
                        type types-log:auto-prov-events;
                        description "Events for auto-prov module.";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list auto-prov

                list bfd {
                    key "event";
                    description "Enter the bfd context";

                    leaf event {
                        type types-log:bfd-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list bfd

                list bgp {
                    key "event";
                    description "Enter the bgp context";

                    leaf event {
                        type types-log:bgp-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list bgp

                list bier {
                    key "event";
                    description "Control operation of bier events.";

                    leaf event {
                        type types-log:bier-events;
                        description "Events for bier module.";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list bier

                list calltrace {
                    key "event";
                    description "Enter the calltrace context";

                    leaf event {
                        type types-log:calltrace-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list calltrace

                list cflowd {
                    key "event";
                    description "Enter the cflowd context";

                    leaf event {
                        type types-log:cflowd-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list cflowd

                list chassis {
                    key "event";
                    description "Enter the chassis context";

                    leaf event {
                        type types-log:chassis-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        description "Generate log events of this type and increment the event counter";
                    }

                    leaf throttle {
                        type boolean;
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list chassis

                list debug {
                    key "event";
                    description "Enter the debug context";

                    leaf event {
                        type types-log:debug-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list debug

                list dhcp {
                    key "event";
                    description "Enter the dhcp context";

                    leaf event {
                        type types-log:dhcp-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list dhcp

                list dhcps {
                    key "event";
                    description "Enter the dhcps context";

                    leaf event {
                        type types-log:dhcps-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list dhcps

                list diameter {
                    key "event";
                    description "Enter the diameter context";

                    leaf event {
                        type types-log:diameter-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list diameter

                list dynsvc {
                    key "event";
                    description "Enter the dynsvc context";

                    leaf event {
                        type types-log:dynsvc-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list dynsvc

                list efm-oam {
                    key "event";
                    description "Enter the efm-oam context";

                    leaf event {
                        type types-log:efm-oam-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list efm-oam

                list elmi {
                    key "event";
                    description "Enter the elmi context";

                    leaf event {
                        type types-log:elmi-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list elmi

                list ering {
                    key "event";
                    description "Enter the ering context";

                    leaf event {
                        type types-log:ethring-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list ering

                list eth-cfm {
                    key "event";
                    description "Enter the eth-cfm context";

                    leaf event {
                        type types-log:ethcfm-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list eth-cfm

                list etun {
                    key "event";
                    description "Enter the etun context";

                    leaf event {
                        type types-log:etun-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list etun

                list filter {
                    key "event";
                    description "Enter the filter context";

                    leaf event {
                        type types-log:filter-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list filter

                list gmpls {
                    key "event";
                    description "Enter the gmpls context";

                    leaf event {
                        type types-log:gmpls-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list gmpls

                list gsmp {
                    key "event";
                    description "Enter the gsmp context";

                    leaf event {
                        type types-log:gsmp-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list gsmp

                list igh {
                    key "event";
                    description "Enter the igh context";

                    leaf event {
                        type types-log:igh-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list igh

                list igmp {
                    key "event";
                    description "Enter the igmp context";

                    leaf event {
                        type types-log:igmp-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list igmp

                list igmp-snooping {
                    key "event";
                    description "Enter the igmp-snooping context";

                    leaf event {
                        type types-log:igmp-snooping-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list igmp-snooping

                list ip {
                    key "event";
                    description "Enter the ip context";

                    leaf event {
                        type types-log:ip-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list ip

                list ipsec {
                    key "event";
                    description "Enter the ipsec context";

                    leaf event {
                        type types-log:ipsec-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list ipsec

                list isis {
                    key "event";
                    description "Enter the isis context";

                    leaf event {
                        type types-log:isis-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list isis

                list l2tp {
                    key "event";
                    description "Enter the l2tp context";

                    leaf event {
                        type types-log:l2tp-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list l2tp

                list lag {
                    key "event";
                    description "Enter the lag context";

                    leaf event {
                        type types-log:lag-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list lag

                list ldap {
                    key "event";
                    description "Enter the ldap context";

                    leaf event {
                        type types-log:ldap-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list ldap

                list ldp {
                    key "event";
                    description "Enter the ldp context";

                    leaf event {
                        type types-log:ldp-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        description "Generate log events of this type and increment the event counter";
                    }

                    leaf throttle {
                        type boolean;
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list ldp

                list li {
                    key "event";
                    description "Enter the li context";

                    leaf event {
                        type types-log:li-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        description "Generate log events of this type and increment the event counter";
                    }

                    leaf throttle {
                        type boolean;
                        description "Throttle log events of this type";
                    }

                    leaf specific-throttle {
                        type boolean;
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list li

                list lldp {
                    key "event";
                    description "Enter the lldp context";

                    leaf event {
                        type types-log:lldp-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list lldp

                list lmp {
                    key "event";
                    description "Enter the lmp context";

                    leaf event {
                        type types-log:lmp-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list lmp

                list logger {
                    key "event";
                    description "Enter the logger context";

                    leaf event {
                        type types-log:logger-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list logger

                list macsec {
                    key "event";
                    description "Enter the macsec context";

                    leaf event {
                        type types-log:macsec-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list macsec

                list mcpath {
                    key "event";
                    description "Enter the mcpath context";

                    leaf event {
                        type types-log:mcpath-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list mcpath

                list mc-redundancy {
                    key "event";
                    description "Enter the mc-redundancy context";

                    leaf event {
                        type types-log:mc-redundancy-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list mc-redundancy

                list mgmt-core {
                    key "event";
                    description "Enter the mgmt-core context";

                    leaf event {
                        type types-log:mgmt-core-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        description "Generate log events of this type and increment the event counter";
                    }

                    leaf throttle {
                        type boolean;
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list mgmt-core

                list mirror {
                    key "event";
                    description "Enter the mirror context";

                    leaf event {
                        type types-log:mirror-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list mirror

                list mld {
                    key "event";
                    description "Enter the mld context";

                    leaf event {
                        type types-log:mld-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list mld

                list mld-snooping {
                    key "event";
                    description "Enter the mld-snooping context";

                    leaf event {
                        type types-log:mld-snooping-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list mld-snooping

                list mpls {
                    key "event";
                    description "Enter the mpls context";

                    leaf event {
                        type types-log:mpls-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        description "Generate log events of this type and increment the event counter";
                    }

                    leaf throttle {
                        type boolean;
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list mpls

                list mpls-tp {
                    key "event";
                    description "Enter the mpls-tp context";

                    leaf event {
                        type types-log:mpls-tp-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list mpls-tp

                list msdp {
                    key "event";
                    description "Enter the msdp context";

                    leaf event {
                        type types-log:msdp-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list msdp

                list nat {
                    key "event";
                    description "Enter the nat context";

                    leaf event {
                        type types-log:nat-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        description "Generate log events of this type and increment the event counter";
                    }

                    leaf throttle {
                        type boolean;
                        description "Throttle log events of this type";
                    }

                    leaf specific-throttle {
                        type boolean;
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list nat

                list ntp {
                    key "event";
                    description "Enter the ntp context";

                    leaf event {
                        type types-log:ntp-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        description "Generate log events of this type and increment the event counter";
                    }

                    leaf throttle {
                        type boolean;
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list ntp

                list oam {
                    key "event";
                    description "Enter the oam context";

                    leaf event {
                        type types-log:oam-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        description "Generate log events of this type and increment the event counter";
                    }

                    leaf throttle {
                        type boolean;
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list oam

                list openflow {
                    key "event";
                    description "Enter the openflow context";

                    leaf event {
                        type types-log:openflow-events;
                        description "Events for openflow module.";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list openflow

                list ospf {
                    key "event";
                    description "Enter the ospf context";

                    leaf event {
                        type types-log:ospf-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        description "Generate log events of this type and increment the event counter";
                    }

                    leaf throttle {
                        type boolean;
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list ospf

                list pcap {
                    key "event";
                    description "Enter the pcap context";

                    leaf event {
                        type types-log:pcap-events;
                        description "Events for PCAP module";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list pcap

                list pim {
                    key "event";
                    description "Enter the pim context";

                    leaf event {
                        type types-log:pim-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        description "Generate log events of this type and increment the event counter";
                    }

                    leaf throttle {
                        type boolean;
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list pim

                list pim-snooping {
                    key "event";
                    description "Enter the pim-snooping context";

                    leaf event {
                        type types-log:pim-snooping-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list pim-snooping

                list port {
                    key "event";
                    description "Enter the port context";

                    leaf event {
                        type types-log:port-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list port

                list ppp {
                    key "event";
                    description "Enter the ppp context";

                    leaf event {
                        type types-log:ppp-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list ppp

                list pppoe {
                    key "event";
                    description "Enter the pppoe context";

                    leaf event {
                        type types-log:pppoe-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list pppoe

                list pppoe-clnt {
                    key "event";
                    description "Enter the pppoe-clnt context";

                    leaf event {
                        type types-log:pppoe-clnt-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list pppoe-clnt

                list ptp {
                    key "event";
                    description "Enter the ptp context";

                    leaf event {
                        type types-log:ptp-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list ptp

                list radius {
                    key "event";
                    description "Enter the radius context";

                    leaf event {
                        type types-log:radius-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list radius

                list rip {
                    key "event";
                    description "Enter the rip context";

                    leaf event {
                        type types-log:rip-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list rip

                list ripng {
                    key "event";
                    description "Enter the ripng context";

                    leaf event {
                        type types-log:ripng-events;
                        description "Events for RIPng module.";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list ripng

                list route-policy {
                    key "event";
                    description "Enter the route-policy context";

                    leaf event {
                        type types-log:route-policy-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list route-policy

                list rpki {
                    key "event";
                    description "Enter the rpki context";

                    leaf event {
                        type types-log:rpki-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list rpki

                list rsvp {
                    key "event";
                    description "Enter the rsvp context";

                    leaf event {
                        type types-log:rsvp-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list rsvp

                list satellite {
                    key "event";
                    description "Enter the satellite context";

                    leaf event {
                        type types-log:satellite-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list satellite

                list security {
                    key "event";
                    description "Enter the security context";

                    leaf event {
                        type types-log:security-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        description "Generate log events of this type and increment the event counter";
                    }

                    leaf throttle {
                        type boolean;
                        description "Throttle log events of this type";
                    }

                    leaf specific-throttle {
                        type boolean;
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list security

                list sflow {
                    key "event";
                    description "Enter the sflow context";

                    leaf event {
                        type types-log:sflow-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list sflow

                list snmp {
                    key "event";
                    description "Enter the snmp context";

                    leaf event {
                        type types-log:snmp-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        description "Generate log events of this type and increment the event counter";
                    }

                    leaf throttle {
                        type boolean;
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list snmp

                list stp {
                    key "event";
                    description "Enter the stp context";

                    leaf event {
                        type types-log:stp-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list stp

                list svcmgr {
                    key "event";
                    description "Enter the svcmgr context";

                    leaf event {
                        type types-log:svcmgr-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        description "Generate log events of this type and increment the event counter";
                    }

                    leaf throttle {
                        type boolean;
                        description "Throttle log events of this type";
                    }

                    leaf specific-throttle {
                        type boolean;
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list svcmgr

                list system {
                    key "event";
                    description "Enter the system context";

                    leaf event {
                        type types-log:system-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        description "Generate log events of this type and increment the event counter";
                    }

                    leaf throttle {
                        type boolean;
                        description "Throttle log events of this type";
                    }

                    leaf specific-throttle {
                        type boolean;
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list system

                list user {
                    key "event";
                    description "Enter the user context";

                    leaf event {
                        type types-log:user-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        description "Generate log events of this type and increment the event counter";
                    }

                    leaf throttle {
                        type boolean;
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list user

                list video {
                    key "event";
                    description "Enter the video context";

                    leaf event {
                        type types-log:video-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list video

                list vrrp {
                    key "event";
                    description "Enter the vrrp context";

                    leaf event {
                        type types-log:vrrp-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        default "minor";
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        default "false";
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list vrrp

                list vrtr {
                    key "event";
                    description "Enter the vrtr context";

                    leaf event {
                        type types-log:vrtr-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        description "Generate log events of this type and increment the event counter";
                    }

                    leaf throttle {
                        type boolean;
                        description "Throttle log events of this type";
                    }

                    leaf specific-throttle {
                        type boolean;
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list vrtr

                list wlan-gw {
                    key "event";
                    description "Enter the wlan-gw context";

                    leaf event {
                        type types-log:wlan-gw-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list wlan-gw

                list wpp {
                    key "event";
                    description "Enter the wpp context";

                    leaf event {
                        type types-log:wpp-events;
                        description "Specific log event as a trigger for one or more EHS handlers";
                    }

                    leaf severity {
                        type enumeration {
                            enum "cleared"                      { value 1; }
                            enum "indeterminate"                { value 2; }
                            enum "critical"                     { value 3; }
                            enum "major"                        { value 4; }
                            enum "minor"                        { value 5; }
                            enum "warning"                      { value 6; }
                        }
                        description "Severity level associated with event type";
                    }

                    leaf generate {
                        type boolean;
                        default "true";
                        description "Generate log events of this type and increment the event counter";
                    }

                    leaf throttle {
                        type boolean;
                        default "true";
                        description "Throttle log events of this type";
                    }

                    leaf specific-throttle {
                        type boolean;
                        description "Use parameters that throttle this specific event";
                    }

                    leaf specific-throttle-limit {
                        type uint32 {
                            range "1..20000";
                        }
                        description "Times that this event can be logged within the specific throttle interval";
                    }

                    leaf specific-throttle-interval {
                        type uint32 {
                            range "1..1200";
                        }
                        description "Duration of the event specific throttling interval";
                    }

                    leaf repeat {
                        type boolean;
                        default "false";
                        description
                            "The value of repeat determines whether or not events of
                             this type will be repeated.  When it has a value of 
                             'true', the event is repeated. When it has a value of 
                             'false', repeating is stopped.";
                    }

                } // list wpp

            } // container log-events

            container event-handling {
                description "Enter the event-handling context";

                list handler {
                    key "name";
                    max-elements 1500;
                    description "Enter the handler context";

                    leaf name {
                        type types-sros:named-item;
                        description "File ID to use when creating a log, or accounting file";
                    }

                    leaf admin-state {
                        type types-sros:admin-state;
                        default "disable";
                        description "Administrative state of EHS event";
                    }

                    leaf description {
                        type types-sros:description;
                        description "Text description";
                    }

                    list entry {
                        key "id";
                        max-elements 1500;
                        description "Enter the entry context";

                        leaf id {
                            type uint32 {
                                range "1..1500";
                            }
                            description "Index of an event entry in parent EHS Event Handler";
                        }

                        leaf admin-state {
                            type types-sros:admin-state;
                            default "enable";
                            description "Administrative state of EHS event";
                        }

                        leaf description {
                            type types-sros:description;
                            description "Text description";
                        }

                        leaf min-delay {
                            type uint32 {
                                range "1..604800";
                            }
                            units "seconds";
                            description "Minimum delay between subsequent executions of the script policy";
                        }

                        container script-policy {
                            description "Enter the script-policy context";

                            leaf name {
                                type leafref {
                                    path "../../../../../../system/script-control/script-policy[owner=current()/../owner]/policy-name";
                                }
                                description "Name combined with value of owner to launch the script policy";
                            }

                            leaf owner {
                                type leafref {
                                    path "../../../../../../system/script-control/script-policy[policy-name=current()/../name]/owner";
                                }
                                default "TiMOS CLI";
                                description "Name combined with value of owner to launch the script policy";
                            }

                        } // container script-policy

                    } // list entry

                } // list handler

            } // container event-handling

            container event-trigger {
                description "Enter the event-trigger context";

                list adp {
                    key "event";
                    description "Enter the adp context";

                    leaf event {
                        type types-log:adp-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list adp

                list application-assurance {
                    key "event";
                    description "Enter the application-assurance context";

                    leaf event {
                        type types-log:application-assurance-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list application-assurance

                list aps {
                    key "event";
                    description "Enter the aps context";

                    leaf event {
                        type types-log:aps-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list aps

                list atm {
                    key "event";
                    description "Enter the atm context";

                    leaf event {
                        type types-log:atm-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list atm

                list auto-prov {
                    key "event";
                    description "Enter the auto-prov context";

                    leaf event {
                        type types-log:auto-prov-events;
                        description "Events for auto-prov module.";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list auto-prov

                list bfd {
                    key "event";
                    description "Enter the bfd context";

                    leaf event {
                        type types-log:bfd-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list bfd

                list bgp {
                    key "event";
                    description "Enter the bgp context";

                    leaf event {
                        type types-log:bgp-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list bgp

                list bier {
                    key "event";
                    description "Configure EHS bier events.";

                    leaf event {
                        type types-log:bier-events;
                        description "Events for bier module.";
                    }

                    leaf admin-state {
                        type types-sros:admin-state;
                        default "disable";
                        description "Administrative state of EHS event";
                    }

                    leaf description {
                        type types-sros:description;
                        description "Text description";
                    }

                    list entry {
                        key "id";
                        description "Configure EHS event trigger-entry.";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Specifies the debounce value to be used in this EHS event trigger-entry.";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list bier

                list calltrace {
                    key "event";
                    description "Enter the calltrace context";

                    leaf event {
                        type types-log:calltrace-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list calltrace

                list cflowd {
                    key "event";
                    description "Enter the cflowd context";

                    leaf event {
                        type types-log:cflowd-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list cflowd

                list chassis {
                    key "event";
                    description "Enter the chassis context";

                    leaf event {
                        type types-log:chassis-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list chassis

                list debug {
                    key "event";
                    description "Enter the debug context";

                    leaf event {
                        type types-log:debug-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list debug

                list dhcp {
                    key "event";
                    description "Enter the dhcp context";

                    leaf event {
                        type types-log:dhcp-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list dhcp

                list dhcps {
                    key "event";
                    description "Enter the dhcps context";

                    leaf event {
                        type types-log:dhcps-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list dhcps

                list diameter {
                    key "event";
                    description "Enter the diameter context";

                    leaf event {
                        type types-log:diameter-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list diameter

                list dynsvc {
                    key "event";
                    description "Enter the dynsvc context";

                    leaf event {
                        type types-log:dynsvc-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list dynsvc

                list efm-oam {
                    key "event";
                    description "Enter the efm-oam context";

                    leaf event {
                        type types-log:efm-oam-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list efm-oam

                list elmi {
                    key "event";
                    description "Enter the elmi context";

                    leaf event {
                        type types-log:elmi-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list elmi

                list ering {
                    key "event";
                    description "Enter the ering context";

                    leaf event {
                        type types-log:ethring-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list ering

                list eth-cfm {
                    key "event";
                    description "Enter the eth-cfm context";

                    leaf event {
                        type types-log:ethcfm-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list eth-cfm

                list etun {
                    key "event";
                    description "Enter the etun context";

                    leaf event {
                        type types-log:etun-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list etun

                list filter {
                    key "event";
                    description "Enter the filter context";

                    leaf event {
                        type types-log:filter-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list filter

                list gmpls {
                    key "event";
                    description "Enter the gmpls context";

                    leaf event {
                        type types-log:gmpls-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list gmpls

                list gsmp {
                    key "event";
                    description "Enter the gsmp context";

                    leaf event {
                        type types-log:gsmp-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list gsmp

                list igh {
                    key "event";
                    description "Enter the igh context";

                    leaf event {
                        type types-log:igh-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list igh

                list igmp {
                    key "event";
                    description "Enter the igmp context";

                    leaf event {
                        type types-log:igmp-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list igmp

                list igmp-snooping {
                    key "event";
                    description "Enter the igmp-snooping context";

                    leaf event {
                        type types-log:igmp-snooping-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list igmp-snooping

                list ip {
                    key "event";
                    description "Enter the ip context";

                    leaf event {
                        type types-log:ip-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list ip

                list ipsec {
                    key "event";
                    description "Enter the ipsec context";

                    leaf event {
                        type types-log:ipsec-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list ipsec

                list isis {
                    key "event";
                    description "Enter the isis context";

                    leaf event {
                        type types-log:isis-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list isis

                list l2tp {
                    key "event";
                    description "Enter the l2tp context";

                    leaf event {
                        type types-log:l2tp-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list l2tp

                list lag {
                    key "event";
                    description "Enter the lag context";

                    leaf event {
                        type types-log:lag-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list lag

                list ldap {
                    key "event";
                    description "Enter the ldap context";

                    leaf event {
                        type types-log:ldap-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list ldap

                list ldp {
                    key "event";
                    description "Enter the ldp context";

                    leaf event {
                        type types-log:ldp-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list ldp

                list li {
                    key "event";
                    description "Enter the li context";

                    leaf event {
                        type types-log:li-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list li

                list lldp {
                    key "event";
                    description "Enter the lldp context";

                    leaf event {
                        type types-log:lldp-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list lldp

                list lmp {
                    key "event";
                    description "Enter the lmp context";

                    leaf event {
                        type types-log:lmp-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list lmp

                list logger {
                    key "event";
                    description "Enter the logger context";

                    leaf event {
                        type types-log:logger-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list logger

                list macsec {
                    key "event";
                    description "Enter the macsec context";

                    leaf event {
                        type types-log:macsec-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list macsec

                list mcpath {
                    key "event";
                    description "Enter the mcpath context";

                    leaf event {
                        type types-log:mcpath-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list mcpath

                list mc-redundancy {
                    key "event";
                    description "Enter the mc-redundancy context";

                    leaf event {
                        type types-log:mc-redundancy-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list mc-redundancy

                list mgmt-core {
                    key "event";
                    description "Enter the mgmt-core context";

                    leaf event {
                        type types-log:mgmt-core-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list mgmt-core

                list mirror {
                    key "event";
                    description "Enter the mirror context";

                    leaf event {
                        type types-log:mirror-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list mirror

                list mld {
                    key "event";
                    description "Enter the mld context";

                    leaf event {
                        type types-log:mld-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list mld

                list mld-snooping {
                    key "event";
                    description "Enter the mld-snooping context";

                    leaf event {
                        type types-log:mld-snooping-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list mld-snooping

                list mpls {
                    key "event";
                    description "Enter the mpls context";

                    leaf event {
                        type types-log:mpls-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list mpls

                list mpls-tp {
                    key "event";
                    description "Enter the mpls-tp context";

                    leaf event {
                        type types-log:mpls-tp-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list mpls-tp

                list msdp {
                    key "event";
                    description "Enter the msdp context";

                    leaf event {
                        type types-log:msdp-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list msdp

                list nat {
                    key "event";
                    description "Enter the nat context";

                    leaf event {
                        type types-log:nat-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list nat

                list ntp {
                    key "event";
                    description "Enter the ntp context";

                    leaf event {
                        type types-log:ntp-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list ntp

                list oam {
                    key "event";
                    description "Enter the oam context";

                    leaf event {
                        type types-log:oam-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list oam

                list openflow {
                    key "event";
                    description "Enter the openflow context";

                    leaf event {
                        type types-log:openflow-events;
                        description "Events for openflow module.";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list openflow

                list ospf {
                    key "event";
                    description "Enter the ospf context";

                    leaf event {
                        type types-log:ospf-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list ospf

                list pcap {
                    key "event";
                    description "Enter the pcap context";

                    leaf event {
                        type types-log:pcap-events;
                        description "Events for PCAP module";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list pcap

                list pim {
                    key "event";
                    description "Enter the pim context";

                    leaf event {
                        type types-log:pim-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list pim

                list pim-snooping {
                    key "event";
                    description "Enter the pim-snooping context";

                    leaf event {
                        type types-log:pim-snooping-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list pim-snooping

                list port {
                    key "event";
                    description "Enter the port context";

                    leaf event {
                        type types-log:port-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list port

                list ppp {
                    key "event";
                    description "Enter the ppp context";

                    leaf event {
                        type types-log:ppp-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list ppp

                list pppoe {
                    key "event";
                    description "Enter the pppoe context";

                    leaf event {
                        type types-log:pppoe-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list pppoe

                list pppoe-clnt {
                    key "event";
                    description "Enter the pppoe-clnt context";

                    leaf event {
                        type types-log:pppoe-clnt-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list pppoe-clnt

                list ptp {
                    key "event";
                    description "Enter the ptp context";

                    leaf event {
                        type types-log:ptp-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list ptp

                list radius {
                    key "event";
                    description "Enter the radius context";

                    leaf event {
                        type types-log:radius-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list radius

                list rip {
                    key "event";
                    description "Enter the rip context";

                    leaf event {
                        type types-log:rip-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list rip

                list ripng {
                    key "event";
                    description "Enter the ripng context";

                    leaf event {
                        type types-log:ripng-events;
                        description "Events for RIPng module.";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list ripng

                list route-policy {
                    key "event";
                    description "Enter the route-policy context";

                    leaf event {
                        type types-log:route-policy-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list route-policy

                list rpki {
                    key "event";
                    description "Enter the rpki context";

                    leaf event {
                        type types-log:rpki-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list rpki

                list rsvp {
                    key "event";
                    description "Enter the rsvp context";

                    leaf event {
                        type types-log:rsvp-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list rsvp

                list satellite {
                    key "event";
                    description "Enter the satellite context";

                    leaf event {
                        type types-log:satellite-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list satellite

                list security {
                    key "event";
                    description "Enter the security context";

                    leaf event {
                        type types-log:security-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list security

                list sflow {
                    key "event";
                    description "Enter the sflow context";

                    leaf event {
                        type types-log:sflow-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list sflow

                list snmp {
                    key "event";
                    description "Enter the snmp context";

                    leaf event {
                        type types-log:snmp-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list snmp

                list stp {
                    key "event";
                    description "Enter the stp context";

                    leaf event {
                        type types-log:stp-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list stp

                list svcmgr {
                    key "event";
                    description "Enter the svcmgr context";

                    leaf event {
                        type types-log:svcmgr-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list svcmgr

                list system {
                    key "event";
                    description "Enter the system context";

                    leaf event {
                        type types-log:system-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list system

                list user {
                    key "event";
                    description "Enter the user context";

                    leaf event {
                        type types-log:user-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list user

                list video {
                    key "event";
                    description "Enter the video context";

                    leaf event {
                        type types-log:video-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list video

                list vrrp {
                    key "event";
                    description "Enter the vrrp context";

                    leaf event {
                        type types-log:vrrp-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list vrrp

                list vrtr {
                    key "event";
                    description "Enter the vrtr context";

                    leaf event {
                        type types-log:vrtr-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list vrtr

                list wlan-gw {
                    key "event";
                    description "Enter the wlan-gw context";

                    leaf event {
                        type types-log:wlan-gw-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list wlan-gw

                list wpp {
                    key "event";
                    description "Enter the wpp context";

                    leaf event {
                        type types-log:wpp-events;
                        description "Specific log event as a trigger for one or more EHS handlers";
                    }

                    leaf admin-state {
                        type types-sros:admin-state;
                        default "disable";
                        description "Administrative state of EHS event";
                    }

                    leaf description {
                        type types-sros:description;
                        description "Text description";
                    }

                    list entry {
                        key "id";
                        description "Enter the entry context";

                        leaf id {
                            type uint32 {
                                range "1..1500";
                            }
                            description "ID of a trigger entry in the parent EHS event trigger";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-id";
                            }
                            description "Log filter for EHS event trigger entry";
                        }

                        leaf handler {
                            type leafref {
                                path "../../../../event-handling/handler/name";
                            }
                            description "Event handler for EHS event trigger entry";
                        }

                        container debounce {
                            description "Enter the debounce context";

                            leaf value {
                                type uint32 {
                                    range "2..15";
                                }
                                description "Number of event occurrences within specific time for EHS to trigger response";
                            }

                            leaf time {
                                type uint32 {
                                    range "1..604800";
                                }
                                units "seconds";
                                description "Time within which specific event must occur for EHS to trigger response";
                            }

                        } // container debounce

                    } // list entry

                } // list wpp

            } // container event-trigger

            list file {
                key "file-id";
                description "Enter the file context";

                leaf file-id {
                    type int32 {
                        range "1..99";
                    }
                    description "File ID when creating a log or accounting file";
                }

                leaf description {
                    type types-sros:description;
                    description "Text description";
                }

                leaf rollover {
                    type int32 {
                        range "5..10080";
                    }
                    units "minutes";
                    default "1440";
                    description "Frequency at which a new log or accounting file is created";
                }

                leaf retention {
                    type int32 {
                        range "1..500";
                    }
                    units "hours";
                    default "12";
                    description "Minimum time that a file is retained on the media";
                }

                container compact-flash-location {
                    description "Enter the compact-flash-location context";

                    leaf primary {
                        type types-log:compact-flash-drive;
                        sros-ext:immutable;
                        default "cf-unspecified";
                        description "Log file location";
                    }

                    leaf backup {
                        type types-log:compact-flash-drive;
                        sros-ext:immutable;
                        default "cf-unspecified";
                        description "Log file location";
                    }

                } // container compact-flash-location

            } // list file

            list filter {
                key "filter-id";
                description "Enter the filter context";

                leaf filter-id {
                    type uint32 {
                        range "1..1500";
                    }
                    description "Identification number for an event log filter";
                }

                leaf description {
                    type types-sros:description;
                    description "Text description";
                }

                leaf default-action {
                    type types-log:filter-action;
                    description "Default action for the event filter";
                }

                list entry {
                    key "entry-id";
                    description "Enter the entry context";

                    leaf entry-id {
                        type uint32 {
                            range "1..999";
                        }
                        description "Identification number for an event log filter parameter";
                    }

                    leaf description {
                        type types-sros:description;
                        description "Text description";
                    }

                    leaf action {
                        type types-log:filter-action;
                        description "Action for this event filter entry";
                    }

                    container match {
                        description "Enter the match context";

                        container application {
                            description "Enter the application context";

                            choice application-match {
                                case eq {

                                    leaf eq {
                                        type types-log:application;
                                        description "Application to match";
                                    }

                                }
                                case neq {

                                    leaf neq {
                                        type types-log:application;
                                        description "Application to be filtered out";
                                    }

                                }
                            }
                        } // container application

                        container event {
                            description "Enter the event context";

                            choice event-match {
                                case eq {

                                    leaf eq {
                                        type uint32 {
                                            range "1..max";
                                        }
                                        description "Log event message to match";
                                    }

                                }
                                case neq {

                                    leaf neq {
                                        type uint32 {
                                            range "1..max";
                                        }
                                        description "Log event message to filter out";
                                    }

                                }
                                case lt {

                                    leaf lt {
                                        type uint32 {
                                            range "1..max";
                                        }
                                        description "Number of the log event to match";
                                    }

                                }
                                case lte {

                                    leaf lte {
                                        type uint32 {
                                            range "1..max";
                                        }
                                        description "Number of the log event to match";
                                    }

                                }
                                case gt {

                                    leaf gt {
                                        type uint32 {
                                            range "1..max";
                                        }
                                        description "Number of the log event to match";
                                    }

                                }
                                case gte {

                                    leaf gte {
                                        type uint32 {
                                            range "1..max";
                                        }
                                        description "Number of the log event to match";
                                    }

                                }
                            }
                        } // container event

                        container message {
                            description "Enter the message context";

                            leaf regexp {
                                type boolean;
                                default "false";
                                description "String comparison to determine if the log event matches the value of pattern";
                            }

                            choice message-match {
                                case eq {

                                    leaf eq {
                                        type string {
                                            length "1..400";
                                        }
                                        description "Log event message to match";
                                    }

                                }
                                case neq {

                                    leaf neq {
                                        type string {
                                            length "1..400";
                                        }
                                        description "Log event message to be filtered out";
                                    }

                                }
                            }
                        } // container message

                        container vrtr-name {
                            description "Enter the vrtr-name context";

                            leaf regexp {
                                type boolean;
                                default "false";
                                description "String comparison to determine if the log event matches the value of router instance";
                            }

                            choice vrtr-name-match {
                                case eq {

                                    leaf eq {
                                        type types-sros:named-item;
                                        description "Specifies the log event router context name to be matched.";
                                    }

                                }
                                case neq {

                                    leaf neq {
                                        type types-sros:named-item;
                                        description "Specifies the log event router context name to be filtered out.";
                                    }

                                }
                            }
                        } // container vrtr-name

                        container severity {
                            description "Enter the severity context";

                            choice severity-match {
                                case eq {

                                    leaf eq {
                                        type types-log:severity-level;
                                        description "Log event severity level to match";
                                    }

                                }
                                case neq {

                                    leaf neq {
                                        type types-log:severity-level;
                                        description "Log event severity level to filter out";
                                    }

                                }
                                case lt {

                                    leaf lt {
                                        type types-log:severity-level;
                                        description "Log event severity level";
                                    }

                                }
                                case lte {

                                    leaf lte {
                                        type types-log:severity-level;
                                        description "Log event severity level";
                                    }

                                }
                                case gt {

                                    leaf gt {
                                        type types-log:severity-level;
                                        description "Log event severity level";
                                    }

                                }
                                case gte {

                                    leaf gte {
                                        type types-log:severity-level;
                                        description "Log event severity level";
                                    }

                                }
                            }
                        } // container severity

                        container subject {
                            description "Enter the subject context";

                            leaf regexp {
                                type boolean;
                                default "false";
                                description "String comparison to determine if the log event matches the value of subject";
                            }

                            choice subject-match {
                                case eq {

                                    leaf eq {
                                        type types-sros:named-item;
                                        description "Log event subject string to match";
                                    }

                                }
                                case neq {

                                    leaf neq {
                                        type types-sros:named-item;
                                        description "Log event subject string to filter out";
                                    }

                                }
                            }
                        } // container subject

                    } // container match

                } // list entry

            } // list filter

            list log-id {
                key "id";
                max-elements 30;
                description "Enter the log-id context";

                leaf id {
                    type int32 {
                        range "1..101";
                    }
                    description "The value of id uniquely identifies an event stream log.";
                }

                leaf admin-state {
                    type types-sros:admin-state;
                    default "enable";
                    description "Administrative state of the log";
                }

                leaf description {
                    type types-sros:description;
                    description "Text description";
                }

                leaf netconf-stream {
                    type types-sros:named-item;
                    description "Destination NETCONF stream name";
                }

                leaf time-format {
                    type enumeration {
                        enum "utc"                          { value 1; }
                        enum "local"                        { value 2; }
                    }
                    default "utc";
                    description "Timestamp format for events sent to logs which have a value of either syslog, or file";
                }

                leaf python-policy {
                    type leafref {
                        path "../../../python/python-policy/name";
                    }
                    description "Python policy name";
                }

                leaf filter {
                    type leafref {
                        path "../../filter/filter-id";
                    }
                    description "Filter for this log's source event stream to limit the event output in this log destination";
                }

                container source {
                    description "Enter the source context";

                    leaf main {
                        type boolean;
                        description "All events in the main stream to be sent to specific destination";
                    }

                    leaf security {
                        type boolean;
                        description "All events in the security event stream to be sent to specific destination";
                    }

                    leaf change {
                        type boolean;
                        description "All events in the activity stream to be sent to specific destination";
                    }

                    leaf debug {
                        type boolean;
                        default "false";
                        description "All debug-trace events in the debug stream to be sent to specific destination";
                    }

                } // container source

                container destination {
                    description "Enter the destination context";

                    choice log-id-destination {
                        case file {

                            leaf file {
                                type leafref {
                                    path "../../../file/file-id";
                                }
                                sros-ext:immutable;
                                description "Log events to send to the specified file ID";
                            }

                        }
                        case syslog {

                            leaf syslog {
                                type leafref {
                                    path "../../../syslog/syslog-id";
                                }
                                sros-ext:immutable;
                                description "Log events to send to the specified syslog ID";
                            }

                        }
                        case memory {

                            container memory {
                                presence "Send log events to a buffer in memory.";
                                description "Enter the memory context";

                                leaf max-entries {
                                    type uint32 {
                                        range "50..3000";
                                    }
                                    sros-ext:immutable;
                                    default "100";
                                    description "Number of events stored in this memory log";
                                }

                            } // container memory

                        }
                        case snmp {

                            container snmp {
                                presence "Send log events to the snmp-trap-group that has the same id as this log.";
                                description "Enter the snmp context";

                                leaf max-entries {
                                    type uint32 {
                                        range "50..3000";
                                    }
                                    sros-ext:immutable;
                                    default "100";
                                    description "Number of events stored in this SNMP log";
                                }

                            } // container snmp

                        }
                        case console {

                            leaf console {
                                type empty;
                                sros-ext:immutable;
                                description "Log events to send to the system console port";
                            }

                        }
                        case netconf {

                            container netconf {
                                presence "Send log events to the netconf.";
                                description "Enter the netconf context";

                                leaf max-entries {
                                    type uint32 {
                                        range "50..3000";
                                    }
                                    sros-ext:immutable;
                                    default "100";
                                    description "Number of events stored in this NETCONF log";
                                }

                            } // container netconf

                        }
                        case cli {

                            container cli {
                                presence "Send log events to the cli.";
                                description "Enter the cli context";

                                leaf max-entries {
                                    type uint32 {
                                        range "50..3000";
                                    }
                                    sros-ext:immutable;
                                    default "100";
                                    description "Number of events stored in this CLI log";
                                }

                            } // container cli

                        }
                    }
                } // container destination

            } // list log-id

            container route-preference {
                description "Enter the route-preference context";

                leaf primary {
                    type enumeration {
                        enum "inband"                       { value 1; }
                        enum "outband"                      { value 2; }
                    }
                    default "outband";
                    description "Primary routing preference for traffic that is generated for SNMP notifications and syslog messages";
                }

                leaf secondary {
                    type enumeration {
                        enum "inband"                       { value 1; }
                        enum "outband"                      { value 2; }
                        enum "none"                         { value 3; }
                    }
                    default "inband";
                    description
                        "Secondary routing preference for traffic that is generated for SNMP
                         notifications and syslog messages";
                }

            } // container route-preference

            list snmp-trap-group {
                key "log-id";
                max-elements 15;
                description "Enter the snmp-trap-group context";

                leaf log-id {
                    type int32 {
                        range "1..100";
                    }
                    description "SNMP notification group associated with the event log";
                }

                leaf description {
                    type types-sros:description;
                    description "Text description";
                }

                list trap-target {
                    key "name";
                    max-elements 25;
                    description "Enter the trap-target context";

                    leaf name {
                        type string {
                            length "1..28";
                        }
                        description "Name for an SNMP notification destination within the SNMP notification group";
                    }

                    leaf description {
                        type types-sros:description;
                        description "Text description";
                    }

                    leaf address {
                        type types-sros:ip-unicast-address;
                        mandatory true;
                        description "IP address attribute for the trap target";
                    }

                    leaf port {
                        type types-qos:tcp-udp-match-port;
                        default "162";
                        description "UDP port number to send messages to this remote SNMP notification collector";
                    }

                    leaf version {
                        type enumeration {
                            enum "snmpv1"                       { value 0; }
                            enum "snmpv2c"                      { value 1; }
                            enum "snmpv3"                       { value 3; }
                        }
                        default "snmpv3";
                        description "SNMP version to format notification messages sent to this SNMP notification collector";
                    }

                    leaf notify-community {
                        type string {
                            length "1..31";
                        }
                        mandatory true;
                        description "SNMPv1 or SNMPv2c community name string, or SNMPv3 security name, for sending a notification";
                    }

                    leaf security-level {
                        type enumeration {
                            enum "no-auth-no-privacy"           { value 1; }
                            enum "auth-no-privacy"              { value 2; }
                            enum "privacy"                      { value 3; }
                        }
                        default "no-auth-no-privacy";
                        description "Security level at which SNMP notification messages are sent to SNMP notification collector";
                    }

                    leaf replay {
                        type boolean;
                        default "false";
                        description "Retransmit missed notifications";
                    }

                } // list trap-target

            } // list snmp-trap-group

            list syslog {
                key "syslog-id";
                description "Enter the syslog context";

                leaf syslog-id {
                    type int32 {
                        range "1..10";
                    }
                    description "Unique arbitrary identifier for this SYSLOG collector target";
                }

                leaf description {
                    type types-sros:description;
                    description "Text description";
                }

                leaf address {
                    type types-sros:ip-unicast-address;
                    description "Target syslog host address";
                }

                leaf facility {
                    type enumeration {
                        enum "kernel"                       { value 0; }
                        enum "user"                         { value 1; }
                        enum "mail"                         { value 2; }
                        enum "systemd"                      { value 3; }
                        enum "auth"                         { value 4; }
                        enum "syslogd"                      { value 5; }
                        enum "printer"                      { value 6; }
                        enum "netnews"                      { value 7; }
                        enum "uucp"                         { value 8; }
                        enum "cron"                         { value 9; }
                        enum "authpriv"                     { value 10; }
                        enum "ftp"                          { value 11; }
                        enum "ntp"                          { value 12; }
                        enum "logaudit"                     { value 13; }
                        enum "logalert"                     { value 14; }
                        enum "cron2"                        { value 15; }
                        enum "local0"                       { value 16; }
                        enum "local1"                       { value 17; }
                        enum "local2"                       { value 18; }
                        enum "local3"                       { value 19; }
                        enum "local4"                       { value 20; }
                        enum "local5"                       { value 21; }
                        enum "local6"                       { value 22; }
                        enum "local7"                       { value 23; }
                    }
                    default "local7";
                    description "Facility code for messages";
                }

                leaf severity {
                    type enumeration {
                        enum "emergency"                    { value 0; }
                        enum "alert"                        { value 1; }
                        enum "critical"                     { value 2; }
                        enum "error"                        { value 3; }
                        enum "warning"                      { value 4; }
                        enum "notice"                       { value 5; }
                        enum "info"                         { value 6; }
                        enum "debug"                        { value 7; }
                    }
                    default "info";
                    description "Severity level threshold for the syslog message";
                }

                leaf log-prefix {
                    type union {
                        type enumeration {
                            enum "no-prefix"                    { value -1; }
                        }
                        type string {
                            length "1..32";
                            pattern "([0-9a-zA-Z]|\\-)+" {
                                error-message "String must contain only alpha-numeric characters or character -";
                            }
                        }
                    }
                    default "TMNX";
                    description "String that is prepended to every log message sent to this target syslog host";
                }

                leaf port {
                    type types-qos:tcp-udp-match-port;
                    default "514";
                    description "UDP port to generate syslog messages";
                }

            } // list syslog

            container throttle-rate {
                description "Enter the throttle-rate context";

                leaf limit {
                    type uint32 {
                        range "1..20000";
                    }
                    default "2000";
                    description "Number of log events within the throttle interval";
                }

                leaf interval {
                    type uint32 {
                        range "1..1200";
                    }
                    default "1";
                    description "Duration of an event throttling interval";
                }

            } // container throttle-rate

        } // container log

    } // grouping conf-log

}
