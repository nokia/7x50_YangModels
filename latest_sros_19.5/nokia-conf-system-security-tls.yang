submodule nokia-conf-system-security-tls {

    yang-version "1.1";

    belongs-to nokia-conf { prefix "conf"; }

    import nokia-sros-yang-extensions     { prefix "sros-ext"; }
    import nokia-types-sros               { prefix "types-sros"; }

    include nokia-conf-groups;
    include nokia-conf-system;
    include nokia-conf-system-security;
    include nokia-conf-system-security-pki;

    sros-ext:sros-major-release "rel19";

    organization "Nokia";

    contact
        "Nokia SR OS Support
         Web: <http://www.nokia.com>";

    description
        "Nokia YANG Data model to configure system security tls parameters. on SR OS based routers.

         Copyright 2016 Nokia. All rights reserved. Reproduction of this document
         is authorized on the condition that the foregoing copyright notice is included.

         This nokia-conf-system-security-tls YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-03-18";

    grouping conf-system-security-tls {
        container tls {
            description "Enter the tls context";

            list cert-profile {
                key "cert-profile-name";
                max-elements 16;
                description "Enter the cert-profile context";

                leaf cert-profile-name {
                    type types-sros:named-item;
                    description "TLS certificate profile name";
                }

                leaf admin-state {
                    type types-sros:admin-state;
                    default "disable";
                    description "Administrative state of the certificate profile";
                }

                list entry {
                    key "entry-id";
                    max-elements 8;
                    sros-ext:auto-restart-to-modify;
                    description "Enter the entry context";

                    leaf entry-id {
                        type int32 {
                            range "1..8";
                        }
                        description "Certificate profile ID";
                    }

                    leaf certificate-file {
                        type types-sros:string-not-all-spaces {
                            length "1..95";
                            pattern "[^:\\\\/]+";
                        }
                        description "Certificate file name";
                    }

                    leaf key-file {
                        type types-sros:string-not-all-spaces {
                            length "1..95";
                            pattern "[^:\\\\/]+";
                        }
                        description "Key file name";
                    }

                    container send-chain {
                        description "Enter the send-chain context";

                        list ca-profile {
                            key "ca-profile-name";
                            max-elements 7;
                            description "Enter the ca-profile context";

                            leaf ca-profile-name {
                                type leafref {
                                    path "../../../../../../pki/ca-profile/ca-profile-name";
                                }
                                description "Certificate Authority (CA) profile name";
                            }

                        } // list ca-profile

                    } // container send-chain

                } // list entry

            } // list cert-profile

            list client-cipher-list {
                key "client-cipher-list-name";
                max-elements 16;
                description "Enter the client-cipher-list context";

                leaf client-cipher-list-name {
                    type types-sros:named-item;
                    description "TLS client cipher list";
                }

                list cipher {
                    key "index";
                    description "Enter the cipher context";

                    leaf index {
                        type uint32 {
                            range "1..255";
                        }
                        description "Index of the cipher";
                    }

                    leaf name {
                        type enumeration {
                            enum "tls-rsa-with-null-md5"        { value 1; }
                            enum "tls-rsa-with-null-sha"        { value 2; }
                            enum "tls-rsa-with3des-ede-cbc-sha" { value 10; }
                            enum "tls-rsa-with-aes128-cbc-sha"  { value 47; }
                            enum "tls-rsa-with-aes256-cbc-sha"  { value 53; }
                            enum "tls-rsa-with-null-sha256"     { value 59; }
                            enum "tls-rsa-with-aes128-cbc-sha256" { value 60; }
                            enum "tls-rsa-with-aes256-cbc-sha256" { value 61; }
                        }
                        mandatory true;
                        description "Value for the cipher suite code";
                    }

                } // list cipher

            } // list client-cipher-list

            list server-cipher-list {
                key "server-cipher-list-name";
                max-elements 16;
                description "Enter the server-cipher-list context";

                leaf server-cipher-list-name {
                    type types-sros:named-item;
                    description "Name of TLS server cipher list.";
                }

                list cipher {
                    key "index";
                    description "Enter the cipher context";

                    leaf index {
                        type uint32 {
                            range "1..255";
                        }
                        description "Index of the cipher";
                    }

                    leaf name {
                        type enumeration {
                            enum "tls-rsa-with-null-md5"        { value 1; }
                            enum "tls-rsa-with-null-sha"        { value 2; }
                            enum "tls-rsa-with3des-ede-cbc-sha" { value 10; }
                            enum "tls-rsa-with-aes128-cbc-sha"  { value 47; }
                            enum "tls-rsa-with-aes256-cbc-sha"  { value 53; }
                            enum "tls-rsa-with-null-sha256"     { value 59; }
                            enum "tls-rsa-with-aes128-cbc-sha256" { value 60; }
                            enum "tls-rsa-with-aes256-cbc-sha256" { value 61; }
                        }
                        mandatory true;
                        description "Value for the cipher suite code";
                    }

                } // list cipher

            } // list server-cipher-list

            list client-tls-profile {
                key "client-profile-name";
                max-elements 16;
                description "Enter the client-tls-profile context";

                leaf client-profile-name {
                    type types-sros:named-item;
                    description "Name of TLS client profile.";
                }

                leaf cert-profile {
                    type leafref {
                        path "../../cert-profile/cert-profile-name";
                    }
                    description "Certificate profile ID";
                }

                leaf cipher-list {
                    type leafref {
                        path "../../client-cipher-list/client-cipher-list-name";
                    }
                    description
                        "Specifies the ordered list of supported cipher suite codes associated
                         with this TLS client profile.";
                }

                leaf admin-state {
                    type types-sros:admin-state;
                    default "disable";
                    description "Administrative state of the client TLS profile";
                }

                leaf trust-anchor-profile {
                    type leafref {
                        path "../../trust-anchor-profile/trust-anchor-profile-name";
                    }
                    description "Trust anchor profile";
                }

            } // list client-tls-profile

            list server-tls-profile {
                key "server-profile-name";
                max-elements 16;
                description "Enter the server-tls-profile context";

                leaf server-profile-name {
                    type types-sros:named-item;
                    description "Name of TLS server profile.";
                }

                leaf cert-profile {
                    type leafref {
                        path "../../cert-profile/cert-profile-name";
                    }
                    description "Certificate profile ID";
                }

                leaf tls-re-negotiate-timer {
                    type uint32 {
                        range "0..65000";
                    }
                    units "minutes";
                    default "0";
                    description "TLS HELLO request timer";
                }

                leaf cipher-list {
                    type leafref {
                        path "../../server-cipher-list/server-cipher-list-name";
                    }
                    description
                        "Specifies the ordered list of supported cipher suite codes associated
                         with this TLS client profile.";
                }

                leaf admin-state {
                    type types-sros:admin-state;
                    default "disable";
                    description "Administrative state of the server TLS profile";
                }

                container authenticate-client {
                    description "Enter the authenticate-client context";

                    leaf trust-anchor-profile {
                        type leafref {
                            path "../../../trust-anchor-profile/trust-anchor-profile-name";
                        }
                        description "Trust anchor profile for TLS client certificate authentication";
                    }

                    leaf common-name-list {
                        type leafref {
                            path "../../../../pki/common-name-list/cn-list-name";
                        }
                        description "Common name list for TLS client certificate authentication";
                    }

                } // container authenticate-client

            } // list server-tls-profile

            list trust-anchor-profile {
                key "trust-anchor-profile-name";
                max-elements 16;
                description "Enter the trust-anchor-profile context";

                leaf trust-anchor-profile-name {
                    type types-sros:named-item;
                    description "Name of TLS trust anchor profile";
                }

                list trust-anchor {
                    key "ca-profile-name";
                    max-elements 8;
                    description "Enter the trust-anchor context";

                    leaf ca-profile-name {
                        type leafref {
                            path "../../../../pki/ca-profile/ca-profile-name";
                        }
                        description "Trusted CA profile";
                    }

                } // list trust-anchor

            } // list trust-anchor-profile

        } // container tls

    } // grouping conf-system-security-tls

}
