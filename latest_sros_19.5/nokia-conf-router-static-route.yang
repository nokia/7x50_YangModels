submodule nokia-conf-router-static-route {

    yang-version "1.1";

    belongs-to nokia-conf { prefix "conf"; }

    import nokia-sros-yang-extensions     { prefix "sros-ext"; }
    import nokia-types-router             { prefix "types-router"; }
    import nokia-types-sros               { prefix "types-sros"; }

    include nokia-conf-groups;
    include nokia-conf-policy-options;

    sros-ext:sros-major-release "rel19";

    organization "Nokia";

    contact
        "Nokia SR OS Support
         Web: <http://www.nokia.com>";

    description
        "Nokia YANG Data model to configure Static route attributes on SR OS based routers.

         Copyright 2016 Nokia. All rights reserved. Reproduction of this document
         is authorized on the condition that the foregoing copyright notice is included.

         This nokia-conf-router-static-route YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-03-26";

    grouping conf-router-static-route-static-routes {
        container static-routes {
            description "Enter the static-routes context";

            container hold-down {
                presence "Enable/Disable hold down time for all static-routes on this router instance.";
                description "Enter the hold-down context";

                leaf initial {
                    type uint32 {
                        range "1..65535";
                    }
                    mandatory true;
                    description "Value for the initial hold down time";
                }

                leaf multiplier {
                    type uint32 {
                        range "1..10";
                    }
                    mandatory true;
                    description "Value by which the previous hold-down time is multiplied to calculate the new one";
                }

                leaf max-value {
                    type uint32 {
                        range "1..65535";
                    }
                    mandatory true;
                    description "Maximum value of the hold down time";
                }

            } // container hold-down

            list route {
                key "ip-prefix route-type";
                description "Enter the route context";

                leaf ip-prefix {
                    type types-sros:ip-prefix;
                    description "IP prefix and prefix length for the static routes";
                }

                leaf route-type {
                    type types-router:unicast-multicast;
                    description "Static route type for unicast or multicast RPF";
                }

                leaf-list community {
                    type types-sros:community;
                    max-elements 12;
                    ordered-by user;
                    description "Community ID associated with the static route";
                }

                leaf tag {
                    type uint32 {
                        range "1..max";
                    }
                    description "Static route tag";
                }

                container blackhole {
                    presence "Blackhole attributes for static route.";
                    description "Enter the blackhole context";

                    leaf description {
                        type types-sros:description-allow-all-white-spaces;
                        description "Text description";
                    }

                    leaf metric {
                        type uint32 {
                            range "0..65535";
                        }
                        default "1";
                        description "Static route metric";
                    }

                    leaf preference {
                        type uint32 {
                            range "1..255";
                        }
                        default "5";
                        description "Priority of this static route over the routes from different sources";
                    }

                    leaf tag {
                        type uint32 {
                            range "1..max";
                        }
                        description "Static route tag";
                    }

                    leaf community {
                        type types-sros:community;
                        description "Community ID associated with the static route";
                    }

                    leaf admin-state {
                        type types-sros:admin-state;
                        description "Administrative state of the static route next hop";
                    }

                    leaf dynamic-bgp {
                        type boolean;
                        default "false";
                        description "Derive static route's next-hop from the best BGP route for the exact same IP prefix";
                    }

                    leaf generate-icmp {
                        type boolean;
                        default "false";
                        description "Send ICMP unreachable messages when received packets match a static route with black-hole next-hop";
                    }

                    container prefix-list {
                        description "Enter the prefix-list context";

                        leaf name {
                            type leafref {
                                path "../../../../../../policy-options/prefix-list/name";
                            }
                            description "Name of a prefix list to match";
                        }

                        leaf flag {
                            type enumeration {
                                enum "any"                          { value 0; }
                                enum "all"                          { value 1; }
                                enum "none"                         { value 2; }
                            }
                            default "any";
                            description "Static route match condition from prefixes in specified prefix list";
                        }

                    } // container prefix-list

                } // container blackhole

                list indirect {
                    key "ip-address";
                    description "Enter the indirect context";

                    leaf ip-address {
                        type types-sros:ip-address;
                        description "Indirect next hop for static routes";
                    }

                    leaf description {
                        type types-sros:description-allow-all-white-spaces;
                        description "Text description";
                    }

                    leaf metric {
                        type uint32 {
                            range "0..65535";
                        }
                        default "1";
                        description "Static route metric";
                    }

                    leaf preference {
                        type uint32 {
                            range "1..255";
                        }
                        default "5";
                        description "Priority of this static route over the routes from different sources";
                    }

                    leaf tag {
                        type uint32 {
                            range "1..max";
                        }
                        description "Static route tag";
                    }

                    leaf community {
                        type types-sros:community;
                        description "Community ID associated with the static route";
                    }

                    leaf destination-class {
                        type uint32 {
                            range "1..255";
                        }
                        description "Destination class for this static route";
                    }

                    leaf source-class {
                        type uint32 {
                            range "1..255";
                        }
                        description "Source class for this static route";
                    }

                    leaf admin-state {
                        type types-sros:admin-state;
                        description "Administrative state of the static route next hop";
                    }

                    container qos {
                        description "Enter the qos context";

                        leaf forwarding-class {
                            type types-sros:fc-name;
                            description "Forwarding class associated with the static route";
                        }

                        leaf priority {
                            type types-sros:priority;
                            description "Static route priority";
                        }

                    } // container qos

                    container prefix-list {
                        description "Enter the prefix-list context";

                        leaf name {
                            type leafref {
                                path "../../../../../../policy-options/prefix-list/name";
                            }
                            description "Name of a prefix list to match";
                        }

                        leaf flag {
                            type enumeration {
                                enum "any"                          { value 0; }
                                enum "all"                          { value 1; }
                                enum "none"                         { value 2; }
                            }
                            default "any";
                            description "Static route match condition from prefixes in specified prefix list";
                        }

                    } // container prefix-list

                    list cpe-check {
                        key "address";
                        max-elements 1;
                        description "Enter the cpe-check context";

                        leaf address {
                            type types-sros:ip-address;
                            description "IP address of the target CPE device";
                        }

                        leaf drop-count {
                            type uint32 {
                                range "1..255";
                            }
                            default "3";
                            description "Number of consecutive ping replies that are missed before declaring the CPE down";
                        }

                        leaf interval {
                            type uint32 {
                                range "1..255";
                            }
                            units "seconds";
                            default "1";
                            description "Time between ICMP pings to the target CPE IP address";
                        }

                        leaf log {
                            type boolean;
                            default "false";
                            description "Log the transitions between active and inactive based on the CPE connectivity check";
                        }

                        leaf padding-size {
                            type uint32 {
                                range "0..16384";
                            }
                            units "bytes";
                            default "56";
                            description "Padding size for the ICMP ping test packet of the CPE connectivity check";
                        }

                    } // list cpe-check

                    container tunnel-next-hop {
                        description "Enter the tunnel-next-hop context";

                        leaf disallow-igp {
                            type boolean;
                            default "false";
                            description "Do not resolve indirect static routes using IGP next-hops in RTM if no tunnel next-hops found in TTM";
                        }

                        leaf resolution {
                            type enumeration {
                                enum "none"                         { value 0; }
                                enum "filter"                       { value 1; }
                                enum "any"                          { value 2; }
                            }
                            default "none";
                            description "Tunnel next hop resolution to resolve indirect static route";
                        }

                        container resolution-filter {
                            description "Enter the resolution-filter context";

                            leaf ldp {
                                type boolean;
                                default "false";
                                description "Use LDP Route Forwarding Equivalence Class (FEC) tunneling for next-hop resolution";
                            }

                            leaf sr-isis {
                                type boolean;
                                default "false";
                                description "Use the SR ISIS tunneling mechanism  to resolve next hop for the static route";
                            }

                            leaf sr-ospf {
                                type boolean;
                                default "false";
                                description "Use SR OSPF tunneling  for next-hop resolution";
                            }

                            leaf sr-ospf3 {
                                type boolean;
                                default "false";
                                description
                                    "Specifies if SR OSPFv3 tunneling mechanism will be used to resolve next-hop
                                     for the static-route or not.";
                            }

                            leaf rib-api {
                                type boolean;
                                default "false";
                                description "Enable/disable setting RIB API type for tunnel-next-hop.";
                            }

                            leaf mpls-fwd-policy {
                                type boolean;
                                default "false";
                                description "Enable/disable setting MPLS Forwarding Policy type for tunnel-next-hop.";
                            }

                            container rsvp-te {
                                presence "Configure RSVP-TE to find the route to indirect next-hop router-static-routes-entry.";
                                description "Enter the rsvp-te context";

                                list lsp {
                                    key "lsp-name";
                                    description "Enter the lsp context";

                                    leaf lsp-name {
                                        type types-sros:named-item-64;
                                        description "Labeled Switch Path name";
                                    }

                                } // list lsp

                            } // container rsvp-te

                            container sr-te {
                                presence "Configure SR-TE to find the route to indirect next-hop static-routes-entry.";
                                description "Enter the sr-te context";

                                list lsp {
                                    key "lsp-name";
                                    description "Enter the lsp context";

                                    leaf lsp-name {
                                        type types-sros:named-item-64;
                                        description "Labeled Switch Path name";
                                    }

                                } // list lsp

                            } // container sr-te

                        } // container resolution-filter

                    } // container tunnel-next-hop

                } // list indirect

                list interface {
                    key "interface-name";
                    description "Enter the interface context";

                    leaf interface-name {
                        type types-sros:interface-name;
                        description "Router interface name";
                    }

                    leaf description {
                        type types-sros:description-allow-all-white-spaces;
                        description "Text description";
                    }

                    leaf metric {
                        type uint32 {
                            range "0..65535";
                        }
                        default "1";
                        description "Static route metric";
                    }

                    leaf preference {
                        type uint32 {
                            range "1..255";
                        }
                        default "5";
                        description "Priority of this static route over the routes from different sources";
                    }

                    leaf tag {
                        type uint32 {
                            range "1..max";
                        }
                        description "Static route tag";
                    }

                    leaf community {
                        type types-sros:community;
                        description "Community ID associated with the static route";
                    }

                    leaf destination-class {
                        type uint32 {
                            range "1..255";
                        }
                        description "Destination class for this static route";
                    }

                    leaf source-class {
                        type uint32 {
                            range "1..255";
                        }
                        description "Source class for this static route";
                    }

                    leaf load-balancing-weight {
                        type uint32 {
                            range "1..max";
                        }
                        description "Load-balancing weight for all of the ECMP next hops";
                    }

                    leaf admin-state {
                        type types-sros:admin-state;
                        description "Administrative state of the static route next hop";
                    }

                    container qos {
                        description "Enter the qos context";

                        leaf forwarding-class {
                            type types-sros:fc-name;
                            description "Forwarding class associated with the static route";
                        }

                        leaf priority {
                            type types-sros:priority;
                            description "Static route priority";
                        }

                    } // container qos

                    container prefix-list {
                        description "Enter the prefix-list context";

                        leaf name {
                            type leafref {
                                path "../../../../../../policy-options/prefix-list/name";
                            }
                            description "Name of a prefix list to match";
                        }

                        leaf flag {
                            type enumeration {
                                enum "any"                          { value 0; }
                                enum "all"                          { value 1; }
                                enum "none"                         { value 2; }
                            }
                            default "any";
                            description "Static route match condition from prefixes in specified prefix list";
                        }

                    } // container prefix-list

                    list cpe-check {
                        key "address";
                        max-elements 1;
                        description "Enter the cpe-check context";

                        leaf address {
                            type types-sros:ip-address;
                            description "IP address of the target CPE device";
                        }

                        leaf drop-count {
                            type uint32 {
                                range "1..255";
                            }
                            default "3";
                            description "Number of consecutive ping replies that are missed before declaring the CPE down";
                        }

                        leaf interval {
                            type uint32 {
                                range "1..255";
                            }
                            units "seconds";
                            default "1";
                            description "Time between ICMP pings to the target CPE IP address";
                        }

                        leaf log {
                            type boolean;
                            default "false";
                            description "Log the transitions between active and inactive based on the CPE connectivity check";
                        }

                        leaf padding-size {
                            type uint32 {
                                range "0..16384";
                            }
                            units "bytes";
                            default "56";
                            description "Padding size for the ICMP ping test packet of the CPE connectivity check";
                        }

                    } // list cpe-check

                } // list interface

                list next-hop {
                    key "ip-address";
                    description "Enter the next-hop context";

                    leaf ip-address {
                        type types-sros:ip-address-with-zone;
                        description "IP address for the next hop";
                    }

                    leaf description {
                        type types-sros:description-allow-all-white-spaces;
                        description "Text description";
                    }

                    leaf metric {
                        type uint32 {
                            range "0..65535";
                        }
                        default "1";
                        description "Static route metric";
                    }

                    leaf preference {
                        type uint32 {
                            range "1..255";
                        }
                        default "5";
                        description "Priority of this static route over the routes from different sources";
                    }

                    leaf tag {
                        type uint32 {
                            range "1..max";
                        }
                        description "Static route tag";
                    }

                    leaf community {
                        type types-sros:community;
                        description "Community ID associated with the static route";
                    }

                    leaf destination-class {
                        type uint32 {
                            range "1..255";
                        }
                        description "Destination class for this static route";
                    }

                    leaf source-class {
                        type uint32 {
                            range "1..255";
                        }
                        description "Source class for this static route";
                    }

                    leaf bfd-liveness {
                        type boolean;
                        default "false";
                        description "Use Bidirectional Forwarding Detection on this static route";
                    }

                    leaf validate-next-hop {
                        type boolean;
                        default "false";
                        description "Track the state of the next hop in the IPv4 ARP Cache or the IPv6 Neighbor Cache";
                    }

                    leaf load-balancing-weight {
                        type uint32 {
                            range "1..max";
                        }
                        description "Load-balancing weight for all of the ECMP next hops";
                    }

                    leaf ldp-sync {
                        type boolean;
                        default "false";
                        description "Use LDP synchronization feature for a static route";
                    }

                    leaf admin-state {
                        type types-sros:admin-state;
                        description "Administrative state of the static route next hop";
                    }

                    container qos {
                        description "Enter the qos context";

                        leaf forwarding-class {
                            type types-sros:fc-name;
                            description "Forwarding class associated with the static route";
                        }

                        leaf priority {
                            type types-sros:priority;
                            description "Static route priority";
                        }

                    } // container qos

                    container prefix-list {
                        description "Enter the prefix-list context";

                        leaf name {
                            type leafref {
                                path "../../../../../../policy-options/prefix-list/name";
                            }
                            description "Name of a prefix list to match";
                        }

                        leaf flag {
                            type enumeration {
                                enum "any"                          { value 0; }
                                enum "all"                          { value 1; }
                                enum "none"                         { value 2; }
                            }
                            default "any";
                            description "Static route match condition from prefixes in specified prefix list";
                        }

                    } // container prefix-list

                    list cpe-check {
                        key "address";
                        max-elements 1;
                        description "Enter the cpe-check context";

                        leaf address {
                            type types-sros:ip-address;
                            description "IP address of the target CPE device";
                        }

                        leaf drop-count {
                            type uint32 {
                                range "1..255";
                            }
                            default "3";
                            description "Number of consecutive ping replies that are missed before declaring the CPE down";
                        }

                        leaf interval {
                            type uint32 {
                                range "1..255";
                            }
                            units "seconds";
                            default "1";
                            description "Time between ICMP pings to the target CPE IP address";
                        }

                        leaf log {
                            type boolean;
                            default "false";
                            description "Log the transitions between active and inactive based on the CPE connectivity check";
                        }

                        leaf padding-size {
                            type uint32 {
                                range "0..16384";
                            }
                            units "bytes";
                            default "56";
                            description "Padding size for the ICMP ping test packet of the CPE connectivity check";
                        }

                    } // list cpe-check

                } // list next-hop

            } // list route

        } // container static-routes

    } // grouping conf-router-static-route-static-routes

}
