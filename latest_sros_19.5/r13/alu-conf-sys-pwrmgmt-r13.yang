module alu-conf-sys-pwrmgmt-r13 {
  yang-version "1";

  namespace "urn:alcatel-lucent.com:sros:ns:yang:conf-sys-pwrmgmt-r13";

  prefix "conf-sys-pwrmgmt-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure power management on SR OS based 
       routers. 
       
       Copyright 2014-2015 Alcatel-Lucent, 2016 Nokia. All rights reserved. 
       Reproduction of this document is authorized on the condition that the 
       foregoing copyright notice is included. 
       
       This alu-conf-sys-pwrmgmt-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2017-11-24";

  grouping alu-conf-sys-pwrmgmt-r13 {
    container power-management {
      description
          "Configure power management";
      container mode {
        description
            "Configure the power capacity mode algorithm";
        leaf none-basic-advanced {
          type enumeration {
            enum none;
            enum basic;
            enum advanced;
          }
          default "basic";
          description
              "keywords - Default: basic";
        } //none-basic-advanced

      } //container mode

      container power-safety-alert {
        description
            "Configure the power capacity to trigger a safety alert event";
        leaf wattage {
          type string;
          description
              "Attribute wattage for power-safety-alert";
        } //wattage

      } //container power-safety-alert

      container power-safety-level {
        description
            "Configure the minimum threshold to power off devices";
        leaf percent {
          type uint32 {
            range "0..100";
          }
          default 100;
          description
              "[0..100] - Default: 100";
        } //percent

      } //container power-safety-level

      list pcm {
        key "pcm-slot chassis";
        description
            "Configure Power Connection Module Parameters.";
        leaf pcm-slot {
          type uint32;
          description
              "Attribute pcm-slot for pcm";
        } //pcm-slot

        leaf chassis {
          type string;
          description
              "Attribute chassis-id for pcm";
        } //chassis

        container pcm-type {
          description
              "Provision the PCM type";
          leaf pcm-type-id {
            type enumeration {
              enum dual;
              enum quad;
            }
          } //pcm-type-id

        } //container pcm-type

      } //list pcm

      list peq {
        key "peq-slot chassis";
        description
            "Configure Power Equalizer Parameters";
        leaf peq-slot {
          type string;
          description
              "Attribute peq-slot for peq";
        } //peq-slot

        leaf chassis {
          type string;
          description
              "Attribute chassis-id for peq";
        } //chassis

        container input-power-mode {
          description
              "Configure the Input Power Mode of the PEQ";
          leaf amperage {
            type enumeration {
              enum 60;
              enum 80;
            }
          } //amperage

        } //container input-power-mode

        container peq-type {
          description
              "Provision the PEQ type";
          leaf peq-type {
            type string {
            }
            description
                "Attribute peq-type for peq-type";
          } //peq-type

        } //container peq-type

        leaf shutdown {
          type boolean;
          description
              "Administratively enable/disable the PEQ";
        }

      } //list peq

    } //container power-management

  } //grouping alu-conf-sys-pwrmgmt-r13

} //module  alu-conf-sys-pwrmgmt-r13
