module alu-conf-svc-vprn-pim-r13 {
  yang-version "1";

  namespace "urn:alcatel-lucent.com:sros:ns:yang:conf-svc-vprn-pim-r13";

  prefix "conf-svc-vprn-pim-r13";

  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure PIM for VPRN services on SR OS 
       based routers. 
       
       Copyright 2014-2015 Alcatel-Lucent, 2016 Nokia. All rights reserved. 
       Reproduction of this document is authorized on the condition that the 
       foregoing copyright notice is included. 
       
       This alu-conf-svc-vprn-pim-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-01-29";

  grouping alu-conf-svc-vprn-pim-r13 {
    container pim {
      presence
          "Configure PIM for VPRN services";
      container apply-to {
        description
            "Create/remove interfaces in PIM";
        leaf all-none {
          type enumeration {
            enum all;
            enum none;
          }
          description
              "keywords";
        } //all-none

      } //container apply-to

      list import {
        key "join-policy-register-policy";
        description
            "Configure import policies";
        leaf join-policy-register-policy {
          type enumeration {
            enum join-policy;
            enum register-policy;
          }
          description
              "keywords";
        } //join-policy-register-policy

        leaf-list policy-name {
          type string {
            length "1..32";
          }
          max-elements 5;
          description
              "[32 chars max] - maximum 5 policies";
        } //policy-name

      } //list import

      leaf ipv4-multicast-disable {
        type boolean;
        description
            "Enable/Disable IPv4 multicast";
      }

      leaf ipv6-multicast-disable {
        type boolean;
        description
            "Enable/Disable IPv6 multicast";
      }

      leaf mc-ecmp-balance {
        type boolean;
        description
            "Enable/Disable multicast balancing of traffic over ECMP links";
      }

      container mc-ecmp-balance-hold {
        description
            "Configure hold time for multicast balancing over ECMP links";
        leaf minutes {
          type uint32 {
            range "2..600";
          }
        } //minutes

      } //container mc-ecmp-balance-hold

      container mc-ecmp-hashing-enabled {
        description
            "Enable/Disable hash based multicast balancing of traffic over ECMP links";
        leaf rebalance {
          type boolean;
        } //rebalance

      } //container mc-ecmp-hashing-enabled

      leaf non-dr-attract-traffic {
        type boolean;
        description
            "Enable/disable attracting traffic when not DR";
      }

      container rpf-table {
        description
            "Configure the route table(s) for RPF lookup";
        leaf rtable-m-rtable-u-both {
          type enumeration {
            enum rtable-m;
            enum rtable-u;
            enum both;
          }
          description
              "keywords";
        } //rtable-m-rtable-u-both

      } //container rpf-table

      container rpf6-table {
        description
            "Configure the IPv6 route table(s) for RPF lookup";
        leaf rtable6-m-rtable6-u-both {
          type enumeration {
            enum rtable6-m;
            enum rtable6-u;
            enum both;
          }
          description
              "keywords";
        } //rtable6-m-rtable6-u-both

      } //container rpf6-table

      leaf shutdown {
        type boolean;
        description
            "Administratively enable or disable the operation of PIM";
      }

      container spt-switchover-threshold {
        description
            "Configure shortest path tree (spt tree) switchover threshold for a group 
             prefix";
        leaf grp-ip-address-mask {
          type string;
          description
              "multicast group address a.b.c.d 
               mask [4..32]";
        } //grp-ip-address-mask

        leaf netmask {
          type string;
          description
              "a.b.c.d (network bits all 1 and host bits all 0)";
        } //netmask

        leaf spt-threshold {
          type string;
          description
              "[1..4294967294]|infinity (threshold in kbps)";
        } //spt-threshold

        leaf grp-ipv6-addr {
          type string;
          description
              "multicast ipv6-address x:x:x:x:x:x:x:x (eight 16-bit pieces) 
               x:x:x:x:x:x:d.d.d.d 
               x [0..FFFF]H 
               d [0..255]D 
               prefix-length [1..128]";
        } //grp-ipv6-addr

      } //container spt-switchover-threshold

      container ssm-assert-compatible-mode {
        description
            "Enable/Disable use of ssm-assert-compatible-mode";
        leaf ssm-assert-compatible-mode-id {
          type enumeration {
            enum enable;
            enum disable;
          }
        } //ssm-assert-compatible-mode-id

      } //container ssm-assert-compatible-mode

      container ssm-default-range-disable {
        description
            "Enable the disabling of SSM Default Range";
        leaf ipv4 {
          type boolean;
        } //ipv4

        leaf ipv6 {
          type boolean;
        } //ipv6

      } //container ssm-default-range-disable

      container grt-extranet {
        presence
            "Configure GRT extranet";
        container group-prefix {
          description
              "Configure group prefixes";
          leaf-list ip-address-mask {
            type inet:ip-prefix;
            max-elements 8;
          } //ip-address-mask

          leaf any {
            type boolean;
          } //any

          leaf group-prefix-id {
            type inet:ip-prefix;
            description
                "ip-address/mask";
          } //group-prefix-id

          leaf starg {
            type boolean;
          } //starg

        } //container group-prefix

      } //container grt-extranet

      list interface {
        key "ip-int-name";
        description
            "Configure PIM interface";
        leaf ip-int-name {
          type string {
            length "1..32";
          }
        } //ip-int-name

        container assert-period {
          description
              "Configure the period for periodic refreshes of PIM Assert messages on an 
               interface";
          leaf assert-period {
            type uint32 {
              range "1..300";
            }
            description
                "[1..300] seconds";
          } //assert-period

        } //container assert-period

        list bfd-enable {
          key "bfd-enable-id";
          description
              "Enable BFD";
          leaf bfd-enable-id {
            type enumeration {
              enum ipv4;
              enum ipv6;
            }
          } //bfd-enable-id

        } //list bfd-enable

        leaf bsm-check-rtr-alert {
          type boolean;
          description
              "Enable/disable accepting of BSM packets without router alert option";
        }

        container hello-interval {
          description
              "Configure the frequency at which PIM hello messages are sent over this 
               interface";
          leaf hello-interval {
            type uint32 {
              range "0..255";
            }
            description
                "[0..255 seconds]";
          } //hello-interval

        } //container hello-interval

        container hello-multiplier {
          description
              "Configure hello-multiplier in multiples of 0.1 (deci-units)";
          leaf deci-units {
            type uint32 {
              range "20..100";
            }
            default 35;
          } //deci-units

        } //container hello-multiplier

        leaf improved-assert {
          type boolean;
          description
              "Enable/disable improved assert processing";
        }

        leaf instant-prune-echo {
          type boolean;
          description
              "Enable/Disable instant PruneEcho for a PIM interface";
        }

        leaf ipv4-multicast-disable {
          type boolean;
          description
              "Enable/Disable IPv4 multicast";
        }

        leaf ipv6-multicast-disable {
          type boolean;
          description
              "Enable/Disable IPv6 multicast";
        }

        container max-groups {
          description
              "Configure the maximum number of groups for this interface";
          leaf max-groups-id {
            type uint16 {
              range "1..16000";
            }
          } //max-groups-id

        } //container max-groups

        list monitor-oper-group {
          key "family";
          description
              "Configure an Operational-Group to monitor";
          leaf group-name {
            type string;
          } //group-name

          leaf family {
            type enumeration {
              enum ipv4;
              enum ipv6;
            }
          } //family

          leaf add {
            type uint32 {
              range "1..4294967295";
            }
          } //add

          leaf set {
            type uint32 {
              range "1..4294967295";
            }
          } //set

          leaf subtract {
            type uint32 {
              range "1..4294967295";
            }
          } //subtract

        } //list monitor-oper-group

        container multicast-senders {
          description
              "Configure the way subnet matching is done for incoming data packets on this 
               interface";
          leaf auto-always-never {
            type enumeration {
              enum auto;
              enum always;
              enum never;
            }
            description
                "keywords";
          } //auto-always-never

        } //container multicast-senders

        container p2mp-ldp-tree-join {
          description
              "Enable/Disable p2mp-ldp-tree-join";
          leaf ipv4 {
            type boolean;
          } //ipv4

          leaf ipv6 {
            type boolean;
          } //ipv6

        } //container p2mp-ldp-tree-join

        container priority {
          description
              "Configure the DR election priority for this interface";
          leaf dr-priority {
            type uint32 {
              range "1..4294967295";
            }
          } //dr-priority

        } //container priority

        leaf shutdown {
          type boolean;
          description
              "Administratively enable/disable the interface";
        }

        container sticky-dr {
          description
              "Enable/disable sticky-DR and configure DR priority for sticky-DR";
          leaf priority {
            type uint32 {
              range "1..4294967295";
            }
          } //priority

        } //container sticky-dr

        container three-way-hello {
          description
              "Configure compatibility mode for three-way-hello";
        }

        leaf tracking-support {
          type boolean;
          description
              "Enable/disable tracking support";
        }

        container mcac {
          description
              "Configure multicast CAC policy and constraints for this interface";
          container if-policy {
            description
                "Configure multicast CAC if-policy for this interface";
            leaf if-policy-name {
              type string {
                length "1..32";
              }
            } //if-policy-name

          } //container if-policy

          container policy {
            description
                "Configure multicast CAC policy name";
            leaf policy-name {
              type string {
                length "1..32";
              }
              description
                  "max 32 chars";
            } //policy-name

          } //container policy

          container unconstrained-bw {
            description
                "Configure unconstrained-bw for multicast cac policy on this interface";
            leaf bandwidth {
              type int32 {
                range "0..2147483647";
              }
            } //bandwidth

            leaf mandatory-bw {
              type int32 {
                range "0..2147483647";
              }
            } //mandatory-bw

          } //container unconstrained-bw

          container mc-constraints {
            description
                "Configure multicast CAC constraints";
            list level {
              key "level-id";
              description
                  "Configure levels and their associated bandwidth for multicast cac policy on 
                   this interface";
              leaf level-id {
                type uint32 {
                  range "1..8";
                }
              } //level-id

              leaf bw {
                type uint32;
                description
                    "[0..2147483647] kbps";
              } //bw

            } //list level

            list number-down {
              key "number-lag-port-down";
              description
                  "Configure number of ports down along with level for multicast cac policy on 
                   this interface";
              leaf number-lag-port-down {
                type string;
                description
                    "Attribute number-lag-port-down for number-down";
              } //number-lag-port-down

              leaf level {
                type uint32 {
                  range "1..8";
                }
              } //level

            } //list number-down

            leaf shutdown {
              type boolean;
              description
                  "Administratively enable/disable constraint for multicast cac policy";
            }

            leaf use-lag-port-weight {
              type boolean;
              description
                  "Enable/disable using the LAG port weight while calculating Multicast CAC 
                   constraints";
            }

          } //container mc-constraints

        } //container mcac

      } //list interface

      container rp {
        description
            "Configure the router as static or Candidate-RP";
        leaf auto-rp-discovery {
          type boolean;
          description
              "Configure auto-rp";
        }

        container bootstrap-export {
          description
              "Configure bootstrap export policies";
          leaf-list policy-name {
            type string {
              length "1..32";
            }
            max-elements 5;
            description
                "[32 chars max] - maximum 5 policies";
          } //policy-name

        } //container bootstrap-export

        container bootstrap-import {
          description
              "Configure bootstrap import policies";
          leaf-list policy-name {
            type string {
              length "1..32";
            }
            max-elements 5;
            description
                "[32 chars max] - maximum 5 policies";
          } //policy-name

        } //container bootstrap-import

        list anycast {
          key "rp-ip-address";
          description
              "Configure PIM anycast protocol instance for the RP";
          leaf rp-ip-address {
            type inet:ip-address;
          } //rp-ip-address

          list rp-set-peer {
            key "ip-address";
            description
                "Configure a peer in the anycast rp-set";
            leaf ip-address {
              type inet:ip-address;
            } //ip-address

          } //list rp-set-peer

        } //list anycast

        container bsr-candidate {
          description
              "Context to configure Candidate Bootstrap parameters";
          container address {
            description
                "Configure the bootstrap address of the router";
            leaf ip-address {
              type inet:ip-address;
            } //ip-address

          } //container address

          container hash-mask-len {
            description
                "Configure the bootstrap hash mask length";
            leaf hash-mask-length {
              type uint32 {
                range "0..32";
              }
            } //hash-mask-length

          } //container hash-mask-len

          container priority {
            description
                "Configure the bootstrap priority of the router";
            leaf bootstrap-priority {
              type uint32 {
                range "0..255";
              }
            } //bootstrap-priority

          } //container priority

          leaf shutdown {
            type boolean;
            description
                "Administratively enable/disable participation of the router in bootstrap 
                 election";
          }

        } //container bsr-candidate

        container ipv6 {
          description
              "Configure IPv6 settings for the PIM protocol instance for the RP";
          list anycast {
            key "ipv6-address";
            description
                "Configure PIM anycast protocol instance for the RP";
            leaf ipv6-address {
              type inet:ipv6-address;
              description
                  "x:x:x:x:x:x:x:x (eight 16-bit pieces) 
                   x:x:x:x:x:x:d.d.d.d 
                   x [0..FFFF]H 
                   d [0..255]D";
            } //ipv6-address

            list rp-set-peer {
              key "ipv6-address";
              description
                  "Configure a peer in the anycast rp-set";
              leaf ipv6-address {
                type inet:ipv6-address;
                description
                    "x:x:x:x:x:x:x:x (eight 16-bit pieces) 
                     x:x:x:x:x:x:d.d.d.d 
                     x [0..FFFF]H 
                     d [0..255]D";
              } //ipv6-address

            } //list rp-set-peer

          } //list anycast

          container bsr-candidate {
            description
                "Context to configure Candidate Bootstrap parameters";
            container address {
              description
                  "Configure the bootstrap address of the router";
              leaf ipv6-address {
                type inet:ipv6-address;
                description
                    "x:x:x:x:x:x:x:x (eight 16-bit pieces) 
                     x:x:x:x:x:x:d.d.d.d 
                     x [0..FFFF]H 
                     d [0..255]D";
              } //ipv6-address

            } //container address

            container hash-mask-len {
              description
                  "Configure the bootstrap hash mask length";
              leaf hash-mask-length {
                type uint32 {
                  range "0..128";
                }
              } //hash-mask-length

            } //container hash-mask-len

            container priority {
              description
                  "Configure the bootstrap priority of the router";
              leaf bootstrap-priority {
                type uint32 {
                  range "0..255";
                }
              } //bootstrap-priority

            } //container priority

            leaf shutdown {
              type boolean;
              description
                  "Administratively enable/disable participation of the router in bootstrap 
                   election";
            }

          } //container bsr-candidate

          container embedded-rp {
            presence
                "Context to configure the Embedded RP parameters";
            list group-range {
              key "ipv6-address-prefix-length";
              description
                  "Configure the group range for Embedded-RP";
              leaf ipv6-address-prefix-length {
                type string;
                description
                    "ipv6-address x:x:x:x:x:x:x:x (eight 16-bit pieces) 
                     x:x:x:x:x:x:d.d.d.d 
                     x [0..FFFF]H 
                     d [0..255]D 
                     prefix-length [8..128]";
              } //ipv6-address-prefix-length

            } //list group-range

            leaf shutdown {
              type boolean;
              description
                  "Administratively enable/disable the Embedded-RP";
            }

          } //container embedded-rp

          container rp-candidate {
            description
                "Context to configure the Candidate RP parameters";
            container address {
              description
                  "Configure the local Candidate-RP address";
              leaf ipv6-address {
                type inet:ipv6-address;
                description
                    "x:x:x:x:x:x:x:x (eight 16-bit pieces) 
                     x:x:x:x:x:x:d.d.d.d 
                     x [0..FFFF]H 
                     d [0..255]D";
              } //ipv6-address

            } //container address

            list group-range {
              key "ipv6-address-prefix-length";
              description
                  "Configure the group range for the Candidate-RP";
              leaf ipv6-address-prefix-length {
                type string;
                description
                    "ipv6-address x:x:x:x:x:x:x:x (eight 16-bit pieces) 
                     x:x:x:x:x:x:d.d.d.d 
                     x [0..FFFF]H 
                     d [0..255]D 
                     prefix-length [16..128]";
              } //ipv6-address-prefix-length

            } //list group-range

            container holdtime {
              description
                  "Configure the Candidate-RP holdtime";
              leaf holdtime {
                type uint32 {
                  range "5..255";
                }
                description
                    "[5..255] seconds";
              } //holdtime

            } //container holdtime

            container priority {
              description
                  "Configure the Candidate-RP priority";
              leaf priority {
                type uint32 {
                  range "0..255";
                }
              } //priority

            } //container priority

            leaf shutdown {
              type boolean;
              description
                  "Administratively enable/disable the Candidate-RP";
            }

          } //container rp-candidate

          container static {
            description
                "Context to configure static group to RP mapping";
            list address {
              key "ipv6-address";
              description
                  "Configure the RP address for multicast group prefixes";
              leaf ipv6-address {
                type inet:ipv6-address;
                description
                    "x:x:x:x:x:x:x:x (eight 16-bit pieces) 
                     x:x:x:x:x:x:d.d.d.d 
                     x [0..FFFF]H 
                     d [0..255]D";
              } //ipv6-address

              list group-prefix {
                key "ipv6-address-prefix-length";
                description
                    "Configure a group prefix for the RP address";
                leaf ipv6-address-prefix-length {
                  type string;
                  description
                      "ipv6-address x:x:x:x:x:x:x:x (eight 16-bit pieces) 
                       x:x:x:x:x:x:d.d.d.d 
                       x [0..FFFF]H 
                       d [0..255]D 
                       prefix-length [8..128]";
                } //ipv6-address-prefix-length

              } //list group-prefix

              leaf override {
                type boolean;
                description
                    "Change the precedence of static RP over dynamically learnt RP";
              }

            } //list address

          } //container static

        } //container ipv6

        container rp-candidate {
          description
              "Context to configure the Candidate RP parameters";
          container address {
            description
                "Configure the local Candidate-RP address";
            leaf ip-address {
              type inet:ip-address;
            } //ip-address

          } //container address

          list group-range {
            key "grp-ip-addr-mask netmask";
            description
                "Configure the group range for the Candidate-RP";
            leaf grp-ip-addr-mask {
              type string;
              description
                  "multicast group address a.b.c.d 
                   mask [4..32]";
            } //grp-ip-addr-mask

            leaf netmask {
              type string;
              description
                  "a.b.c.d (network bits all 1 and host bits all 0)";
            } //netmask

          } //list group-range

          container holdtime {
            description
                "Configure the Candidate-RP holdtime";
            leaf holdtime {
              type uint32 {
                range "5..255";
              }
              description
                  "[5..255] seconds";
            } //holdtime

          } //container holdtime

          container priority {
            description
                "Configure the Candidate-RP priority";
            leaf priority {
              type uint32 {
                range "0..255";
              }
            } //priority

          } //container priority

          leaf shutdown {
            type boolean;
            description
                "Administratively enable/disable the Candidate-RP";
          }

        } //container rp-candidate

        container static {
          description
              "Context to configure static group to RP mapping";
          list address {
            key "ip-address";
            description
                "Configure the RP address for multicast group prefixes";
            leaf ip-address {
              type inet:ip-address;
            } //ip-address

            list group-prefix {
              key "grp-ip-addr-mask netmask";
              description
                  "Configure a group prefix for the RP address";
              leaf grp-ip-addr-mask {
                type inet:ip-prefix;
                description
                    "multicast group address a.b.c.d 
                     mask [4..32]";
              } //grp-ip-addr-mask

              leaf netmask {
                type string;
                description
                    "a.b.c.d (network bits all 1 and host bits all 0)";
              } //netmask

            } //list group-prefix

            leaf override {
              type boolean;
              description
                  "Change the precedence of static RP over dynamically learnt RP";
            }

          } //list address

        } //container static

      } //container rp

      container ssm-groups {
        presence
            "Configure the SSM group ranges";
        list group-range {
          key "ip-prefix-mask-ipv6-prefix-prefix-length netmask";
          description
              "Add/remove SSM group range";
          leaf ip-prefix-mask-ipv6-prefix-prefix-length {
            type string;
            description
                "Attribute ip-prefix/mask|ipv6-prefix/prefix-length for group-range";
          } //ip-prefix-mask-ipv6-prefix-prefix-length

          leaf netmask {
            type string;
            description
                "a.b.c.d (network bits all 1 and host bits all 0)";
          } //netmask

        } //list group-range

      } //container ssm-groups

    } //container pim

  } //grouping alu-conf-svc-vprn-pim-r13

} //module  alu-conf-svc-vprn-pim-r13
