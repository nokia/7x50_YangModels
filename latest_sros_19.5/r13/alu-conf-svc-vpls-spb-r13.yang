module alu-conf-svc-vpls-spb-r13 {
  yang-version "1";

  namespace "urn:alcatel-lucent.com:sros:ns:yang:conf-svc-vpls-spb-r13";

  prefix "conf-svc-vpls-spb-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure Shortest Path Bridging on SR OS 
       based routers. 
       
       Copyright 2014-2015 Alcatel-Lucent, 2016 Nokia. All rights reserved. 
       Reproduction of this document is authorized on the condition that the 
       foregoing copyright notice is included. 
       
       This alu-conf-svc-vpls-spb-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-03-05";

  grouping alu-conf-svc-vpls-spb-r13 {
    container spb {
      description
          "Configure Shortest Path Bridging";
      container lsp-pacing-interval {
        description
            "Configure the interval for sending LSPs from the interface";
        leaf milli-seconds {
          type uint32 {
            range "0..65535";
          }
        } //milli-seconds

      } //container lsp-pacing-interval

      container retransmit-interval {
        description
            "Configure the minimum interval between LSP packets retransmission for the 
             given interface";
        leaf seconds {
          type int32 {
            range "1..65535";
          }
        } //seconds

      } //container retransmit-interval

      leaf shutdown {
        type boolean;
        description
            "Administratively Enable/disable the interface";
      }

      container level {
        description
            "Configure SPB level information";
        leaf level-id {
          type uint32 {
          }
        } //level-id

        container hello-interval {
          description
              "Configure hello-interval for this interface";
          leaf seconds {
            type int32 {
              range "1..20000";
            }
          } //seconds

        } //container hello-interval

        container hello-multiplier {
          description
              "Configure hello-multiplier for this level";
          leaf multiplier {
            type int32 {
              range "2..100";
            }
          } //multiplier

        } //container hello-multiplier

        container metric {
          description
              "Configure IS-IS interface metric for IPv4 unicast";
          leaf ipv4-metric {
            type uint32 {
              range "1..16777215";
            }
          } //ipv4-metric

        } //container metric

      } //container level

    } //container spb

  } //grouping alu-conf-svc-vpls-spb-r13

} //module  alu-conf-svc-vpls-spb-r13
