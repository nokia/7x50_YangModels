module alu-conf-svc-ipfix-r13 {
  yang-version "1";

  namespace "urn:alcatel-lucent.com:sros:ns:yang:conf-svc-ipfix-r13";

  prefix "conf-svc-ipfix-r13";

  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure IP Flow Information Export 
       protocol on SR OS based routers. 
       
       Copyright 2014-2015 Alcatel-Lucent, 2016 Nokia. All rights reserved. 
       Reproduction of this document is authorized on the condition that the 
       foregoing copyright notice is included. 
       
       This alu-conf-svc-ipfix-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2017-10-02";

  grouping alu-conf-svc-ipfix-r13 {
    container ipfix {
      description
          "Configure IP Flow Information Export protocol";
      list ipfix-export-policy {
        key "policy-name";
        description
            "Configure an IPFIX Export policy";
        leaf policy-name {
          type string {
            length "1..32";
          }
          description
              "[32 characters max]";
        } //policy-name

        container description {
          description
              "Configure the description of this policy";
          leaf description-string {
            type string {
              length "1..80";
            }
          } //description-string

        } //container description

        container template-format {
          description
              "Configure the template format used by the IPFIX collectors";
          leaf template-format-id {
            type enumeration {
              enum format1;
              enum format2;
            }
          } //template-format-id

        } //container template-format

        list collector {
          key "router ip";
          description
              "Configure IPFIX for a collector";
          leaf router {
            type string {
              length "1..32";
            }
            description
                "Attribute router-instance for collector";
          } //router

          leaf ip {
            type inet:ip-address;
          } //ip

          container mtu {
            description
                "Configure the Maximum Transmission Unit";
            leaf mtu-id {
              type uint32 {
                range "512..9212";
              }
            } //mtu-id

          } //container mtu

          leaf shutdown {
            type boolean;
            description
                "Enable/disable exporting to this collector";
          }

          container source-address {
            description
                "Configure the source IP address";
            leaf ip-address {
              type inet:ip-address;
            } //ip-address

          } //container source-address

          container template-refresh-timeout {
            description
                "Configure the time in seconds after which IPFIX Templates are resent to this 
                 collector";
            leaf hrs {
              type uint32 {
                range "1..24";
              }
            } //hrs

            leaf min {
              type uint32 {
                range "1..59";
              }
            } //min

            leaf sec {
              type uint32 {
                range "1..59";
              }
            } //sec

            leaf days {
              type uint32 {
              }
            } //days

          } //container template-refresh-timeout

        } //list collector

      } //list ipfix-export-policy

    } //container ipfix

  } //grouping alu-conf-svc-ipfix-r13

} //module  alu-conf-svc-ipfix-r13
