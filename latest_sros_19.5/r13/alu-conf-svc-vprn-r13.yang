module alu-conf-svc-vprn-r13 {
  yang-version "1";

  namespace "urn:alcatel-lucent.com:sros:ns:yang:conf-svc-vprn-r13";

  prefix "conf-svc-vprn-r13";

  import alu-conf-svc-vprn-bgp-r13 {
    prefix "conf-svc-vprn-bgp-r13";
  }
  import alu-conf-svc-vprn-dhcp6-r13 {
    prefix "conf-svc-vprn-dhcp6-r13";
  }
  import alu-conf-svc-vprn-dhcps-r13 {
    prefix "conf-svc-vprn-dhcps-r13";
  }
  import alu-conf-svc-vprn-fspec-r13 {
    prefix "conf-svc-vprn-fspec-r13";
  }
  import alu-conf-svc-vprn-if-r13 {
    prefix "conf-svc-vprn-if-r13";
  }
  import alu-conf-svc-vprn-igmp-r13 {
    prefix "conf-svc-vprn-igmp-r13";
  }
  import alu-conf-svc-vprn-ipt-r13 {
    prefix "conf-svc-vprn-ipt-r13";
  }
  import alu-conf-svc-vprn-isis-r13 {
    prefix "conf-svc-vprn-isis-r13";
  }
  import alu-conf-svc-vprn-l2tp-r13 {
    prefix "conf-svc-vprn-l2tp-r13";
  }
  import alu-conf-svc-vprn-mld-r13 {
    prefix "conf-svc-vprn-mld-r13";
  }
  import alu-conf-svc-vprn-nat-r13 {
    prefix "conf-svc-vprn-nat-r13";
  }
  import alu-conf-svc-vprn-ntp-r13 {
    prefix "conf-svc-vprn-ntp-r13";
  }
  import alu-conf-svc-vprn-nwif-r13 {
    prefix "conf-svc-vprn-nwif-r13";
  }
  import alu-conf-svc-vprn-ospf-r13 {
    prefix "conf-svc-vprn-ospf-r13";
  }
  import alu-conf-svc-vprn-ospf3-r13 {
    prefix "conf-svc-vprn-ospf3-r13";
  }
  import alu-conf-svc-vprn-pim-r13 {
    prefix "conf-svc-vprn-pim-r13";
  }
  import alu-conf-svc-vprn-ptp-r13 {
    prefix "conf-svc-vprn-ptp-r13";
  }
  import alu-conf-svc-vprn-radv-r13 {
    prefix "conf-svc-vprn-radv-r13";
  }
  import alu-conf-svc-vprn-rip-r13 {
    prefix "conf-svc-vprn-rip-r13";
  }
  import alu-conf-svc-vprn-ripng-r13 {
    prefix "conf-svc-vprn-ripng-r13";
  }
  import alu-conf-svc-vprn-spoke-r13 {
    prefix "conf-svc-vprn-spoke-r13";
  }
  import alu-conf-svc-vprn-srcad-r13 {
    prefix "conf-svc-vprn-srcad-r13";
  }
  import alu-conf-svc-vprn-subif-r13 {
    prefix "conf-svc-vprn-subif-r13";
  }
  import alu-conf-svc-vprn-wlan-r13 {
    prefix "conf-svc-vprn-wlan-r13";
  }
  import alu-conf-svc-vprn-wpp-r13 {
    prefix "conf-svc-vprn-wpp-r13";
  }
  import alu-conf-vprn-radprox-r13 {
    prefix "conf-vprn-radprox-r13";
  }
  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure VPRN Services on SR OS based 
       routers. 
       
       Copyright 2014-2015 Alcatel-Lucent, 2016 Nokia. All rights reserved. 
       Reproduction of this document is authorized on the condition that the 
       foregoing copyright notice is included. 
       
       This alu-conf-svc-vprn-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-06-03";

  grouping alu-conf-svc-vprn-r13 {
    list vprn {
      key "service-id";
      description
          "Configure VPRN Services";
      leaf service-id {
        type string;
        description
            "Attribute service-id for vprn";
      } //service-id

      leaf customer {
        type uint32 {
          range "1..2147483647";
        }
      } //customer

      leaf inter-as-mvpn {
        type boolean;
        status "obsolete";
        description
            "keyword - Indicates that VPRN service being configured is used for inter-AS 
             MVPN only";
      } //inter-as-mvpn

      leaf name {
        type string;
        description
            "64-char max";
      } //name

      list aggregate {
        key "ip-prefix-ip-prefix-length";
        description
            "Create/delete an aggregate route";
        leaf ip-prefix-ip-prefix-length {
          type string;
          description
              "Attribute ip-prefix/ip-prefix-length for aggregate";
        } //ip-prefix-ip-prefix-length

        leaf summary-only {
          type boolean;
        } //summary-only

        leaf as-set {
          type boolean;
        } //as-set

        leaf aggregator {
          type string;
          description
              "as-number - [1..4294967295] 
               ip-address - a.b.c.d";
        } //aggregator

        leaf black-hole {
          type boolean;
        } //black-hole

        leaf-list community {
          type string;
          max-elements 12;
          description
              "Attribute comm-id for aggregate";
        } //community

        leaf indirect {
          type string;
        } //indirect

        leaf generate-icmp {
          type boolean;
        } //generate-icmp

        leaf description {
          type string {
            length "1..80";
          }
        } //description

        leaf local-preference {
          type uint32;
        } //local-preference

      } //list aggregate

      leaf allow-export-bgp-vpn {
        type boolean;
        description
            "Allow/Disallow exporting BGP VPN";
      }

      container autonomous-system {
        description
            "Configure the AS number for the vprn service";
        leaf as-number {
          type uint32 {
            range "1..4294967295";
          }
        } //as-number

      } //container autonomous-system

      container bgp-shared-queue {
        description
            "Enable/Disable BGP Shared Queue";
        leaf cir {
          type string;
          description
              "[0..100000000|max] Kbps";
        } //cir

        leaf pir {
          type string;
          description
              "[1..100000000|max] Kbps";
        } //pir

      } //container bgp-shared-queue

      leaf carrier-carrier-vpn {
        type boolean;
        description
            "Configure support for Carrier supporting Carrier VPN";
      }

      container confederation {
        description
            "Create/delete confederation autonomous systems within an AS";
        leaf confed-as-num {
          type uint32 {
            range "1..4294967295";
          }
        } //confed-as-num

        leaf-list members {
          type uint32 {
            range "1..4294967295";
          }
          max-elements 15;
        } //members

      } //container confederation

      list description {
        key "description-string";
        description
            "Description for the service";
        leaf description-string {
          type string {
            length "1..80";
          }
        } //description-string

      } //list description

      leaf disable-selective-fib {
        type boolean;
        description
            "Enable/disable selective FIB";
      }

      container ecmp {
        description
            "Enable/disable ECMP and configure max number of routes for path sharing";
        leaf max-ecmp-routes {
          type string;
          description
              "Attribute max-ecmp-routes for ecmp";
        } //max-ecmp-routes

      } //container ecmp

      container enable-bgp-vpn-backup {
        description
            "Enable/disable BGP vpn backup path";
        leaf ipv4 {
          type boolean;
        } //ipv4

        leaf ipv6 {
          type boolean;
        } //ipv6

      } //container enable-bgp-vpn-backup

      list encryption-keygroup {
        key "direction";
        description
            "Configure the encryption keygroup for the vprn service";
        leaf keygroup-id {
          type string;
          description
              "Attribute keygroup-id for encryption-keygroup";
        } //keygroup-id

        leaf direction {
          type enumeration {
            enum inbound;
            enum outbound;
          }
        } //direction

      } //list encryption-keygroup

      leaf entropy-label {
        type boolean;
        description
            "Enable/disable use of entropy-label";
      }

      leaf export-inactive-bgp {
        type boolean;
        description
            "Allow/Disallow exporting inactive BGP routes";
      }

      container fib-priority {
        description
            "Specify the FIB Priority for VPRN";
        leaf high-standard {
          type enumeration {
            enum high;
            enum standard;
          }
        } //high-standard

      } //container fib-priority

      leaf hash-label {
        type boolean;
        description
            "Enable/disable use of hash-label";
      }

      leaf ignore-nh-metric {
        type boolean;
        description
            "Enable/Disable ignore next-hop metric";
      }

      container label-mode {
        description
            "Specify the mode of allocation of service labels for VPRN";
        leaf vrf-next-hop {
          type enumeration {
            enum vrf;
            enum next-hop;
          }
        } //vrf-next-hop

      } //container label-mode

      container maximum-ipv6-routes {
        description
            "Configure the maximum IPv6 routes for this VRF";
        leaf number {
          type int32 {
            range "1..2147483647";
          }
        } //number

        leaf log-only {
          type boolean;
          description
              "keyword - specifies to not disable learning of new routes if maximum is 
               reached only log the event";
        } //log-only

        leaf threshold {
          type uint32 {
            range "0..100";
          }
        } //threshold

      } //container maximum-ipv6-routes

      container maximum-routes {
        description
            "Configure the max-routes for this VRF";
        leaf number {
          type int32 {
            range "1..2147483647";
          }
        } //number

        leaf log-only {
          type boolean;
          description
              "keyword - specifies to not disable learning of new routes if maximum is 
               reached only log the event";
        } //log-only

        leaf threshold {
          type uint32 {
            range "0..100";
          }
        } //threshold

      } //container maximum-routes

      container mc-maximum-routes {
        description
            "Configure the max multicast routes for this VRF";
        leaf number {
          type uint32 {
            range "1..2147483647";
          }
        } //number

        leaf log-only {
          type boolean;
          description
              "keyword - specifies to not disable learning of new routes if maximum is 
               reached only log the event";
        } //log-only

        leaf threshold {
          type uint32 {
            range "0..100";
          }
        } //threshold

      } //container mc-maximum-routes

      container mss-adjust-group {
        description
            "Configure the ISA-BB group for TCP Maximum Segment Size adjustment";
        leaf bb-group-id {
          type uint32 {
            range "1..4";
          }
        } //bb-group-id

        leaf segment-size {
          type uint32 {
            range "160..10240";
          }
        } //segment-size

      } //container mss-adjust-group

      container multicast-info-policy {
        description
            "Configure multicast information policy";
        leaf policy-name {
          type string {
            length "1..32";
          }
          description
              "[Max 32 chars]";
        } //policy-name

      } //container multicast-info-policy

      container reassembly-group {
        description
            "Configure the ISA-BB group for IP datagram fragment reassembly";
        leaf bb-group-id {
          type uint32 {
            range "1..4";
          }
        } //bb-group-id

      } //container reassembly-group

      container route-distinguisher {
        description
            "Configure route distinguisher";
        leaf rd {
          type string {
            length "1..21";
          }
          description
              "<ip-addr:comm-val>|<2byte-asnumber:ext-comm-val>|<4byte-asnumber:comm-val> 
               ip-addr - a.b.c.d 
               comm-val - [0..65535] 
               2byte-asnumber - [1..65535] 
               ext-comm-val - [0..4294967295] 
               4byte-asnumber - [1..4294967295]";
        } //rd

        leaf auto-rd {
          type boolean;
        } //auto-rd

      } //container route-distinguisher

      container router-id {
        description
            "Configure the router-id for the virtual router";
        leaf ip-address {
          type inet:ip-address;
        } //ip-address

      } //container router-id

      container service-name {
        status "obsolete";
        description
            "Configure a service name";
        leaf service-name {
          type string;
          description
              "64-char max";
        } //service-name

      } //container service-name

      leaf shutdown {
        type boolean;
        description
            "Administratively enable/disable the service";
      }

      container single-sfm-overload {
        description
            "Configure IGP single-sfm overload behavior";
        leaf holdoff-time {
          type uint32 {
            range "1..600";
          }
          description
              "[1..600] seconds";
        } //holdoff-time

      } //container single-sfm-overload

      list static-route {
        key "ip-prefix-prefix-length netmask preference metric tag mcast-family community description";
        status "obsolete";
        description
            "Creates/deletes static route entries";
        leaf ip-prefix-prefix-length {
          type string;
          description
              "Attribute ip-prefix/prefix-length for static-route";
        } //ip-prefix-prefix-length

        leaf netmask {
          type string;
          description
              "a.b.c.d (network bits all 1 and host bits all 0)";
        } //netmask

        leaf next-hop {
          type string;
          description
              "Attribute ip-int-name|ip-address|ipv6-address for static-route";
        } //next-hop

        leaf indirect {
          type string;
          description
              "Attribute ip-address for static-route";
        } //indirect

        leaf black-hole {
          type boolean;
        } //black-hole

        leaf preference {
          type uint16 {
            range "1..255";
          }
        } //preference

        leaf metric {
          type uint32 {
            range "0..65535";
          }
        } //metric

        leaf enable-disable {
          type enumeration {
            enum enable;
            enum disable;
          }
          description
              "keywords - specify state of static-route";
        } //enable-disable

        leaf tag {
          type uint32 {
            range "1..4294967295";
          }
        } //tag

        leaf bfd-enable {
          type boolean;
          description
              "keyword - enables BFD sessions on this static route";
        } //bfd-enable

        leaf cpe-check {
          type string;
          description
              "Attribute cpe-ip-address for static-route";
        } //cpe-check

        leaf interval {
          type uint32 {
            range "1..255";
          }
          default 1;
        } //interval

        leaf drop-count {
          type uint32 {
            range "1..255";
          }
          default 3;
        } //drop-count

        leaf log {
          type boolean;
        } //log

        leaf ipsec-tunnel {
          type string {
            length "1..32";
          }
        } //ipsec-tunnel

        leaf prefix-list {
          type string {
            length "1..32";
          }
        } //prefix-list

        leaf all-none {
          type enumeration {
            enum all;
            enum none;
          }
          description
              "keyword - specify prefix-list to be considered";
        } //all-none

        leaf fc {
          type string;
          description
              "Attribute fc for static-route";
        } //fc

        leaf priority {
          type enumeration {
            enum low;
            enum high;
          }
        } //priority

        leaf mcast-family {
          type enumeration {
            enum mcast-ipv4;
          }
        } //mcast-family

        leaf community {
          type string;
          description
              "[72 chars max] 
               <2 byte-asnumber:comm-val>|<well-known-comm> 
               2 byte-asnumber - [0..65535] 
               comm-val - [0..65535] 
               well-known-comm - no-export|no-export-subconfed| 
               no-advertise";
        } //community

        leaf description {
          type string {
            length "1..80";
          }
        } //description

        leaf padding-size {
          type uint32 {
            range "0..16384";
          }
        } //padding-size

        leaf generate-icmp {
          type boolean;
        } //generate-icmp

        leaf validate-next-hop {
          type boolean;
        } //validate-next-hop

        leaf source-class {
          type uint32 {
            range "1..255";
          }
        } //source-class

        leaf dest-class {
          type uint32 {
            range "1..255";
          }
        } //dest-class

      } //list static-route

      container static-route-hold-down {
        description
            "Enable/Disable hold down time feature globally for the static-routes on the 
             system";
        leaf initial {
          type uint32 {
            range "1..65535";
          }
          default 3600;
        } //initial

        leaf multiplier {
          type uint32 {
            range "1..10";
          }
        } //multiplier

        leaf max-value {
          type uint32 {
            range "1..65535";
          }
          default 3600;
        } //max-value

      } //container static-route-hold-down

      container type {
        description
            "Configure the VPRN type";
        leaf hub-spoke-subscriber-split-horizon {
          type enumeration {
            enum hub;
            enum spoke;
            enum subscriber-split-horizon;
          }
          description
              "keywords";
        } //hub-spoke-subscriber-split-horizon

      } //container type

      container vrf-export {
        description
            "Export route policies used to determine which routes are advertised to all 
             peers";
        leaf-list policy-name {
          type string;
          max-elements 15;
          description
              "Attribute policy-name for vrf-export";
        } //policy-name

        leaf plcy-or-long-expr {
          type string {
            length "1..255";
          }
          description
              "Attribute plcy-or-long-expr for vrf-export";
        } //plcy-or-long-expr

        leaf-list plcy-or-expr {
          type string {
            length "1..64";
          }
          max-elements 14;
          description
              "Attribute plcy-or-expr for vrf-export";
        } //plcy-or-expr

      } //container vrf-export

      container vrf-import {
        description
            "Import route policies used to determine which routes are imported from all 
             peers";
        leaf-list policy-name {
          type string;
          max-elements 15;
          description
              "Attribute policy-name for vrf-import";
        } //policy-name

        leaf plcy-or-long-expr {
          type string {
            length "1..255";
          }
          description
              "Attribute plcy-or-long-expr for vrf-import";
        } //plcy-or-long-expr

        leaf-list plcy-or-expr {
          type string {
            length "1..64";
          }
          max-elements 14;
          description
              "Attribute plcy-or-expr for vrf-import";
        } //plcy-or-expr

      } //container vrf-import

      container vrf-target {
        description
            "Route target to be used for the VPRN";
        leaf ext-community {
          type string;
          description
              "Attribute ext-community for vrf-target";
        } //ext-community

        leaf export {
          type string;
        } //export

        leaf import {
          type string;
        } //import

      } //container vrf-target

      container vsd-domain {
        description
            "Configure the VPRN VSD domain";
        leaf name {
          type string;
        } //name

      } //container vsd-domain

      container weighted-ecmp {
        description
            "Enable/disable weighted ecmp capability";
      }

      list aa-interface {
        key "aa-if-name";
        description
            "Create/delete or configure an AA interface";
        leaf aa-if-name {
          type string {
            length "1..32";
          }
          description
              "[32 chars max] (must start with a letter)";
        } //aa-if-name

        list address {
          key "ip-address-mask";
          description
              "Assigns an IP address to the interface";
          leaf ip-address-mask {
            type string;
          } //ip-address-mask

        } //list address

        container description {
          description
              "Description for an AA interface";
          leaf long-description-string {
            type string {
              length "1..255";
            }
          } //long-description-string

        } //container description

        container ip-mtu {
          description
              "Configure the AA interface IP MTU";
          leaf octets {
            type uint32 {
              range "512..9000";
            }
          } //octets

        } //container ip-mtu

        leaf shutdown {
          type boolean;
          description
              "Administratively enable/disable the interface";
        }

        list sap {
          key "sap-id";
          description
              "Configure a SAP";
          leaf sap-id {
            type string;
            description
                "<sap-id>     : <slot>/<mda>/aa-svc:<vlan> 
                 <slot>     : iom slot (must be IOM3 or above) 
                 <mda>     : isa-aa mda 
                 aa-svc     : keyword 
                 <vlan>     : [1..4094]";
          } //sap-id

          container description {
            description
                "Description for the SAP";
            leaf long-description-string {
              type string {
                length "1..160";
              }
            } //long-description-string

          } //container description

          leaf shutdown {
            type boolean;
            description
                "Administratively enable/disable the SAP";
          }

          container egress {
            description
                "Configure egress parameter";
            list filter {
              key "ip";
              description
                  "Apply egress filter";
              leaf ip {
                type string;
                description
                    "[1..65535]|<name:64 char max>";
              } //ip

            } //list filter

            list qos {
              key "policy-id";
              description
                  "Apply egress qos policy";
              leaf policy-id {
                type string;
                description
                    "[1..65535] | <name : 64 char max>";
              } //policy-id

            } //list qos

          } //container egress

          container ingress {
            description
                "Configure ingress parameter";
            list qos {
              key "policy-id";
              description
                  "Apply ingress qos policy";
              leaf policy-id {
                type string;
                description
                    "[1..65535] | <name : 64 char max>";
              } //policy-id

            } //list qos

          } //container ingress

        } //list sap

      } //list aa-interface

      container aaa {
        description
            "Configure the AAA reachability via VPRN service";
        container remote-servers {
          description
              "Configure the remote-servers";
          container ldap {
            status "obsolete";
            description
                "Configure LDAP authentication parameters for the system";
            leaf public-key-authentication {
              type boolean;
              description
                  "Enable/disable SSH public-key authentication via LDAP";
            }

            container retry {
              description
                  "Number of attempts to retry contacting an LDAP server";
              leaf count {
                type uint32 {
                  range "1..10";
                }
                description
                    "[1..10] - Default 3";
              } //count

            } //container retry

            leaf shutdown {
              type boolean;
              description
                  "Enable/disable LDAP protocol operation";
            }

            container timeout {
              description
                  "Timeout for a response from an LDAP server";
              leaf seconds {
                type uint32 {
                  range "1..90";
                }
                description
                    "[1..90] - Default 3";
              } //seconds

            } //container timeout

            leaf use-default-template {
              type boolean;
              description
                  "Enable/disable LDAP default template";
            }

            list server {
              key "server-index";
              description
                  "Add/remove an LDAP server";
              leaf server-index {
                type uint32 {
                  range "1..5";
                }
              } //server-index

              container address {
                description
                    "Configure LDAP server address";
                leaf ip-address {
                  type string;
                  description
                      "Attribute ip-address for address";
                } //ip-address

                leaf port {
                  type int32 {
                    range "1..65535";
                  }
                  default 389;
                  description
                      "[1..65535] TCP - Default: 389";
                } //port

              } //container address

              container bind-authentication {
                description
                    "Configure LDAP server authentication";
                leaf root-dn {
                  type string {
                    length "1..512";
                  }
                } //root-dn

                leaf password {
                  type string {
                    length "1..500";
                  }
                  description
                      "plain text - [128 chars max] 
                       hash 
                       hash2 
                       custom";
                } //password

                leaf hash-hash2-custom {
                  type enumeration {
                    enum hash;
                    enum hash2;
                    enum custom;
                  }
                } //hash-hash2-custom

              } //container bind-authentication

              container ldap-server {
                description
                    "Configure LDAP server name";
                leaf server-name {
                  type string {
                    length "1..32";
                  }
                } //server-name

              } //container ldap-server

              container search {
                description
                    "Configure LDAP server search domain";
                leaf base-dn {
                  type string {
                    length "1..512";
                  }
                } //base-dn

              } //container search

              leaf shutdown {
                type boolean;
                description
                    "Enable/disable this LDAP server";
              }

              container tls-profile {
                description
                    "Configure TLS client transport profile";
                leaf tls-profile-name {
                  type string {
                    length "1..32";
                  }
                } //tls-profile-name

              } //container tls-profile

            } //list server

          } //container ldap

          container radius {
            description
                "Configure RADIUS authentication parameters for the system";
            container access-algorithm {
              description
                  "Configure the algorithm used to access the set of RADIUS servers";
              leaf direct-round-robin {
                type enumeration {
                  enum direct;
                  enum round-robin;
                }
                description
                    "keywords";
              } //direct-round-robin

            } //container access-algorithm

            leaf accounting {
              type boolean;
              description
                  "Enable/disable RADIUS command accounting";
            }

            container accounting-port {
              description
                  "Port number on which to contact RADIUS server for accounting requests";
              leaf port {
                type string;
                description
                    "[1..65535]";
              } //port

            } //container accounting-port

            leaf authorization {
              type boolean;
              description
                  "Enable/disable RADIUS command authorization";
            }

            leaf interactive-authentication {
              type boolean;
              description
                  "Enable/disable RADIUS interactive authentication";
            }

            container port {
              description
                  "Port number on which to contact RADIUS server";
              leaf port {
                type int32 {
                  range "1..65535";
                }
              } //port

            } //container port

            container retry {
              description
                  "Number of attempts to retry contacting the RADIUS server";
              leaf count {
                type uint32 {
                  range "1..10";
                }
              } //count

            } //container retry

            list server {
              key "server-index";
              description
                  "Add/remove a RADIUS server";
              leaf server-index {
                type uint32 {
                  range "1..5";
                }
              } //server-index

              leaf address {
                type string;
                description
                    "Attribute ip-address for server";
              } //address

              leaf secret {
                type string {
                  length "1..500";
                }
                description
                    "secret-key - [64 chars max] 
                     hash-key 
                     hash2-key 
                     custom-key";
              } //secret

              leaf hash-hash2-custom {
                type enumeration {
                  enum hash;
                  enum hash2;
                  enum custom;
                }
                description
                    "keywords - specify hashing scheme";
              } //hash-hash2-custom

            } //list server

            leaf shutdown {
              type boolean;
              description
                  "Enable/disable RADIUS protocol operation";
            }

            container timeout {
              description
                  "Timeout for a response from the RADIUS server";
              leaf seconds {
                type uint32 {
                  range "1..90";
                }
                default 3;
              } //seconds

            } //container timeout

            leaf use-default-template {
              type boolean;
              description
                  "Enable-disable RADIUS default template";
            }

          } //container radius

          container tacplus {
            description
                "Configure TACACS+ authentication parameters for the system";
            container accounting {
              description
                  "Enable/disable TACACS+ command accounting";
              leaf record-type {
                type enumeration {
                  enum start-stop;
                  enum stop-only;
                }
                description
                    "keywords";
              } //record-type

            } //container accounting

            container authorization {
              description
                  "Enable/disable TACACS+ command authorization";
              leaf use-priv-lvl {
                type boolean;
              } //use-priv-lvl

            } //container authorization

            leaf interactive-authentication {
              type boolean;
              description
                  "Enable/disable TACACS+ interactive authentication";
            }

            list server {
              key "server-index";
              description
                  "Add/remove a TACACS+ server";
              leaf server-index {
                type uint32 {
                  range "1..5";
                }
              } //server-index

              leaf address {
                type string;
                description
                    "Attribute ip-address for server";
              } //address

              leaf secret {
                type string {
                  length "1..500";
                }
                description
                    "secret-key - [128 chars max] 
                     hash-key 
                     hash2-key 
                     custom-key";
              } //secret

              leaf hash-hash2-custom {
                type enumeration {
                  enum hash;
                  enum hash2;
                  enum custom;
                }
                description
                    "keywords - specify hashing scheme";
              } //hash-hash2-custom

              leaf port {
                type uint16;
                default 49;
              } //port

            } //list server

            leaf shutdown {
              type boolean;
              description
                  "Enable/disable TACACS+ protocol operation";
            }

            container timeout {
              description
                  "Timeout for a response from the TACACS+ server";
              leaf seconds {
                type uint32 {
                  range "1..90";
                }
                default 3;
              } //seconds

            } //container timeout

            leaf use-default-template {
              type boolean;
              description
                  "Enable/disable TACACS+ default template";
            }

            container priv-lvl-map {
              presence
                  "Configure privilege level mapping";
              list priv-lvl {
                key "priv-lvl";
                description
                    "Configure a user profile for this privilege level";
                leaf priv-lvl {
                  type uint32 {
                    range "0..15";
                  }
                } //priv-lvl

                leaf user-profile-name {
                  type string {
                    length "1..32";
                  }
                } //user-profile-name

              } //list priv-lvl

            } //container priv-lvl-map

          } //container tacplus

        } //container remote-servers

      } //container aaa

      list aarp-interface {
        key "aarp-int-name";
        description
            "Create/delete or configure an AARP interface";
        leaf aarp-int-name {
          type string {
            length "1..32";
          }
          description
              "[32 chars max] (must start with a letter)";
        } //aarp-int-name

        container description {
          description
              "Description for an AARP interface";
          leaf long-description-string {
            type string {
              length "1..255";
            }
          } //long-description-string

        } //container description

        container ip-mtu {
          description
              "Configure the interface IP MTU";
          leaf octets {
            type uint32 {
              range "512..9000";
            }
          } //octets

        } //container ip-mtu

        leaf shutdown {
          type boolean;
          description
              "Administratively enable/disable the interface";
        }

        list spoke-sdp {
          key "sdp-id-vc-id";
          description
              "Provision a spoke SDP binding";
          leaf sdp-id-vc-id {
            type string;
            description
                "sdp-id - [1..32767] 
                 vc-id - [1..4294967295]";
          } //sdp-id-vc-id

          container aarp {
            description
                "Configure AARP instance id";
            leaf aarpId {
              type uint32 {
                range "1..65535";
              }
            } //aarpId

            leaf type {
              type enumeration {
                enum subscriber-side-shunt;
                enum network-side-shunt;
              }
            } //type

          } //container aarp

          container description {
            description
                "Set description for spoke-sdp";
            leaf description-string {
              type string {
                length "1..80";
              }
            } //description-string

          } //container description

          leaf shutdown {
            type boolean;
            description
                "Administratively enable/disable the spoke SDP binding";
          }

          container egress {
            description
                "Spoke SDP egress configuration";
            container filter {
              description
                  "Apply egress filter";
              leaf ip {
                type string;
                description
                    "[1..65535]|<name:64 char max>";
              } //ip

            } //container filter

            list vc-label {
              key "egress-vc-label";
              description
                  "Configure egress VC label";
              leaf egress-vc-label {
                type int32 {
                  range "16..1048575";
                }
              } //egress-vc-label

            } //list vc-label

          } //container egress

          container ingress {
            description
                "Spoke SDP ingress configuration";
            container filter {
              description
                  "Apply ingress filter";
              leaf ip {
                type string;
                description
                    "[1..65535]|<name:64 char max>";
              } //ip

            } //container filter

            list vc-label {
              key "ingress-vc-label";
              description
                  "Configure ingress VC label";
              leaf ingress-vc-label {
                type string;
                description
                    "Attribute ingress-vc-label for vc-label";
              } //ingress-vc-label

            } //list vc-label

          } //container ingress

        } //list spoke-sdp

      } //list aarp-interface

      container auto-bind-tunnel {
        description
            "Configure auto-bind-tunnel information";
        container ecmp {
          description
              "Configure maximum ECMP routes information";
          leaf max-ecmp-routes {
            type string;
            description
                "[1..32]: default 1";
          } //max-ecmp-routes

        } //container ecmp

        leaf enforce-strict-tunnel-tagging {
          type boolean;
          description
              "Enable/Disable Use of admin-tags for resolving routes for this service";
        }

        container resolution {
          description
              "Configure resolution method for tunnel selection";
          leaf disabled-any-filter {
            type enumeration {
              enum disabled;
              enum any;
              enum filter;
            }
          } //disabled-any-filter

        } //container resolution

        leaf weighted-ecmp {
          type boolean;
          description
              "Enable/disable weighted ecmp capability";
        }

        container resolution-filter {
          description
              "Configure auto-bind-tunnel resolution filter information";
          leaf bgp {
            type boolean;
            description
                "Enable/disable setting BGP type for auto-bind-tunnel";
          }

          leaf gre {
            type boolean;
            description
                "Enable/disable setting GRE type for auto-bind-tunnel";
          }

          leaf ldp {
            type boolean;
            description
                "Enable/disable setting LDP type for auto-bind-tunnel";
          }

          leaf mpls-fwd-policy {
            type boolean;
            description
                "Enable/disable MPLS Forwarding Policy for auto-bind-tunnel";
          }

          leaf rib-api {
            type boolean;
            description
                "Enable/disable setting RIB-API type for auto-bind-tunnel";
          }

          leaf rsvp {
            type boolean;
            description
                "Enable/disable setting RSVP-TE type for auto-bind-tunnel";
          }

          leaf sr-isis {
            type boolean;
            description
                "Enable/disable setting SR-ISIS type for auto-bind-tunnel";
          }

          leaf sr-ospf {
            type boolean;
            description
                "Enable/disable setting SR-OSPF type for auto-bind-tunnel";
          }

          leaf sr-ospf3 {
            type boolean;
            description
                "Enable/disable setting SR-OSPF3 type for auto-bind-tunnel";
          }

          leaf sr-policy {
            type boolean;
            description
                "Enable/disable SR-Policy type for auto-bind-tunnel";
          }

          leaf sr-te {
            type boolean;
            description
                "Enable/disable setting SR-TE type for auto-bind-tunnel";
          }

          leaf udp {
            type boolean;
            description
                "Enable/disable setting UDP type for auto-bind-tunnel";
          }

        } //container resolution-filter

      } //container auto-bind-tunnel

      uses "conf-svc-vprn-bgp-r13:alu-conf-svc-vprn-bgp-r13";
      uses "conf-svc-vprn-dhcps-r13:alu-conf-svc-vprn-dhcps-r13";
      uses "conf-svc-vprn-dhcp6-r13:alu-conf-svc-vprn-dhcp6-r13";
      container dns {
        presence
            "Configure Domain Name Servers";
        container ipv4-source-address {
          description
              "Configure the IPv4 DNS source address";
          leaf ipv4-address {
            type inet:ip-address;
            description
                "a.b.c.d";
          } //ipv4-address

        } //container ipv4-source-address

        container ipv6-source-address {
          description
              "Configure the IPv6 DNS source address";
          leaf ipv6-source-address-id {
            type inet:ipv6-address;
            description
                "ipv6-address";
          } //ipv6-source-address-id

        } //container ipv6-source-address

        container primary-dns {
          description
              "Configure the primary Domain Name Server address";
          leaf ip-address {
            type string;
            description
                "Attribute ip-address for primary-dns";
          } //ip-address

        } //container primary-dns

        container secondary-dns {
          description
              "Configure the secondary Domain Name Server address";
          leaf secondary-dns-string {
            type string;
            description
                "ip-address";
          } //secondary-dns-string

        } //container secondary-dns

        leaf shutdown {
          type boolean;
          description
              "Enable or disable DNS";
        }

        container tertiary-dns {
          description
              "Configure the tertiary Domain Name Server address";
          leaf tertiary-dns-string {
            type string;
            description
                "ip-address";
          } //tertiary-dns-string

        } //container tertiary-dns

      } //container dns

      container eth-cfm {
        description
            "Configure CFM parameters";
        container tunnel-fault {
          description
              "Accept/Ignore tunnel fault notification";
          leaf tunnel-fault-id {
            type enumeration {
              enum accept;
              enum ignore;
            }
          } //tunnel-fault-id

        } //container tunnel-fault

      } //container eth-cfm

      container firewall {
        description
            "Configure the IPv6 firewall";
        list domain {
          key "domain-name";
          description
              "Configure firewall domains";
          leaf domain-name {
            type string;
          } //domain-name

          leaf nat-group {
            type uint32 {
              range "1..4";
            }
          } //nat-group

          container dhcp6-server {
            description
                "Configure the DHCPv6 server";
            leaf router {
              type string {
                length "1..32";
              }
              description
                  "Attribute router-name for dhcp6-server";
            } //router

            leaf name {
              type string;
            } //name

          } //container dhcp6-server

          leaf shutdown {
            type boolean;
            description
                "Administratively disable the domain";
          }

          list prefix {
            key "prefix-prefix-length";
            description
                "Configure IPv6 prefixes";
            leaf prefix-prefix-length {
              type string;
              description
                  "Attribute prefix/prefix-length for prefix";
            } //prefix-prefix-length

            container description {
              description
                  "Configure a description";
              leaf description-string {
                type string {
                  length "1..80";
                }
              } //description-string

            } //container description

          } //list prefix

        } //list domain

      } //container firewall

      uses "conf-svc-vprn-fspec-r13:alu-conf-svc-vprn-fspec-r13";
      container grt-lookup {
        description
            "Configure global route table lookup";
        container export-grt {
          description
              "Export route policies used to determine which routes are exported to GRT";
          leaf-list policy-name {
            type string;
            max-elements 5;
            description
                "Attribute policy-name for export-grt";
          } //policy-name

          leaf plcy-or-long-expr {
            type string {
              length "1..255";
            }
            description
                "Attribute plcy-or-long-expr for export-grt";
          } //plcy-or-long-expr

          leaf-list plcy-or-expr {
            type string {
              length "1..64";
            }
            max-elements 4;
            description
                "Attribute plcy-or-expr for export-grt";
          } //plcy-or-expr

        } //container export-grt

        container export-limit {
          description
              "Maximum number of routes that can be exported";
          leaf num-routes {
            type int32 {
              range "0..1000";
            }
          } //num-routes

        } //container export-limit

        container export-v6-limit {
          description
              "Maximum number of IPv6 routes that can be exported";
          leaf num-routes {
            type int32 {
              range "0..1000";
            }
          } //num-routes

        } //container export-v6-limit

        container import-grt {
          description
              "Import route policies used to determine which routes are imported from GRT";
          leaf-list policy-name {
            type string;
            max-elements 5;
            description
                "Attribute policy-name for import-grt";
          } //policy-name

          leaf plcy-or-long-expr {
            type string {
              length "1..255";
            }
            description
                "Attribute plcy-or-long-expr for import-grt";
          } //plcy-or-long-expr

          leaf-list plcy-or-expr {
            type string {
              length "1..64";
            }
            max-elements 4;
            description
                "Attribute plcy-or-expr for import-grt";
          } //plcy-or-expr

        } //container import-grt

        container enable-grt {
          presence
              "Enable/disable global route table lookup";
          leaf allow-local-management {
            type boolean;
            description
                "Enable/disable management traffic from GRT-leaking enabled VPRN instances to 
                 reach local interfaces in the base routing instance";
          }

          container static-route {
            status "obsolete";
            description
                "Create/delete static route entries";
            leaf ip-prefix-prefix-length {
              type string;
              description
                  "Attribute ip-prefix[/prefix-length] for static-route";
            } //ip-prefix-prefix-length

            leaf netmask {
              type string;
              description
                  "a.b.c.d (network bits all 1 and host bits all 0)";
            } //netmask

            leaf preference {
              type uint16 {
                range "1..255";
              }
            } //preference

            leaf metric {
              type uint32 {
                range "0..65535";
              }
            } //metric

            leaf enable-disable {
              type enumeration {
                enum enable;
                enum disable;
              }
              description
                  "keywords - specify state of static-route";
            } //enable-disable

            leaf grt {
              type boolean;
              description
                  "keyword - global route table lookup";
            } //grt

          } //container static-route

        } //container enable-grt

      } //container grt-lookup

      container gsmp {
        description
            "Configure GSMP connections maintained in this service";
        leaf shutdown {
          type boolean;
          description
              "Administratively enable/disable GSMP";
        }

        list group {
          key "name";
          description
              "Provision a GSMP neighbor group";
          leaf name {
            type string {
              length "1..32";
            }
          } //name

          container description {
            description
                "Description for the GSMP group";
            leaf description-string {
              type string {
                length "1..80";
              }
            } //description-string

          } //container description

          container hold-multiplier {
            description
                "Configure hold-multiplier for the GSMP connections in this group";
            leaf multiplier {
              type uint32 {
                range "1..100";
              }
            } //multiplier

          } //container hold-multiplier

          leaf idle-filter {
            type boolean;
            description
                "enable/disable filtering ANCP messages from IDLE DSL lines";
          }

          container keepalive {
            description
                "Configure keepalive value for the GSMP connections in this group";
            leaf seconds {
              type uint32 {
                range "1..25";
              }
            } //seconds

          } //container keepalive

          leaf persistency-database {
            type boolean;
            description
                "enable/disable storing of DSL line information when the GSMP connection 
                 terminates";
          }

          leaf shutdown {
            type boolean;
            description
                "Administratively enable/disable the GSMP group";
          }

          container ancp {
            presence
                "configure ANCP parameters for this GSMP group";
            leaf dynamic-topology-discover {
              type boolean;
              description
                  "Enable/disable the ANCP dynamic topology discovery capability";
            }

            leaf oam {
              type boolean;
              description
                  "Enable/disable the ANCP OAM capability";
            }

          } //container ancp

          list neighbor {
            key "ip-address";
            description
                "Add/remove a neighbor in the GSMP group";
            leaf ip-address {
              type inet:ip-address;
              description
                  "ip-address a.b.c.d ( unicast address only)";
            } //ip-address

            container description {
              description
                  "Description for the GSMP neighbor";
              leaf description-string {
                type string {
                  length "1..80";
                }
              } //description-string

            } //container description

            container local-address {
              description
                  "Configure the local address for this neighbor";
              leaf ip-address {
                type inet:ip-address;
                description
                    "ip-address a.b.c.d ( unicast address only)";
              } //ip-address

            } //container local-address

            container priority-marking {
              description
                  "Configure the type of priority marking to be used";
              leaf prec {
                type int32 {
                  range "0..7";
                }
              } //prec

              leaf dscp {
                type string {
                  length "1..32";
                }
                description
                    "Attribute dscp-name for priority-marking";
              } //dscp

            } //container priority-marking

            leaf shutdown {
              type boolean;
              description
                  "Administratively enable/disable the neighbor";
            }

          } //list neighbor

        } //list group

      } //container gsmp

      container gtp {
        description
            "Configure GTP";
        container s11 {
          description
              "Configure the S11 interface for GTP";
          list interface {
            key "interface-name";
            description
                "Configure the S11 interface name";
            leaf interface-name {
              type string {
                length "1..32";
              }
              description
                  "[32 chars max] (must start with a letter)";
            } //interface-name

            container apn-policy {
              description
                  "Configure the APN policy for the S11 interface";
              leaf apn-policy-name {
                type string {
                  length "1..32";
                }
              } //apn-policy-name

            } //container apn-policy

          } //list interface

          container peer-profile-map {
            description
                "Configure a peer profile map";
            list address {
              key "ip-prefix-ip-prefix-length";
              description
                  "Configure a peer profile map address";
              leaf ip-prefix-ip-prefix-length {
                type string;
                description
                    "Attribute ip-prefix/ip-prefix-length for address";
              } //ip-prefix-ip-prefix-length

              leaf peer-profile {
                type string;
              } //peer-profile

            } //list address

          } //container peer-profile-map

        } //container s11

        container uplink {
          presence
              "Configure the uplink for GTP";
          container apn {
            description
                "Configure the Network Identifier part of the APN";
            leaf apn {
              type string {
                length "1..80";
              }
            } //apn

          } //container apn

          container pdn-type {
            description
                "Configure the default 3GPP-PDN type";
            leaf pdn-type-id {
              type enumeration {
                enum ipv4;
                enum ipv6;
                enum ipv4v6;
              }
            } //pdn-type-id

          } //container pdn-type

          container peer-profile-map {
            description
                "Configure a peer profile map";
            list address {
              key "ip-prefix-ip-prefix-length";
              description
                  "Configure a peer profile map address";
              leaf ip-prefix-ip-prefix-length {
                type string;
                description
                    "Attribute ip-prefix/ip-prefix-length for address";
              } //ip-prefix-ip-prefix-length

              leaf peer-profile {
                type string;
              } //peer-profile

            } //list address

          } //container peer-profile-map

        } //container uplink

      } //container gtp

      uses "conf-svc-vprn-igmp-r13:alu-conf-svc-vprn-igmp-r13";
      container igmp-host-tracking {
        description
            "Configure IGMP host tracking";
        container expiry-time {
          description
              "Configure the time that the system continues to track inactive hosts";
          leaf expiry-time {
            type uint32 {
              range "1..65535";
            }
            description
                "[1..65535] seconds";
          } //expiry-time

        } //container expiry-time

        leaf shutdown {
          type boolean;
          description
              "Administratively enable/disable IGMP host tracking";
        }

      } //container igmp-host-tracking

      uses "conf-svc-vprn-if-r13:alu-conf-svc-vprn-if-r13";
      list ip-mirror-interface {
        key "ip-int-name";
        description
            "Create/delete or configure an IP Mirror interface";
        leaf ip-int-name {
          type string {
            length "1..32";
          }
          description
              "[32 chars max] (must start with a letter)";
        } //ip-int-name

        container description {
          description
              "Description for VPRN ip-mirror interface";
          leaf long-description-string {
            type string {
              length "1..255";
            }
          } //long-description-string

        } //container description

        leaf shutdown {
          type boolean;
          description
              "Administratively enable/disable the interface";
        }

        list spoke-sdp {
          key "sdp-id-vc-id";
          description
              "Provision a spoke SDP binding";
          leaf sdp-id-vc-id {
            type string;
            description
                "sdp-id - [1..32767] 
                 vc-id - [1..4294967295]";
          } //sdp-id-vc-id

          container description {
            description
                "Set description for spoke-sdp";
            leaf description-string {
              type string {
                length "1..80";
              }
              description
                  "80 char max";
            } //description-string

          } //container description

          leaf shutdown {
            type boolean;
            description
                "Administratively enable/disable the spoke SDP binding";
          }

          container ingress {
            description
                "Spoke SDP ingress configuration";
            container filter {
              description
                  "Apply ingress filter";
              leaf ip {
                type string;
                description
                    "[1..65535]|<name:64 char max>";
              } //ip

            } //container filter

            list vc-label {
              key "ingress-vc-label";
              description
                  "Configure ingress VC label";
              leaf ingress-vc-label {
                type string;
                description
                    "Attribute ingress-vc-label for vc-label";
              } //ingress-vc-label

            } //list vc-label

          } //container ingress

        } //list spoke-sdp

      } //list ip-mirror-interface

      uses "conf-svc-vprn-ipt-r13:alu-conf-svc-vprn-ipt-r13";
      container ipsec {
        description
            "Configure IPsec Policies";
        leaf allow-reverse-route-override {
          type boolean;
          description
              "Enable/disable overridding the reverse route";
        }

        list security-policy {
          key "security-policy-id";
          description
              "Configure IPsec security policy";
          leaf security-policy-id {
            type string;
            description
                "Attribute security-policy-id for security-policy";
          } //security-policy-id

          list entry {
            key "entry-id";
            description
                "Configure IPsec security policy params";
            leaf entry-id {
              type uint32 {
                range "1..16";
              }
            } //entry-id

            container local-ip {
              description
                  "Configure local Ip prefix/mask for this policy param entry";
              leaf ip-prefix-prefix-length {
                type inet:ip-prefix;
                description
                    "ip-prefix - a.b.c.d 
                     host bits must be 0 
                     0.0.0.0 not allowed 
                     prefix-length [1..32]";
              } //ip-prefix-prefix-length

              leaf netmask {
                type string;
                description
                    "a.b.c.d (network bits all 1 and host bits all 0) 
                     0.0.0.0 not allowed";
              } //netmask

              leaf any {
                type boolean;
                description
                    "keyword to specify that it can be any address";
              } //any

            } //container local-ip

            container local-v6-ip {
              description
                  "Configure local IPv6 prefix/mask for this policy param entry";
              leaf ipv6-prefix-prefix-length {
                type string;
                description
                    "ipv6-prefix x:x:x:x:x:x:x:x (eight 16-bit pieces) 
                     x:x:x:x:x:x:d.d.d.d 
                     x [0..FFFF]H 
                     d [0..255]D 
                     host bits must be 0 
                     :: not allowed 
                     prefix-length [1..128]";
              } //ipv6-prefix-prefix-length

              leaf any {
                type boolean;
                description
                    "keyword to specify that it can be any address";
              } //any

            } //container local-v6-ip

            container remote-ip {
              description
                  "Configure remote Ip prefix/mask for this policy param entry";
              leaf ip-prefix-prefix-length {
                type inet:ip-prefix;
                description
                    "ip-prefix - a.b.c.d 
                     host bits must be 0 
                     0.0.0.0 not allowed 
                     prefix-length [1..32]";
              } //ip-prefix-prefix-length

              leaf netmask {
                type string;
                description
                    "a.b.c.d (network bits all 1 and host bits all 0) 
                     0.0.0.0 not allowed";
              } //netmask

              leaf any {
                type boolean;
                description
                    "keyword to specify that it can be any address";
              } //any

            } //container remote-ip

            container remote-v6-ip {
              description
                  "Configure remote IPv6 prefix/mask for this policy param entry";
              leaf ipv6-prefix-prefix-length {
                type string;
                description
                    "ipv6-prefix x:x:x:x:x:x:x:x (eight 16-bit pieces) 
                     x:x:x:x:x:x:d.d.d.d 
                     x [0..FFFF]H 
                     d [0..255]D 
                     host bits must be 0 
                     :: not allowed 
                     prefix-length [1..128]";
              } //ipv6-prefix-prefix-length

              leaf any {
                type boolean;
                description
                    "keyword to specify that it can be any address";
              } //any

            } //container remote-v6-ip

          } //list entry

        } //list security-policy

      } //container ipsec

      container ipv6 {
        description
            "Configure IPv6";
        container reachable-time {
          description
              "Configure neighbor reachability detection timer";
          leaf seconds {
            type uint32 {
              range "30..3600";
            }
          } //seconds

        } //container reachable-time

        container stale-time {
          description
              "Configure the time a neighbor discovery cache entry can remain stale before 
               being removed";
          leaf seconds {
            type uint32 {
              range "60..65535";
            }
          } //seconds

        } //container stale-time

      } //container ipv6

      uses "conf-svc-vprn-isis-r13:alu-conf-svc-vprn-isis-r13";
      uses "conf-svc-vprn-l2tp-r13:alu-conf-svc-vprn-l2tp-r13";
      container log {
        description
            "Event stream logging configuration";
        list filter {
          key "filter-id";
          description
              "Configure an event filter";
          leaf filter-id {
            type uint32 {
              range "1..1500";
            }
          } //filter-id

          container default-action {
            description
                "Specify the default action for the event filter";
            leaf drop-forward {
              type enumeration {
                enum drop;
                enum forward;
              }
              description
                  "keywords - specify match action";
            } //drop-forward

          } //container default-action

          container description {
            description
                "Description string for the event filter";
            leaf description-string {
              type string {
                length "1..80";
              }
            } //description-string

          } //container description

          list entry {
            key "entry-id";
            description
                "Configure an event filter entry";
            leaf entry-id {
              type uint32 {
                range "1..999";
              }
            } //entry-id

            container action {
              description
                  "Specify the action for this event filter entry";
              leaf drop-forward {
                type enumeration {
                  enum drop;
                  enum forward;
                }
                description
                    "keywords - specify match action";
              } //drop-forward

            } //container action

            container description {
              description
                  "Description for this event filter entry";
              leaf description-string {
                type string {
                  length "1..80";
                }
              } //description-string

            } //container description

            container match {
              presence
                  "Specify match conditions for this event filter entry";
              container application {
                description
                    "Specify application id to match";
                leaf eq-neq {
                  type enumeration {
                    enum eq;
                    enum neq;
                  }
                  description
                      "operator";
                } //eq-neq

                leaf application-id {
                  type string {
                    length "1..32";
                  }
                  description
                      "Attribute application-id for application";
                } //application-id

              } //container application

              container message {
                description
                    "Specify pattern to match message";
                leaf eq-neq {
                  type enumeration {
                    enum eq;
                    enum neq;
                  }
                } //eq-neq

                leaf pattern {
                  type string {
                    length "1..400";
                  }
                } //pattern

                leaf regexp {
                  type boolean;
                  description
                      "keyword: use regular expression match";
                } //regexp

              } //container message

              container number {
                description
                    "Specify event-id number to match";
                leaf eq-neq-lt-lte-gt-gte {
                  type enumeration {
                    enum eq;
                    enum neq;
                    enum lt;
                    enum lte;
                    enum gt;
                    enum gte;
                  }
                  description
                      "operator";
                } //eq-neq-lt-lte-gt-gte

                leaf event-id {
                  type uint32 {
                    range "1..4294967295";
                  }
                } //event-id

              } //container number

              container severity {
                description
                    "Specify severity level to match";
                leaf eq-neq-lt-lte-gt-gte {
                  type enumeration {
                    enum eq;
                    enum neq;
                    enum lt;
                    enum lte;
                    enum gt;
                    enum gte;
                  }
                  description
                      "operator";
                } //eq-neq-lt-lte-gt-gte

                leaf severity-level {
                  type enumeration {
                    enum cleared;
                    enum indeterminate;
                    enum critical;
                    enum major;
                    enum minor;
                    enum warning;
                  }
                } //severity-level

              } //container severity

              container subject {
                description
                    "Specify subject string to match";
                leaf eq-neq {
                  type enumeration {
                    enum eq;
                    enum neq;
                  }
                  description
                      "operator";
                } //eq-neq

                leaf subject {
                  type string {
                    length "1..32";
                  }
                } //subject

                leaf regexp {
                  type boolean;
                  description
                      "keyword: use regular expression match";
                } //regexp

              } //container subject

            } //container match

          } //list entry

        } //list filter

        list log-id {
          key "log-id";
          description
              "Configure an event log destination";
          leaf log-id {
            type uint16 {
              range "1..100";
            }
          } //log-id

          container description {
            description
                "Description for this log-id";
            leaf description-string {
              type string {
                length "1..80";
              }
            } //description-string

          } //container description

          container filter {
            description
                "Specify filter to be used";
            leaf filter-id {
              type uint32 {
                range "1..1001";
              }
            } //filter-id

          } //container filter

          container from {
            description
                "Specify the source event stream directed to this destination";
            leaf main {
              type boolean;
              description
                  "keyword - specifies 'main' source stream";
            } //main

            leaf change {
              type boolean;
              description
                  "keyword - specifies 'change' source stream";
            } //change

          } //container from

          container netconf-stream {
            description
                "Configure a NETCONF stream";
            leaf stream-name {
              type string;
            } //stream-name

          } //container netconf-stream

          container python-policy {
            description
                "Configure a Python policy to process syslog messages";
            leaf policy-name {
              type string;
            } //policy-name

          } //container python-policy

          leaf shutdown {
            type boolean;
            description
                "Administratively enable/disable the event log";
          }

          container time-format {
            description
                "Specify whether time should be displayed in local or UTC";
            leaf local-utc {
              type enumeration {
                enum local;
                enum utc;
              }
              default "utc";
              description
                  "keywords (Default - utc)";
            } //local-utc

          } //container time-format

          container to {
            description
                "Configure the destination type for this event log";
            leaf syslog {
              type uint16 {
                range "1..30";
              }
            } //syslog

            leaf snmp {
              type boolean;
              description
                  "keyword - specifies SNMP as destination";
            } //snmp

            leaf netconf {
              type boolean;
              description
                  "keyword - specifies NETCONF as destination";
            } //netconf

            leaf size {
              type uint16 {
                range "50..3000";
              }
              default 100;
            } //size

          } //container to

        } //list log-id

        list snmp-trap-group {
          key "log-id";
          description
              "Configure SNMP trap receivers and their operational parameters for a given 
               log-id";
          leaf log-id {
            type uint16 {
              range "1..100";
            }
          } //log-id

          container description {
            description
                "Description for this SNMP trap group";
            leaf description-string {
              type string {
                length "1..80";
              }
            } //description-string

          } //container description

          list trap-target {
            key "name";
            description
                "Configure SNMP notification receiver and operation parameters";
            leaf name {
              type string {
                length "1..28";
              }
            } //name

            leaf address {
              type string;
              description
                  "Attribute ip-address for trap-target";
            } //address

            leaf port {
              type uint16;
              default 162;
              description
                  "[0..65535] Default: 162";
            } //port

            leaf snmpv1-snmpv2c-snmpv3 {
              type enumeration {
                enum snmpv1;
                enum snmpv2c;
                enum snmpv3;
              }
              default "snmpv3";
              description
                  "keywords - specify message processing model 
                   Default: snmpv3";
            } //snmpv1-snmpv2c-snmpv3

            leaf notify-community {
              type string {
                length "1..31";
              }
            } //notify-community

            leaf security-level {
              type enumeration {
                enum no-auth-no-privacy;
                enum auth-no-privacy;
                enum privacy;
              }
            } //security-level

            leaf replay {
              type boolean;
              description
                  "keyword - enable retransmit of missed notifications";
            } //replay

          } //list trap-target

        } //list snmp-trap-group

        list syslog {
          key "syslog-id";
          description
              "Configure a target syslog host";
          leaf syslog-id {
            type uint16 {
              range "1..30";
            }
          } //syslog-id

          container address {
            description
                "Specify target syslog host address";
            leaf ip-address {
              type string;
              description
                  "Attribute ip-address for address";
            } //ip-address

          } //container address

          container description {
            description
                "Description for this target syslog host";
            leaf description-string {
              type string {
                length "1..80";
              }
            } //description-string

          } //container description

          container facility {
            description
                "Configure the facility code that is used for the messages associated with this 
                 syslog-id";
            leaf syslog-facility {
              type enumeration {
                enum kernel;
                enum user;
                enum mail;
                enum systemd;
                enum auth;
                enum syslogd;
                enum printer;
                enum netnews;
                enum uucp;
                enum cron;
                enum authpriv;
                enum ftp;
                enum ntp;
                enum logaudit;
                enum logalert;
                enum cron2;
                enum local0;
                enum local1;
                enum local2;
                enum local3;
                enum local4;
                enum local5;
                enum local6;
                enum local7;
              }
            } //syslog-facility

          } //container facility

          container level {
            description
                "Configure the syslog message severity level threshold";
            leaf syslog-level {
              type enumeration {
                enum emergency;
                enum alert;
                enum critical;
                enum error;
                enum warning;
                enum notice;
                enum info;
                enum debug;
              }
            } //syslog-level

          } //container level

          container log-prefix {
            description
                "Configure a string to be prepended to every log message sent to the target 
                 syslog host";
            leaf log-prefix-string {
              type string {
                length "1..32";
              }
            } //log-prefix-string

          } //container log-prefix

          container port {
            description
                "Configure the UDP port used to generate syslog messages";
            leaf port {
              type uint16;
            } //port

          } //container port

        } //list syslog

      } //container log

      container management {
        description
            "Configure the node management via VPRN service";
        leaf allow-ftp {
          type boolean;
          description
              "Allow/disallow access to ftp server";
        }

        leaf allow-grpc {
          type boolean;
          description
              "Allow/disallow access to grpc server";
        }

        leaf allow-netconf {
          type boolean;
          description
              "Allow/disallow access to NETCONF server";
        }

        leaf allow-ssh {
          type boolean;
          description
              "Allow/disallow access to SSH server";
        }

        leaf allow-telnet {
          type boolean;
          description
              "Allow/disallow access to telnet server";
        }

        leaf allow-telnet6 {
          type boolean;
          description
              "Allow/disallow access to telnet IPv6 server";
        }

        leaf telnet-server {
          type boolean;
          status "obsolete";
          description
              "Start/Stop telnet server";
        }

        leaf telnet6-server {
          type boolean;
          status "obsolete";
          description
              "Start/Stop telnet IPv6 server";
        }

        container ssh {
          status "obsolete";
          description
              "Configure SSH parameters";
          leaf server-shutdown {
            type boolean;
            status "obsolete";
            description
                "start/stop SSH server";
          }

        } //container ssh

      } //container management

      uses "conf-svc-vprn-mld-r13:alu-conf-svc-vprn-mld-r13";
      container msdp {
        presence
            "Create/Configure or delete MSDP instance";
        container active-source-limit {
          description
              "Configure maximum number of active source messages accepted by MSDP";
          leaf number {
            type int32 {
              range "0..1000000";
            }
          } //number

        } //container active-source-limit

        leaf data-encapsulation {
          type boolean;
          description
              "Enable/Disable encapsulation of multicast data used by MSDP";
        }

        container export {
          description
              "Configure policies to export Source Active state from the Source Active list 
               into MSDP";
          leaf-list policy-name {
            type string {
              length "1..32";
            }
            max-elements 5;
          } //policy-name

        } //container export

        container import {
          description
              "Configure policies to import Source Active state from the Source Active list 
               into MSDP";
          leaf-list policy-name {
            type string {
              length "1..32";
            }
            max-elements 5;
          } //policy-name

        } //container import

        container local-address {
          description
              "Configure the local end of an MSDP session";
          leaf ip-address {
            type inet:ip-address;
            description
                "[a.b.c.d]";
          } //ip-address

        } //container local-address

        container receive-msdp-msg-rate {
          description
              "Configure number of messages MSDP can read";
          leaf number {
            type uint32 {
              range "10..10000";
            }
          } //number

          leaf interval {
            type uint32 {
              range "1..600";
            }
          } //interval

          leaf threshold {
            type uint32 {
              range "1..1000000";
            }
          } //threshold

        } //container receive-msdp-msg-rate

        container rpf-table {
          description
              "Configure the route table(s) for RPF lookup";
          leaf rtable-m-rtable-u-both {
            type enumeration {
              enum rtable-m;
              enum rtable-u;
              enum both;
            }
            description
                "keywords";
          } //rtable-m-rtable-u-both

        } //container rpf-table

        container sa-timeout {
          description
              "Configure a MSDP SA-timeout";
          leaf seconds {
            type uint32 {
              range "90..600";
            }
            default 90;
          } //seconds

        } //container sa-timeout

        leaf shutdown {
          type boolean;
          description
              "Administratively enable/disable the MSDP instance";
        }

        list group {
          key "group-name";
          description
              "Configure a MSDP group";
          leaf group-name {
            type string {
              length "1..32";
            }
          } //group-name

          container active-source-limit {
            description
                "Configure maximum number of active source messages accepted by MSDP group";
            leaf number {
              type int32 {
                range "0..1000000";
              }
            } //number

          } //container active-source-limit

          container export {
            description
                "Configure policies to export Source Active state from the Source Active list 
                 into MSDP";
            leaf-list policy-name {
              type string {
                length "1..32";
              }
              max-elements 5;
            } //policy-name

          } //container export

          container import {
            description
                "Configure policies to import Source Active state from the Source Active list 
                 into MSDP";
            leaf-list policy-name {
              type string {
                length "1..32";
              }
              max-elements 5;
            } //policy-name

          } //container import

          container local-address {
            description
                "Configure the local end of an MSDP session";
            leaf ip-address {
              type inet:ip-address;
              description
                  "[a.b.c.d]";
            } //ip-address

          } //container local-address

          container mode {
            description
                "Configure mode of a MSDP group";
            leaf mesh-group-standard {
              type enumeration {
                enum mesh-group;
                enum standard;
              }
              description
                  "keywords";
            } //mesh-group-standard

          } //container mode

          container receive-msdp-msg-rate {
            description
                "Configure number of messages MSDP group can read";
            leaf number {
              type uint32 {
                range "10..10000";
              }
            } //number

            leaf interval {
              type uint32 {
                range "1..600";
              }
            } //interval

            leaf threshold {
              type uint32 {
                range "1..1000000";
              }
            } //threshold

          } //container receive-msdp-msg-rate

          leaf shutdown {
            type boolean;
            description
                "Administratively enable/disable the MSDP group instance";
          }

          list peer {
            key "ip-address";
            description
                "Configure a MSDP group peer";
            leaf ip-address {
              type inet:ip-address;
              description
                  "[a.b.c.d]";
            } //ip-address

            container active-source-limit {
              description
                  "Configure maximum number of active source messages accepted by MSDP peer";
              leaf number {
                type int32 {
                  range "0..1000000";
                }
              } //number

            } //container active-source-limit

            container authentication-key {
              description
                  "Configure the MD5 authentication key for the MSDP peering session";
              leaf authentication-key-hash-key {
                type string {
                  length "1..500";
                }
                description
                    "authentication-key - [256 chars max] 
                     hash-key 
                     hash2-key 
                     custom-key";
              } //authentication-key-hash-key

              leaf hash-hash2-custom {
                type enumeration {
                  enum hash;
                  enum hash2;
                  enum custom;
                }
                description
                    "keywords - specify hashing scheme";
              } //hash-hash2-custom

            } //container authentication-key

            leaf default-peer {
              type boolean;
              description
                  "Enable/Disable default peer as MSDP peer";
            }

            container export {
              description
                  "Configure policies to export Source Active state from the Source Active list 
                   into MSDP group peer";
              leaf-list policy-name {
                type string {
                  length "1..32";
                }
                max-elements 5;
              } //policy-name

            } //container export

            container import {
              description
                  "Configure policies to import Source Active state from the Source Active list 
                   into MSDP group peer";
              leaf-list policy-name {
                type string {
                  length "1..32";
                }
                max-elements 5;
              } //policy-name

            } //container import

            container local-address {
              description
                  "Configure the local end of an MSDP peering session";
              leaf ip-address {
                type inet:ip-address;
                description
                    "[a.b.c.d]";
              } //ip-address

            } //container local-address

            container receive-msdp-msg-rate {
              description
                  "Configure number of messages MSDP group peer can read";
              leaf number {
                type uint32 {
                  range "10..10000";
                }
              } //number

              leaf interval {
                type uint32 {
                  range "1..600";
                }
              } //interval

              leaf threshold {
                type uint32 {
                  range "1..1000000";
                }
              } //threshold

            } //container receive-msdp-msg-rate

            leaf shutdown {
              type boolean;
              description
                  "Administratively enable/disable the MSDP peer group instance";
            }

          } //list peer

        } //list group

        list peer {
          key "ip-address";
          description
              "Configure a MSDP peer";
          leaf ip-address {
            type inet:ip-address;
            description
                "[a.b.c.d]";
          } //ip-address

          container active-source-limit {
            description
                "Configure maximum number of active source messages accepted by MSDP peer";
            leaf number {
              type int32 {
                range "0..1000000";
              }
            } //number

          } //container active-source-limit

          container authentication-key {
            description
                "Configure the MD5 authentication key for the MSDP peering session";
            leaf authentication-key-hash-key {
              type string {
                length "1..500";
              }
              description
                  "authentication-key - [256 chars max] 
                   hash-key 
                   hash2-key 
                   custom-key";
            } //authentication-key-hash-key

            leaf hash-hash2-custom {
              type enumeration {
                enum hash;
                enum hash2;
                enum custom;
              }
              description
                  "keywords - specify hashing scheme";
            } //hash-hash2-custom

          } //container authentication-key

          leaf default-peer {
            type boolean;
            description
                "Enable/Disable default peer as MSDP peer";
          }

          container export {
            description
                "Configure policies to export Source Active state from the Source Active list 
                 into MSDP";
            leaf-list policy-name {
              type string {
                length "1..32";
              }
              max-elements 5;
            } //policy-name

          } //container export

          container import {
            description
                "Configure policies to import Source Active state from the Source Active list 
                 into MSDP";
            leaf-list policy-name {
              type string {
                length "1..32";
              }
              max-elements 5;
            } //policy-name

          } //container import

          container local-address {
            description
                "Configure the local end of an MSDP peering session";
            leaf ip-address {
              type inet:ip-address;
              description
                  "[a.b.c.d]";
            } //ip-address

          } //container local-address

          container receive-msdp-msg-rate {
            description
                "Configure number of messages MSDP peer can read";
            leaf number {
              type uint32 {
                range "10..10000";
              }
            } //number

            leaf interval {
              type uint32 {
                range "1..600";
              }
            } //interval

            leaf threshold {
              type uint32 {
                range "1..1000000";
              }
            } //threshold

          } //container receive-msdp-msg-rate

          leaf shutdown {
            type boolean;
            description
                "Administratively enable/disable the MSDP peer instance";
          }

        } //list peer

        list source {
          key "unicast-ip-prefix-mask";
          description
              "Configure a MSDP source";
          leaf unicast-ip-prefix-mask {
            type inet:ip-prefix;
            description
                "ip-prefix/mask";
          } //unicast-ip-prefix-mask

          container active-source-limit {
            description
                "Configure maximum number of active source messages accepted by MSDP source";
            leaf number {
              type uint32 {
                range "0..1000000";
              }
            } //number

          } //container active-source-limit

        } //list source

      } //container msdp

      container mtrace2 {
        description
            "Configure UDP-based Multicast Traceroute (mstat2 and mtrace2)";
        leaf shutdown {
          type boolean;
          description
              "Administratively enable/disable launching UDP-based Multicast Traceroute 
               (mstat2 or mtrace2) tests, and listening for unsolicited test packets";
        }

        container udp-port {
          description
              "Configure the UDP port used when launching an mstat2 or mtrace2 test, and when 
               listening for unsolicited test packets";
          leaf udp-port-number {
            type uint32 {
              range "1024..49151";
            }
            default 5000;
            description
                "[1024..49151] - Default: 5000";
          } //udp-port-number

        } //container udp-port

      } //container mtrace2

      container mvpn {
        description
            "Configure multicast VPN";
        container auto-discovery {
          description
              "Enable/disable multicast VPN membership auto-discovery via BGP";
          leaf default-mdt-safi {
            type enumeration {
              enum default;
              enum mdt-safi;
            }
            description
                "keyword";
          } //default-mdt-safi

          leaf source-address {
            type inet:ip-address;
          } //source-address

        } //container auto-discovery

        container c-mcast-signaling {
          description
              "Specifies the protocol to use for PE-to-PE signaling of CE multicast states";
          leaf bgp-pim {
            type enumeration {
              enum bgp;
              enum pim;
            }
            description
                "keyword - protocol";
          } //bgp-pim

        } //container c-mcast-signaling

        container intersite-shared {
          description
              "Enable/Disable the use of intersite shared C-trees";
          leaf persistent-type5-adv {
            type boolean;
          } //persistent-type5-adv

          leaf kat-type5-adv-withdraw {
            type boolean;
          } //kat-type5-adv-withdraw

        } //container intersite-shared

        container mdt-type {
          description
              "Specifies the type of the PE node (for non-GRE only)";
          leaf mdt-type-id {
            type enumeration {
              enum sender-only;
              enum receiver-only;
              enum sender-receiver;
            }
          } //mdt-type-id

        } //container mdt-type

        container umh-selection {
          description
              "Specifies the algorithm for selecting the UMH from the UMH route candidate set";
          leaf umh-selection-id {
            type enumeration {
              enum highest-ip;
              enum hash-based;
              enum tunnel-status;
              enum unicast-rt-pref;
            }
          } //umh-selection-id

        } //container umh-selection

        container vrf-export {
          description
              "Export route policies used to determine which multicast VPN routes are 
               advertised to all peers";
          leaf-list policy-name {
            type string;
            max-elements 15;
            description
                "Attribute policy-name for vrf-export";
          } //policy-name

          leaf unicast {
            type boolean;
            description
                "keyword - uses unicast vrf-export policy for the multicast VPN";
          } //unicast

          leaf plcy-or-long-expr {
            type string {
              length "1..255";
            }
            description
                "Attribute plcy-or-long-expr for vrf-export";
          } //plcy-or-long-expr

          leaf-list plcy-or-expr {
            type string {
              length "1..64";
            }
            max-elements 14;
            description
                "Attribute plcy-or-expr for vrf-export";
          } //plcy-or-expr

        } //container vrf-export

        container vrf-import {
          description
              "Import route policies used to determine which multicast VPN routes are 
               imported from all peers";
          leaf-list policy-name {
            type string;
            max-elements 15;
            description
                "Attribute policy-name for vrf-import";
          } //policy-name

          leaf unicast {
            type boolean;
            description
                "keyword - uses unicast vrf-import policy for the multicast VPN";
          } //unicast

          leaf plcy-or-long-expr {
            type string {
              length "1..255";
            }
            description
                "Attribute plcy-or-long-expr for vrf-import";
          } //plcy-or-long-expr

          leaf-list plcy-or-expr {
            type string {
              length "1..64";
            }
            max-elements 14;
            description
                "Attribute plcy-or-expr for vrf-import";
          } //plcy-or-expr

        } //container vrf-import

        container provider-tunnel {
          description
              "Configure provider tunnel for the multicast VPN";
          container inclusive {
            description
                "Configure inclusive provider tunnels for the multicast VPN";
            container bsr {
              description
                  "Configure bsr signalling";
              leaf bsr-id {
                type enumeration {
                  enum unicast;
                  enum spmsi;
                }
              } //bsr-id

            } //container bsr

            leaf wildcard-spmsi {
              type boolean;
              description
                  "Enable/Disable wildcard spmsi";
            }

            container bier {
              presence
                  "Configure BIER for inclusive provider tunnel";
              leaf shutdown {
                type boolean;
                description
                    "Administratively enable/disable the use of BIER";
              }

              container sub-domain {
                description
                    "Configure BIER sub domain for inclusive provider tunnel";
                leaf sub-domain-id {
                  type uint32 {
                    range "0..255";
                  }
                } //sub-domain-id

              } //container sub-domain

            } //container bier

            container mldp {
              presence
                  "Enable/Disable the Context for specifiying MLDP for the provider tunnel";
              leaf shutdown {
                type boolean;
                description
                    "Administratively enable/disable the use of MLDP";
              }

            } //container mldp

            container pim {
              description
                  "Configure the PIM mode and group address for PIM based inclusive provider 
                   tunnels";
              leaf asm-ssm {
                type enumeration {
                  enum asm;
                  enum ssm;
                }
                description
                    "keyword - PIM mode";
              } //asm-ssm

              leaf grp-address {
                type inet:ip-address;
                description
                    "a.b.c.d - multicast group address";
              } //grp-address

              container hello-interval {
                description
                    "Configure the frequency at which PIM hello messages are sent over this 
                     interface";
                leaf hello-interval {
                  type uint32 {
                    range "0..255";
                  }
                } //hello-interval

              } //container hello-interval

              container hello-multiplier {
                description
                    "Configure hello-multiplier in multiples of 0.1 (deci-units)";
                leaf deci-units {
                  type uint32 {
                    range "20..100";
                  }
                  default 35;
                } //deci-units

              } //container hello-multiplier

              leaf improved-assert {
                type boolean;
                description
                    "Enable/disable improved assert processing";
              }

              leaf shutdown {
                type boolean;
                description
                    "Administratively enable/disable the inclusive provider tunnels";
              }

              leaf three-way-hello {
                type boolean;
                description
                    "Configure compatibility mode for three-way-hello";
              }

              leaf tracking-support {
                type boolean;
                description
                    "Enable/disable tracking support";
              }

            } //container pim

            container rsvp {
              presence
                  "Enable/Disable the Context for specifiying RSVP P2MP LSP for the provider 
                   tunnel";
              leaf enable-bfd-leaf {
                type boolean;
                description
                    "Enable/disable bfd-leaf";
              }

              container enable-bfd-root {
                description
                    "Enable/disable bfd-root";
                leaf transmit-interval {
                  type uint32 {
                    range "10..100000";
                  }
                  description
                      "[10..100000] in milliseconds";
                } //transmit-interval

                leaf multiplier {
                  type string;
                  description
                      "[3..20]";
                } //multiplier

              } //container enable-bfd-root

              container lsp-template {
                description
                    "Specify the Lsp Template";
                leaf lsp-template {
                  type string {
                    length "1..32";
                  }
                } //lsp-template

              } //container lsp-template

              leaf shutdown {
                type boolean;
                description
                    "Administratively enable/disable the use of RSVP";
              }

            } //container rsvp

          } //container inclusive

          container selective {
            description
                "Configure selective provider tunnels for the multicast VPN";
            leaf auto-discovery-disable {
              type boolean;
              description
                  "Enable/disable multicast VPN membership auto-discovery via BGP";
            }

            container data-delay-interval {
              description
                  "Configure the data delay interval";
              leaf value {
                type uint32 {
                  range "3..180";
                }
              } //value

            } //container data-delay-interval

            container data-threshold {
              description
                  "Configures threshold for a group prefix";
              leaf c-grp-ip-addr-mask {
                type string;
                description
                    "multicast group address a.b.c.d 
                     mask [4..32]";
              } //c-grp-ip-addr-mask

              leaf netmask {
                type string;
                description
                    "a.b.c.d (network bits all 1 and host bits all 0)";
              } //netmask

              leaf s-pmsi-threshold {
                type uint32 {
                  range "0..4294967294";
                }
                description
                    "[1..4294967294](threshold in kbps)";
              } //s-pmsi-threshold

              leaf c-grp-ipv6-addr-prefix-length {
                type string;
                description
                    "multicast ipv6-address x:x:x:x:x:x:x:x (eight 16-bit pieces) 
                     x:x:x:x:x:x:d.d.d.d 
                     x [0..FFFF]H 
                     d [0..255]D 
                     prefix-length [1..128]";
              } //c-grp-ipv6-addr-prefix-length

              leaf pe-threshold-add {
                type uint32 {
                  range "1..65535";
                }
              } //pe-threshold-add

              leaf pe-threshold-delete {
                type uint32 {
                  range "2..65535";
                }
              } //pe-threshold-delete

            } //container data-threshold

            leaf enable-asm-mdt {
              type boolean;
              description
                  "Enable/disable mdt-range check at egress for classic draft-rosen only";
            }

            leaf join-tlv-packing-disable {
              type boolean;
              description
                  "Disable/enable packing of multiple MDT join tlvs";
            }

            container maximum-p2mp-spmsi {
              description
                  "Specify the maximum number of p2mp s-pmsi tunnels for the mvpn";
              leaf range {
                type uint32 {
                  range "1..4000";
                }
                description
                    "[1..4000]";
              } //range

            } //container maximum-p2mp-spmsi

            container pim-asm {
              description
                  "Specifies the PIM ASM groups to use for the selective provider tunnel for 
                   classic draft-rosen only";
              leaf grp-ip-address-mask {
                type string;
                description
                    "multicast group address a.b.c.d 
                     mask [4..32]";
              } //grp-ip-address-mask

              leaf netmask {
                type string;
                description
                    "a.b.c.d (network bits all 1 and host bits all 0)";
              } //netmask

            } //container pim-asm

            container pim-ssm {
              description
                  "Specifies the PIM SSM groups to use for the selective provider tunnel";
              leaf grp-ip-address-mask {
                type string;
                description
                    "multicast group address a.b.c.d 
                     mask [4..32]";
              } //grp-ip-address-mask

              leaf netmask {
                type string;
                description
                    "a.b.c.d (network bits all 1 and host bits all 0)";
              } //netmask

            } //container pim-ssm

            container bier {
              presence
                  "Configure BIER for selective provider tunnel";
              leaf shutdown {
                type boolean;
                description
                    "Administratively enable/disable the use of BIER";
              }

              container sub-domain {
                description
                    "Configure BIER sub domain for selective provider tunnel";
                leaf sub-domain-id {
                  type uint32 {
                    range "0..255";
                  }
                } //sub-domain-id

              } //container sub-domain

            } //container bier

            container mldp {
              presence
                  "Enable/Disable the Context for specifiying MLDP for the provider tunnel";
              leaf shutdown {
                type boolean;
                description
                    "Administratively enable/disable the use of MLDP";
              }

            } //container mldp

            list multistream-spmsi {
              key "multistream-spmsi-id";
              description
                  "Configure multistream spmsi";
              leaf multistream-spmsi-id {
                type uint32 {
                  range "1..1024";
                }
              } //multistream-spmsi-id

              container lsp-template {
                description
                    "Configure LSP template for multistream spmsi";
                leaf lsp-template-string {
                  type string {
                    length "1..32";
                  }
                } //lsp-template-string

              } //container lsp-template

              container mdt-pim {
                description
                    "Configure mdt pim";
                leaf mode {
                  type enumeration {
                    enum asm;
                    enum ssm;
                  }
                } //mode

                leaf group-address {
                  type string;
                } //group-address

              } //container mdt-pim

              leaf shutdown {
                type boolean;
                description
                    "Administratively enable/disable multistream spmsi";
              }

              list group {
                key "ip-address-mask";
                description
                    "Configure group prefix for multistream spmsi";
                leaf ip-address-mask {
                  type string;
                  description
                      "Attribute ip-address[/mask] for group";
                } //ip-address-mask

                container source {
                  description
                      "Configure source prefix for multistream spmsi";
                  leaf ip-address-mask {
                    type string;
                    description
                        "Attribute ip-address[/mask] for source";
                  } //ip-address-mask

                  leaf any {
                    type boolean;
                    description
                        "specifes all sources for multistream policy";
                  } //any

                } //container source

              } //list group

            } //list multistream-spmsi

            container rsvp {
              presence
                  "Enable/Disable the Context for specifiying RSVP P2MP LSP for the provider 
                   tunnel";
              container lsp-template {
                description
                    "Specify the Lsp Template";
                leaf lsp-template {
                  type string {
                    length "1..32";
                  }
                } //lsp-template

              } //container lsp-template

              leaf shutdown {
                type boolean;
                description
                    "Administratively enable/disable the use of P2MP Auto LSP";
              }

            } //container rsvp

          } //container selective

        } //container provider-tunnel

        container red-source-list {
          description
              "Configure red source list";
          container src-prefix {
            description
                "Configure source prefix list";
            leaf-list ip-address-mask {
              type inet:ip-prefix;
              max-elements 8;
            } //ip-address-mask

            leaf src-prefix-id {
              type inet:ip-prefix;
              description
                  "ip-address/mask";
            } //src-prefix-id

          } //container src-prefix

          container ipv6 {
            description
                "Configure IPV6 red source list";
            container src-prefix {
              description
                  "Configure IPV6 source prefix list";
              leaf-list ipv6-prefix-prefix-length {
                type string;
                max-elements 8;
              } //ipv6-prefix-prefix-length

              leaf src-prefix-string {
                type string;
                description
                    "ipv6-prefix[/prefix-length]";
              } //src-prefix-string

            } //container src-prefix

          } //container ipv6

        } //container red-source-list

        container rpf-select {
          description
              "Configure RPF select";
          list core-mvpn {
            key "service-id";
            description
                "Configure core-mvpn instance";
            leaf service-id {
              type string;
            } //service-id

            container group-prefix {
              description
                  "Configure group prefix";
              leaf-list ip-address-mask {
                type inet:ip-prefix;
                max-elements 8;
              } //ip-address-mask

              leaf group-prefix-id {
                type inet:ip-prefix;
                description
                    "ip-address/mask";
              } //group-prefix-id

              leaf starg {
                type boolean;
              } //starg

            } //container group-prefix

          } //list core-mvpn

        } //container rpf-select

        container umh-pe-backup {
          description
              "Configure umh-pe-backup for the multicast VPN";
          list umh-pe {
            key "ip-address";
            description
                "Specifies a standby PE for each primary PE in a UFD session";
            leaf ip-address {
              type inet:ip-address;
              description
                  "[a.b.c.d]";
            } //ip-address

            leaf standby {
              type inet:ip-address;
              description
                  "ip-address";
            } //standby

          } //list umh-pe

        } //container umh-pe-backup

        container vrf-target {
          description
              "Route target to be used for the multicast VPN";
          leaf ext-community {
            type string;
            description
                "Attribute ext-community for vrf-target";
          } //ext-community

          leaf unicast {
            type boolean;
            description
                "keyword - uses unicast vrf-target ext-community for the multicast VPN";
          } //unicast

          container export {
            description
                "Specifies communities to be sent to peers";
            leaf ext-community {
              type string;
              description
                  "Attribute ext-community for export";
            } //ext-community

            leaf unicast {
              type boolean;
              description
                  "keyword - uses unicast vrf-target export ext-community for the multicast VPN";
            } //unicast

          } //container export

          container import {
            description
                "Specifies communities to be accepted from peers";
            leaf ext-community {
              type string;
              description
                  "Attribute ext-community for import";
            } //ext-community

            leaf unicast {
              type boolean;
              description
                  "keyword - uses unicast vrf-target import ext-community for the multicast VPN";
            } //unicast

          } //container import

        } //container vrf-target

      } //container mvpn

      uses "conf-svc-vprn-nat-r13:alu-conf-svc-vprn-nat-r13";
      container network {
        description
            "Configure network policy";
        container ingress {
          description
              "Configure ingress policies";
          container filter {
            description
                "Apply network ingress filter";
            leaf ip {
              type string;
              description
                  "[1..65535]|<name:64 char max>";
            } //ip

            leaf ipv6 {
              type string;
              description
                  "[1..65535]|<name:64 char max>";
            } //ipv6

          } //container filter

          container qos {
            description
                "Associate a network Quality of Service (QoS) policy";
            leaf network-policy-id {
              type uint32 {
                range "1..65535";
              }
            } //network-policy-id

            leaf fp-redirect-group {
              type string {
                length "1..32";
              }
            } //fp-redirect-group

            leaf instance {
              type uint16 {
                range "1..65535";
              }
            } //instance

          } //container qos

          leaf urpf-check {
            type boolean;
            description
                "Enable/disable URPF checking when the network interface is in selective VPRN 
                 mode";
          }

        } //container ingress

      } //container network

      uses "conf-svc-vprn-nwif-r13:alu-conf-svc-vprn-nwif-r13";
      uses "conf-svc-vprn-ntp-r13:alu-conf-svc-vprn-ntp-r13";
      uses "conf-svc-vprn-ospf-r13:alu-conf-svc-vprn-ospf-r13";
      uses "conf-svc-vprn-ospf3-r13:alu-conf-svc-vprn-ospf3-r13";
      container pcp-server {
        description
            "Configure Port Control Policy servers";
        list server {
          key "pcp-server-name";
          description
              "Configure a PCP server";
          leaf pcp-server-name {
            type string {
              length "1..32";
            }
          } //pcp-server-name

          container description {
            description
                "Configure a description";
            leaf description-string {
              type string {
                length "1..80";
              }
            } //description-string

          } //container description

          container dual-stack-lite-address {
            description
                "Configure the inside Dual Stack Lite AFTR address (optional)";
            leaf ipv6-address {
              type inet:ipv6-address;
              description
                  "Attribute ipv6-address for dual-stack-lite-address";
            } //ipv6-address

          } //container dual-stack-lite-address

          container fwd-inside-router {
            description
                "Configure the PCP forwarding inside virtual router instance";
            leaf router-instance {
              type string {
                length "1..32";
              }
              description
                  "Attribute router-instance for fwd-inside-router";
            } //router-instance

            leaf service-name {
              type string;
            } //service-name

          } //container fwd-inside-router

          list interface {
            key "interface-name";
            description
                "Associate an interface";
            leaf interface-name {
              type string {
                length "1..32";
              }
              description
                  "[32 chars max] (must start with a letter)";
            } //interface-name

          } //list interface

          container pcp-server-policy {
            description
                "Configure the PCP server policy";
            leaf name {
              type string {
                length "1..32";
              }
            } //name

          } //container pcp-server-policy

          leaf shutdown {
            type boolean;
            description
                "Administratively enable or disable the PCP server";
          }

        } //list server

      } //container pcp-server

      uses "conf-svc-vprn-pim-r13:alu-conf-svc-vprn-pim-r13";
      uses "conf-svc-vprn-ptp-r13:alu-conf-svc-vprn-ptp-r13";
      uses "conf-vprn-radprox-r13:alu-conf-vprn-radprox-r13";
      container radius-server {
        description
            "Configure RADIUS servers";
        list server {
          key "server-name";
          description
              "Add/remove a RADIUS server";
          leaf server-name {
            type string {
              length "1..32";
            }
          } //server-name

          leaf address {
            type string;
            description
                "Attribute ip-address for server";
          } //address

          leaf secret {
            type string {
              length "1..500";
            }
            description
                "secret-key - [64 chars max] 
                 hash-key 
                 hash2-key 
                 custom-key";
          } //secret

          leaf hash-hash2-custom {
            type enumeration {
              enum hash;
              enum hash2;
              enum custom;
            }
            description
                "keywords - specify hashing scheme";
          } //hash-hash2-custom

          leaf accept-coa {
            type boolean;
            description
                "Configure this server for Change of Authorization messages";
          }

          container acct-port {
            description
                "Configure the ACCT UDP port";
            leaf port {
              type uint16 {
                range "1..65535";
              }
            } //port

          } //container acct-port

          container auth-port {
            description
                "Configure the AUTH UDP port";
            leaf port {
              type uint16 {
                range "1..65535";
              }
            } //port

          } //container auth-port

          container coa-script-policy {
            description
                "Configure a RADIUS script policy to modify Change-of-Authorization messages";
            leaf script-policy-name {
              type string {
                length "1..32";
              }
            } //script-policy-name

          } //container coa-script-policy

          container description {
            description
                "Configure a description";
            leaf description-string {
              type string {
                length "1..80";
              }
            } //description-string

          } //container description

          container pending-requests-limit {
            description
                "Configure the limit of the number of pending RADIUS requests";
            leaf limit {
              type uint32 {
                range "1..4096";
              }
            } //limit

          } //container pending-requests-limit

          container python-policy {
            description
                "Configure a Python script policy to modify Change-of-Authorization messages";
            leaf name {
              type string {
                length "1..32";
              }
            } //name

          } //container python-policy

        } //list server

      } //container radius-server

      list redundant-interface {
        key "ip-int-name";
        description
            "Create/delete or configure a redundant interface";
        leaf ip-int-name {
          type string {
            length "1..32";
          }
          description
              "[32 chars max] (must start with a letter)";
        } //ip-int-name

        container address {
          description
              "Assigns an IP address/IP subnet format and a remote IP to the interface";
          leaf ip-address-mask {
            type string;
            description
                "ip-address a.b.c.d (no multicast address) 
                 mask [0..32]";
          } //ip-address-mask

          leaf netmask {
            type string;
            description
                "a.b.c.d (network bits all 1 and host bits all 0)";
          } //netmask

          leaf remote-ip {
            type inet:ip-address;
          } //remote-ip

        } //container address

        container delayed-enable {
          status "obsolete";
          leaf seconds {
            type uint32 {
              range "1..65535";
            }
          } //seconds

          leaf init-only {
            type boolean;
          } //init-only

        } //container delayed-enable

        list description {
          key "long-description-string";
          description
              "Description for redundant interface";
          leaf long-description-string {
            type string {
              length "1..255";
            }
          } //long-description-string

        } //list description

        container ip-mtu {
          description
              "Configure the interface IP MTU";
          leaf octets {
            type uint32 {
              range "512..9000";
            }
          } //octets

        } //container ip-mtu

        leaf shutdown {
          type boolean;
          description
              "Administratively enable/disable the interface";
        }

        container hold-time {
          description
              "Configure the hold times (up/down) for the interface";
          list down {
            key "ip";
            description
                "Configure the hold time when the interface is coming up";
            leaf ip {
              type boolean;
            } //ip

            leaf seconds {
              type uint32 {
                range "1..1200";
              }
            } //seconds

            leaf init-only {
              type boolean;
            } //init-only

          } //list down

          list up {
            key "ip";
            description
                "Configure the hold time when the interface is going down";
            leaf ip {
              type boolean;
            } //ip

            leaf seconds {
              type uint32 {
                range "1..1200";
              }
            } //seconds

          } //list up

        } //container hold-time

        list spoke-sdp {
          key "sdp-id-vc-id";
          description
              "Provision a spoke SDP binding";
          leaf sdp-id-vc-id {
            type string;
            description
                "sdp-id - [1..32767] 
                 vc-id - [1..4294967295]";
          } //sdp-id-vc-id

          leaf control-word {
            type boolean;
            description
                "Enable/disable setting the CW bit in the label message";
          }

          container description {
            description
                "Set description for spoke-sdp";
            leaf description-string {
              type string {
                length "1..80";
              }
              description
                  "80 char max";
            } //description-string

          } //container description

          leaf shutdown {
            type boolean;
            description
                "Administratively enable/disable the spoke SDP binding";
          }

          container control-channel-status {
            description
                "Configure control channel status information";
            leaf acknowledgment {
              type boolean;
              description
                  "Enable/disable acknowledgment";
            }

            container refresh-timer {
              description
                  "Configure refresh timer";
              leaf seconds {
                type uint32 {
                  range "10..65535";
                }
              } //seconds

            } //container refresh-timer

            container request-timer {
              description
                  "Configure request-timer for the control channel status";
              leaf request-timer-secs {
                type uint32 {
                  range "10..65535";
                }
              } //request-timer-secs

              leaf retry-timer {
                type uint32 {
                  range "3..60";
                }
              } //retry-timer

              leaf timeout-multiplier {
                type uint32 {
                  range "3..15";
                }
              } //timeout-multiplier

            } //container request-timer

            leaf shutdown {
              type boolean;
              description
                  "Administratively enable/disable the control channel status";
            }

          } //container control-channel-status

          container egress {
            description
                "Spoke SDP egress configuration";
            container filter {
              description
                  "Apply egress filter";
              leaf ip {
                type string;
                description
                    "[1..65535]|<name:64 char max>";
              } //ip

            } //container filter

            list vc-label {
              key "egress-vc-label";
              description
                  "Configure egress VC label";
              leaf egress-vc-label {
                type int32 {
                  range "16..1048575";
                }
              } //egress-vc-label

            } //list vc-label

          } //container egress

          container ingress {
            description
                "Spoke SDP ingress configuration";
            container filter {
              description
                  "Apply ingress filter";
              leaf ip {
                type string;
                description
                    "[1..65535]|<name:64 char max>";
              } //ip

            } //container filter

            list vc-label {
              key "ingress-vc-label";
              description
                  "Configure ingress VC label";
              leaf ingress-vc-label {
                type string;
                description
                    "Attribute ingress-vc-label for vc-label";
              } //ingress-vc-label

            } //list vc-label

          } //container ingress

          container pw-path-id {
            presence
                "Configure PW path identifier information";
            container agi {
              description
                  "Configure Attachment Group Identifier";
              leaf attachment-group-identifier {
                type string {
                }
                description
                    "<0..4294967295>:<0..4294967295>";
              } //attachment-group-identifier

            } //container agi

            container saii-type2 {
              description
                  "Configure Source Attachment Individual Identifier (SAII)";
              leaf global-id-node-id-ac-id {
                type string {
                }
                description
                    "Attribute global-id:node-id:ac-id for saii-type2";
              } //global-id-node-id-ac-id

            } //container saii-type2

            container taii-type2 {
              description
                  "Configure Target Attachment Individual Identifier (TAII)";
              leaf global-id-node-id-ac-id {
                type string {
                }
                description
                    "Attribute global-id:node-id:ac-id for taii-type2";
              } //global-id-node-id-ac-id

            } //container taii-type2

          } //container pw-path-id

        } //list spoke-sdp

      } //list redundant-interface

      uses "conf-svc-vprn-rip-r13:alu-conf-svc-vprn-rip-r13";
      uses "conf-svc-vprn-ripng-r13:alu-conf-svc-vprn-ripng-r13";
      uses "conf-svc-vprn-radv-r13:alu-conf-svc-vprn-radv-r13";
      container sgt-qos {
        description
            "Configure DSCP/Dot1p re-marking for self-generated traffic";
        container application {
          description
              "Configure DSCP/Dot1p re-marking for applications";
          leaf dscp-app-name {
            type enumeration {
              enum bgp;
              enum bmp;
              enum call-trace;
              enum cflowd;
              enum dhcp;
              enum diameter;
              enum dns;
              enum ftp;
              enum grpc;
              enum gtp;
              enum http;
              enum icmp;
              enum igmp;
              enum l2tp;
              enum ldp;
              enum mld;
              enum msdp;
              enum mtrace2;
              enum ndis;
              enum ntp;
              enum ospf;
              enum pcep;
              enum pim;
              enum ptp;
              enum radius;
              enum rip;
              enum rsvp;
              enum sflow;
              enum snmp;
              enum snmp-notification;
              enum srrp;
              enum ssh;
              enum syslog;
              enum tacplus;
              enum telnet;
              enum tftp;
              enum traceroute;
              enum vrrp;
            }
            description
                "Attribute dscp-app-name for application";
          } //dscp-app-name

          leaf dscp {
            type string {
              length "1..4";
            }
            description
                "Attribute dscp-value for application";
          } //dscp

          leaf dot1p {
            type string {
              length "1..4";
            }
            description
                "[none|0..7]";
          } //dot1p

          leaf dot1p-app-name {
            type enumeration {
              enum arp;
              enum isis;
              enum pppoe;
            }
            description
                "Attribute dot1p-app-name for application";
          } //dot1p-app-name

        } //container application

        list dscp {
          key "dscp-name";
          description
              "Configure DSCP name to FC mapping";
          leaf dscp-name {
            type string {
              length "1..32";
            }
            description
                "Attribute dscp-name for dscp";
          } //dscp-name

          leaf fc {
            type enumeration {
              enum be;
              enum l2;
              enum af;
              enum l1;
              enum h2;
              enum ef;
              enum h1;
              enum nc;
            }
            default "be";
          } //fc

        } //list dscp

      } //container sgt-qos

      container snmp {
        description
            "Configure SNMP parameters for this VPRN";
        leaf access {
          type boolean;
          description
              "Enable/disable SNMP access on the VPRN interface";
        }

        list community {
          key "community-name hash-hash2-custom";
          description
              "Create/delete SNMP community strings for vprn data access";
          leaf community-name {
            type string {
              length "1..500";
            }
            description
                "community-name - [32 chars max] 
                 hash-key 
                 hash2-key 
                 custom-key";
          } //community-name

          leaf version {
            type enumeration {
              enum v1;
              enum v2c;
              enum both;
            }
          } //version

          leaf hash-hash2-custom {
            type enumeration {
              enum hash;
              enum hash2;
              enum custom;
            }
            description
                "keywords - hashing scheme for community-name";
          } //hash-hash2-custom

          leaf access-permissions {
            type enumeration {
              enum r;
              enum rw;
            }
            description
                "Attribute access-permissions for community";
          } //access-permissions

          leaf src-access-list {
            type string {
              length "1..32";
            }
            description
                "list-name - [32 chars max]";
          } //src-access-list

        } //list community

      } //container snmp

      uses "conf-svc-vprn-srcad-r13:alu-conf-svc-vprn-srcad-r13";
      uses "conf-svc-vprn-spoke-r13:alu-conf-svc-vprn-spoke-r13";
      container static-route-entry {
        description
            "Creates/Configure or Delete static route entries";
        leaf ip-prefix-prefix-length {
          type string;
          description
              "Attribute ip-prefix/prefix-length for static-route-entry";
        } //ip-prefix-prefix-length

        leaf mcast {
          type boolean;
          description
              "keyword - Indicates that static-route being configured is used for mcast table 
               only";
        } //mcast

        container community {
          description
              "Create/Configure or Delete/Deconfigure community for static-route-entry";
          leaf-list comm-id {
            type string;
            max-elements 12;
            description
                "Attribute comm-id for community";
          } //comm-id

        } //container community

        list tag {
          key "tag";
          description
              "Create/Configure or Delete/Deconfigure tag for static-route-entry";
          leaf tag {
            type uint32 {
              range "1..4294967295";
            }
          } //tag

        } //list tag

        container black-hole {
          presence
              "Create/Configure or Delete/Deconfigure blackhole nexthop for 
               static-route-entry";
          list community {
            key "comm-id";
            description
                "Create/Configure or Delete/Deconfigure community";
            leaf comm-id {
              type string;
              description
                  "Attribute comm-id for community";
            } //comm-id

          } //list community

          list description {
            key "description-string";
            description
                "Create/Configure or Delete/Deconfigure description";
            leaf description-string {
              type string {
                length "1..80";
              }
            } //description-string

          } //list description

          leaf generate-icmp {
            type boolean;
            description
                "Create/Configure or Delete/Deconfigure generate-icmp";
          }

          list metric {
            key "metric";
            description
                "Create/Configure or Delete/Deconfigure static route metric";
            leaf metric {
              type uint32 {
                range "0..65535";
              }
            } //metric

          } //list metric

          container preference {
            description
                "Create/Configure or Delete/Deconfigure preference";
            leaf preference {
              type uint16 {
                range "1..255";
              }
            } //preference

          } //container preference

          list prefix-list {
            key "prefix-list-name all-none";
            description
                "Create/Configure or Delete/Deconfigure static route prefix-list";
            leaf prefix-list-name {
              type string {
                length "1..32";
              }
            } //prefix-list-name

            leaf all-none {
              type enumeration {
                enum all;
                enum none;
                enum any;
              }
            } //all-none

          } //list prefix-list

          leaf shutdown {
            type boolean;
            description
                "Administratively enable/disable the static route black-hole nexthop";
          }

          list tag {
            key "tag";
            description
                "Create/Configure or Delete/Deconfigure static route tag";
            leaf tag {
              type uint32 {
                range "1..4294967295";
              }
            } //tag

          } //list tag

        } //container black-hole

        container grt {
          presence
              "Create/Configure or Delete/Deconfigure GRT nexthop for static-route-entry";
          list description {
            key "description-string";
            description
                "Create/Configure or Delete/Deconfigure description";
            leaf description-string {
              type string {
                length "1..80";
              }
            } //description-string

          } //list description

          list metric {
            key "metric";
            description
                "Create/Configure or Delete/Deconfigure static route metric";
            leaf metric {
              type uint32 {
                range "0..65535";
              }
            } //metric

          } //list metric

          container preference {
            description
                "Create/Configure or Delete/Deconfigure preference";
            leaf preference {
              type uint16 {
                range "1..255";
              }
            } //preference

          } //container preference

          leaf shutdown {
            type boolean;
            description
                "Administratively enable/disable the static route Grt nexthop";
          }

        } //container grt

        list indirect {
          key "ip-address";
          description
              "Create/Configure or Delete/Deconfigure indirect next-hop for 
               static-route-entry";
          leaf ip-address {
            type string;
            description
                "Attribute ip-address for indirect";
          } //ip-address

          list community {
            key "comm-id";
            description
                "Create/Configure or Delete/Deconfigure community";
            leaf comm-id {
              type string;
              description
                  "Attribute comm-id for community";
            } //comm-id

          } //list community

          list description {
            key "description-string";
            description
                "Create/Configure or Delete/Deconfigure description";
            leaf description-string {
              type string {
                length "1..80";
              }
            } //description-string

          } //list description

          list destination-class {
            key "dest-index";
            description
                "Create/Configure or Delete/Deconfigure destination-class";
            leaf dest-index {
              type uint32 {
                range "1..255";
              }
            } //dest-index

          } //list destination-class

          list metric {
            key "metric";
            description
                "Create/Configure or Delete/Deconfigure static route metric";
            leaf metric {
              type uint32 {
                range "0..65535";
              }
            } //metric

          } //list metric

          container preference {
            description
                "Create/Configure or Delete/Deconfigure static route preference";
            leaf preference {
              type uint16 {
                range "1..255";
              }
            } //preference

          } //container preference

          list prefix-list {
            key "prefix-list-name all-none";
            description
                "Create/Configure or Delete/Deconfigure static route prefix-list";
            leaf prefix-list-name {
              type string {
                length "1..32";
              }
            } //prefix-list-name

            leaf all-none {
              type enumeration {
                enum all;
                enum none;
                enum any;
              }
            } //all-none

          } //list prefix-list

          leaf shutdown {
            type boolean;
            description
                "Administratively enable/disable the static route indirect nexthop";
          }

          list source-class {
            key "source-index";
            description
                "Create/Configure or Delete/Deconfigure source-class";
            leaf source-index {
              type uint32 {
                range "1..255";
              }
            } //source-index

          } //list source-class

          list tag {
            key "tag";
            description
                "Create/Configure or Delete/Deconfigure static route tag";
            leaf tag {
              type uint32 {
                range "1..4294967295";
              }
            } //tag

          } //list tag

          list cpe-check {
            key "cpe-ip-address";
            description
                "Create/Configure or Delete/Deconfigure cpe-check Address";
            leaf cpe-ip-address {
              type string;
              description
                  "Attribute cpe-ip-address for cpe-check";
            } //cpe-ip-address

            container drop-count {
              description
                  "Create/Configure or Delete/Deconfigure cpe-check drop-count";
              leaf count {
                type uint64 {
                  range "1..255";
                }
                default 3;
              } //count

            } //container drop-count

            container interval {
              description
                  "Create/Configure or Delete/Deconfigure cpe-check interval";
              leaf seconds {
                type uint32 {
                  range "1..255";
                }
                default 1;
              } //seconds

            } //container interval

            leaf log {
              type boolean;
              description
                  "Create/Configure or Delete/Deconfigure cpe-check log";
            }

            container padding-size {
              description
                  "Create/Configure or Delete/Deconfigure cpe-check padding-size";
              leaf padding-size {
                type uint32 {
                  range "0..16384";
                }
              } //padding-size

            } //container padding-size

          } //list cpe-check

          list forwarding-class {
            key "forwarding-class-string";
            description
                "Create/Configure or Delete/Deconfigure forwarding-class";
            leaf forwarding-class-string {
              type string;
              description
                  "be|l2|af|l1|h2|ef|h1|nc";
            } //forwarding-class-string

            list priority {
              key "low-high";
              description
                  "Create/Configure or Delete/Deconfigure forwarding-class priority";
              leaf low-high {
                type enumeration {
                  enum low;
                  enum high;
                }
              } //low-high

            } //list priority

          } //list forwarding-class

        } //list indirect

        list ipsec-tunnel {
          key "ipsec-tunnel-name";
          description
              "Create/Configure or Delete/Deconfigure ipsec-tunnel next-hop for 
               static-route-entry";
          leaf ipsec-tunnel-name {
            type string {
              length "1..32";
            }
          } //ipsec-tunnel-name

          list community {
            key "comm-id";
            description
                "Create/Configure or Delete/Deconfigure community";
            leaf comm-id {
              type string;
              description
                  "Attribute comm-id for community";
            } //comm-id

          } //list community

          list description {
            key "description-string";
            description
                "Create/Configure or Delete/Deconfigure description";
            leaf description-string {
              type string {
                length "1..80";
              }
            } //description-string

          } //list description

          list destination-class {
            key "dest-index";
            description
                "Create/Configure or Delete/Deconfigure destination-class";
            leaf dest-index {
              type uint32 {
                range "1..255";
              }
            } //dest-index

          } //list destination-class

          list metric {
            key "metric";
            description
                "Create/Configure or Delete/Deconfigure static route metric";
            leaf metric {
              type uint32 {
                range "0..65535";
              }
            } //metric

          } //list metric

          container preference {
            description
                "Create/Configure or Delete/Deconfigure static route preference";
            leaf preference {
              type uint16 {
                range "1..255";
              }
            } //preference

          } //container preference

          leaf shutdown {
            type boolean;
            description
                "Administratively enable/disable the static route nexthop";
          }

          list source-class {
            key "source-index";
            description
                "Create/Configure or Delete/Deconfigure source-class";
            leaf source-index {
              type uint32 {
                range "1..255";
              }
            } //source-index

          } //list source-class

          list tag {
            key "tag";
            description
                "Create/Configure or Delete/Deconfigure static route tag";
            leaf tag {
              type uint32 {
                range "1..4294967295";
              }
            } //tag

          } //list tag

          list forwarding-class {
            key "forwarding-class-string";
            description
                "Create/Configure or Delete/Deconfigure forwarding-class";
            leaf forwarding-class-string {
              type string;
              description
                  "be|l2|af|l1|h2|ef|h1|nc";
            } //forwarding-class-string

            list priority {
              key "low-high";
              description
                  "Create/Configure or Delete/Deconfigure forwarding class priority";
              leaf low-high {
                type enumeration {
                  enum low;
                  enum high;
                }
              } //low-high

            } //list priority

          } //list forwarding-class

        } //list ipsec-tunnel

        list next-hop {
          key "ip-int-name-ip-address-ipv6-address";
          description
              "Create/Configure or Delete/Deconfigure nexthop for static-route-entry";
          leaf ip-int-name-ip-address-ipv6-address {
            type string;
            description
                "Attribute ip-int-name|ip-address|ipv6-address for next-hop";
          } //ip-int-name-ip-address-ipv6-address

          leaf bfd-enable {
            type boolean;
            description
                "Create/Configure or Delete/Deconfigure bfd";
          }

          list community {
            key "comm-id";
            description
                "Create/Configure or Delete/Deconfigure community";
            leaf comm-id {
              type string;
              description
                  "Attribute comm-id for community";
            } //comm-id

          } //list community

          list description {
            key "description-string";
            description
                "Create/Configure or Delete/Deconfigure description";
            leaf description-string {
              type string {
                length "1..80";
              }
            } //description-string

          } //list description

          list destination-class {
            key "dest-index";
            description
                "Create/Configure or Delete/Deconfigure destination-class";
            leaf dest-index {
              type uint32 {
                range "1..255";
              }
            } //dest-index

          } //list destination-class

          list load-balancing-weight {
            key "load-balancing-weight-id";
            leaf load-balancing-weight-id {
              type uint32;
            } //load-balancing-weight-id

          } //list load-balancing-weight

          list metric {
            key "metric";
            description
                "Create/Configure or Delete/Deconfigure static route metric";
            leaf metric {
              type uint32 {
                range "0..65535";
              }
            } //metric

          } //list metric

          container preference {
            description
                "Create/Configure or Delete/Deconfigure static route preference";
            leaf preference {
              type uint16 {
                range "1..255";
              }
            } //preference

          } //container preference

          list prefix-list {
            key "prefix-list-name all-none";
            description
                "Create/Configure or Delete/Deconfigure static route prefix-list";
            leaf prefix-list-name {
              type string {
                length "1..32";
              }
            } //prefix-list-name

            leaf all-none {
              type enumeration {
                enum all;
                enum none;
                enum any;
              }
            } //all-none

          } //list prefix-list

          leaf shutdown {
            type boolean;
            description
                "Administratively enable/disable the static route nexthop";
          }

          list source-class {
            key "source-index";
            description
                "Create/Configure or Delete/Deconfigure source-class";
            leaf source-index {
              type uint32 {
                range "1..255";
              }
            } //source-index

          } //list source-class

          list tag {
            key "tag";
            description
                "Create/Configure or Delete/Deconfigure static route tag";
            leaf tag {
              type uint32 {
                range "1..4294967295";
              }
            } //tag

          } //list tag

          leaf validate-next-hop {
            type boolean;
            description
                "Create/Configure or Delete/Deconfigure validate-next-hop";
          }

          list cpe-check {
            key "cpe-ip-address";
            description
                "Create/Configure or Delete/Deconfigure cpe-check address";
            leaf cpe-ip-address {
              type string;
              description
                  "Attribute cpe-ip-address for cpe-check";
            } //cpe-ip-address

            container drop-count {
              description
                  "Create/Configure or Delete/Deconfigure cpe-check drop-count";
              leaf count {
                type uint32 {
                  range "1..255";
                }
                default 3;
              } //count

            } //container drop-count

            container interval {
              description
                  "Create/Configure or Delete/Deconfigure cpe-check interval";
              leaf seconds {
                type uint32 {
                  range "1..255";
                }
                default 1;
              } //seconds

            } //container interval

            leaf log {
              type boolean;
              description
                  "Create/Configure or Delete/Deconfigure cpe-check log";
            }

            container padding-size {
              description
                  "Create/Configure or Delete/Deconfigure cpe-check padding-size";
              leaf padding-size {
                type uint32 {
                  range "0..16384";
                }
              } //padding-size

            } //container padding-size

          } //list cpe-check

          list forwarding-class {
            key "forwarding-class-string";
            description
                "Create/Configure or Delete/Deconfigure forwarding-class";
            leaf forwarding-class-string {
              type string;
              description
                  "be|l2|af|l1|h2|ef|h1|nc";
            } //forwarding-class-string

            list priority {
              key "low-high";
              description
                  "Create/Configure or Delete/Deconfigure forwarding class priority";
              leaf low-high {
                type enumeration {
                  enum low;
                  enum high;
                }
              } //low-high

            } //list priority

          } //list forwarding-class

        } //list next-hop

      } //container static-route-entry

      uses "conf-svc-vprn-subif-r13:alu-conf-svc-vprn-subif-r13";
      container ttl-propagate {
        description
            "Manage TTL propagation from IP header into label stack";
        container local {
          description
              "Manage TTL propagation from IP header into label stack for local packets";
          leaf ttl-prop-type {
            type enumeration {
              enum none;
              enum all;
              enum vc-only;
              enum inherit;
            }
            default "inherit";
            description
                "none|all|vc-only|inherit - Default: inherit";
          } //ttl-prop-type

        } //container local

        container transit {
          description
              "Manage TTL propagation from IP header into label stack for transit packets";
          leaf ttl-prop-type {
            type enumeration {
              enum none;
              enum all;
              enum vc-only;
              enum inherit;
            }
            default "inherit";
            description
                "none|all|vc-only|inherit - Default: inherit";
          } //ttl-prop-type

        } //container transit

      } //container ttl-propagate

      container twamp-light {
        description
            "Configure TWAMP-Light (Two Way Active Measurement Protocol, Light) parameters 
             for the VPRN";
        container reflector {
          description
              "Configure TWAMP-Light reflector parameters";
          leaf udp-port {
            type string;
            description
                "[862 | 64364..64373] - mandatory when creating a TWAMP-Light reflector";
          } //udp-port

          container description {
            description
                "Configure a description for the TWAMP-Light reflector";
            leaf description-string {
              type string {
                length "1..80";
              }
            } //description-string

          } //container description

          leaf shutdown {
            type boolean;
            description
                "Administratively enable/disable the TWAMP-Light reflector";
          }

          list prefix {
            key "ip-prefix-prefix-length";
            description
                "Create or configure a prefix for the TWAMP-Light reflector";
            leaf ip-prefix-prefix-length {
              type string;
              description
                  "Attribute ip-prefix/prefix-length for prefix";
            } //ip-prefix-prefix-length

            container description {
              description
                  "Configure a description for the TWAMP-Light reflector prefix";
              leaf description-string {
                type string {
                  length "1..80";
                }
              } //description-string

            } //container description

          } //list prefix

        } //container reflector

      } //container twamp-light

      list video-interface {
        key "ip-int-name";
        description
            "Configure a video interface";
        leaf ip-int-name {
          type string {
            length "1..30";
          }
          description
              "[29 chars max] (must start with a letter)";
        } //ip-int-name

        container accounting-policy {
          description
              "Configure Accounting Policy";
          leaf acct-policy-id {
            type uint32 {
              range "1..99";
            }
          } //acct-policy-id

        } //container accounting-policy

        list address {
          key "ip-address-mask";
          description
              "Assigns an IP address to the interface";
          leaf ip-address-mask {
            type inet:ip-prefix;
            description
                "ip-address a.b.c.d 
                 mask [1..32]";
          } //ip-address-mask

        } //list address

        container cpu-protection {
          description
              "Configure a CPU protection policy";
          leaf policy-id {
            type uint32 {
              range "1..255";
            }
          } //policy-id

        } //container cpu-protection

        container description {
          description
              "Description for video interface";
          leaf description-string {
            type string {
              length "1..80";
            }
          } //description-string

        } //container description

        container multicast-service {
          description
              "Configure service ID of the associated multicast service";
          leaf service-id {
            type string;
            description
                "Attribute service-id for multicast-service";
          } //service-id

        } //container multicast-service

        container output-format {
          description
              "Configure the output format";
          leaf udp-rtp-udp {
            type enumeration {
              enum udp;
              enum rtp-udp;
            }
            description
                "keywords";
          } //udp-rtp-udp

        } //container output-format

        container rt-client-src-address {
          description
              "Configure an IP address for the RT client";
          leaf ip-address {
            type inet:ip-address;
          } //ip-address

        } //container rt-client-src-address

        leaf shutdown {
          type boolean;
          description
              "Administratively enable/disable the video interface";
        }

        container adi {
          description
              "Configure Ad-Insertion for the video interface";
          container scte30 {
            description
                "Configure scte30 parameters";
            list ad-server {
              key "ip-address";
              description
                  "Configure ad server address";
              leaf ip-address {
                type inet:ip-address;
              } //ip-address

            } //list ad-server

            container local-address {
              description
                  "Configure local address for scte 30 control and data streams";
              leaf control {
                type inet:ip-address;
              } //control

              leaf data {
                type inet:ip-address;
              } //data

            } //container local-address

          } //container scte30

        } //container adi

        list channel {
          key "mcast-address source";
          description
              "Configure channel";
          leaf mcast-address {
            type inet:ip-address;
            description
                "a.b.c.d - multicast channel address";
          } //mcast-address

          leaf source {
            type inet:ip-address;
            description
                "a.b.c.d - unicast source address";
          } //source

          leaf channel-name {
            type string {
              length "1..32";
            }
            description
                "max 32 chars";
          } //channel-name

          container description {
            description
                "Add/remove description for channel";
            leaf description-string {
              type string {
                length "1..80";
              }
              description
                  "[Max 80 chars]";
            } //description-string

          } //container description

          container scte35-action {
            description
                "Enable/disable forwarding scte 35 cue avails";
            leaf forward-drop {
              type enumeration {
                enum forward;
                enum drop;
              }
              description
                  "keywords";
            } //forward-drop

          } //container scte35-action

          list zone-channel {
            key "mcast-address source";
            description
                "Configure zone-channel";
            leaf mcast-address {
              type inet:ip-address;
            } //mcast-address

            leaf source {
              type inet:ip-address;
            } //source

            leaf adi-channel-name {
              type string {
                length "1..32";
              }
            } //adi-channel-name

          } //list zone-channel

        } //list channel

        container video-sap {
          description
              "Configure group id for the video interface";
          leaf video-group-id {
            type uint32 {
              range "1..4";
            }
          } //video-group-id

          container egress {
            description
                "Configure egress parameters";
            container filter {
              description
                  "Configure an egress filter";
              leaf ip {
                type string;
                description
                    "[1..65535]|<name:64 char max>";
              } //ip

            } //container filter

            container qos {
              description
                  "Configure qos policy";
              leaf egress-qos-policy-id {
                type string;
                description
                    "[1..65535]|<name:64 char max>";
              } //egress-qos-policy-id

            } //container qos

          } //container egress

          container ingress {
            description
                "Configure ingress parameters";
            container filter {
              description
                  "Configure an ingress filter";
              leaf ip {
                type string;
                description
                    "[1..65535]|<name:64 char max>";
              } //ip

            } //container filter

            container qos {
              description
                  "Configure qos policy";
              leaf ingress-qos-policy-id {
                type string;
                description
                    "[1..65535]|<name:64 char max>";
              } //ingress-qos-policy-id

            } //container qos

          } //container ingress

        } //container video-sap

      } //list video-interface

      container vrgw {
        presence
            "Configure Virtual Residential Gateway functionality";
        container lanext {
          presence
              "Configure Home LAN Extension functionality";
          leaf shutdown {
            type boolean;
            description
                "Enable/disable the Home LAN Extension functionality";
          }

          container wlan-gw-group {
            description
                "Configure the ISA WLAN Gateway group";
            leaf nat-group-id {
              type uint32 {
                range "1..4";
              }
            } //nat-group-id

          } //container wlan-gw-group

        } //container lanext

      } //container vrgw

      container vxlan {
        description
            "Configure vxlan information";
        list tunnel-termination {
          key "ip-address-ipv6-address";
          description
              "Configure vxlan tunnel-termination ip information";
          leaf ip-address-ipv6-address {
            type string;
            description
                "Attribute ip-address|ipv6-address for tunnel-termination";
          } //ip-address-ipv6-address

          leaf fpe {
            type uint32 {
              range "1..64";
            }
          } //fpe

        } //list tunnel-termination

      } //container vxlan

      uses "conf-svc-vprn-wlan-r13:alu-conf-svc-vprn-wlan-r13";
      uses "conf-svc-vprn-wpp-r13:alu-conf-svc-vprn-wpp-r13";
    } //list vprn

  } //grouping alu-conf-svc-vprn-r13

} //module  alu-conf-svc-vprn-r13
