module alu-conf-router-nhroute-r13 {
  yang-version "1";

  namespace "urn:alcatel-lucent.com:sros:ns:yang:conf-router-nhroute-r13";

  prefix "conf-router-nhroute-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure how to select the next-hop on SR 
       OS based routers. 
       
       Copyright 2014-2015 Alcatel-Lucent, 2016 Nokia. All rights reserved. 
       Reproduction of this document is authorized on the condition that the 
       foregoing copyright notice is included. 
       
       This alu-conf-router-nhroute-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2017-09-11";

  grouping alu-conf-router-nhroute-r13 {
    container route-next-hop-policy {
      description
          "Configure how to select the next-hop";
      leaf abort {
        type boolean;
        description
            "Discard the changes that have been made to route next-hop templates during a 
             session";
      }

      leaf begin {
        type boolean;
        description
            "Switch to edit mode for route next-hop templates - use commit to save or abort 
             to discard the changes made in a session";
      }

      leaf commit {
        type boolean;
        description
            "Save the changes made to route next-hop templates during a session";
      }

      list template {
        key "name";
        description
            "Create/delete a route next-hop template";
        leaf name {
          type string {
            length "1..32";
          }
        } //name

        container description {
          description
              "Configure the description of this next-hop template";
          leaf description-string {
            type string {
              length "1..80";
            }
          } //description-string

        } //container description

        list exclude-group {
          key "ip-admin-group-name";
          description
              "Configure the admin groups out of which the next-hop link can never be 
               selected";
          leaf ip-admin-group-name {
            type string {
              length "1..32";
            }
          } //ip-admin-group-name

        } //list exclude-group

        list include-group {
          key "ip-admin-group-name";
          description
              "Configure the admin groups out of which the next-hop link is selected";
          leaf ip-admin-group-name {
            type string {
              length "1..32";
            }
          } //ip-admin-group-name

          leaf pref {
            type uint32 {
              range "1..255";
            }
            description
                "[1..255] - default 255";
          } //pref

        } //list include-group

        container nh-type {
          description
              "Configure the type of next-hop that's preferred";
          leaf nh-type-id {
            type enumeration {
              enum ip;
              enum tunnel;
            }
          } //nh-type-id

        } //container nh-type

        container protection-type {
          description
              "Configure the protection type used";
          leaf protection-type-id {
            type enumeration {
              enum link;
              enum node;
            }
          } //protection-type-id

        } //container protection-type

        leaf srlg-enable {
          type boolean;
          description
              "Configure if next-hops from the SRLG are selected";
        }

      } //list template

    } //container route-next-hop-policy

  } //grouping alu-conf-router-nhroute-r13

} //module  alu-conf-router-nhroute-r13
