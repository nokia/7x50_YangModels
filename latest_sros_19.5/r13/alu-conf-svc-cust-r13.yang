module alu-conf-svc-cust-r13 {
  yang-version "1";

  namespace "urn:alcatel-lucent.com:sros:ns:yang:conf-svc-cust-r13";

  prefix "conf-svc-cust-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure customers on SR OS based routers. 
       
       Copyright 2014-2015 Alcatel-Lucent, 2016 Nokia. All rights reserved. 
       Reproduction of this document is authorized on the condition that the 
       foregoing copyright notice is included. 
       
       This alu-conf-svc-cust-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-04-11";

  grouping alu-conf-svc-cust-r13 {
    list customer {
      key "customer-id";
      description
          "Configure customers";
      leaf customer-id {
        type uint32 {
          range "1..2147483647";
        }
      } //customer-id

      leaf name {
        type string;
      } //name

      list contact {
        key "contact-information";
        description
            "Configure contact Information";
        leaf contact-information {
          type string {
            length "1..80";
          }
        } //contact-information

      } //list contact

      list customer-name {
        key "customer-name";
        status "obsolete";
        description
            "Configure a customer name";
        leaf customer-name {
          type string;
        } //customer-name

      } //list customer-name

      list description {
        key "description-string";
        description
            "Description for this customer";
        leaf description-string {
          type string {
            length "1..80";
          }
        } //description-string

      } //list description

      list phone {
        key "phone-number";
        description
            "Phone numbers for the contact";
        leaf phone-number {
          type string {
            length "1..80";
          }
          description
              "[80 chars max] - specify in any format";
        } //phone-number

      } //list phone

      list multi-service-site {
        key "customer-site-name";
        description
            "Configure a multi-service site for this customer";
        leaf customer-site-name {
          type string {
            length "1..32";
          }
        } //customer-site-name

        container assignment {
          description
              "Specify the port for the multi-service";
          leaf port {
            type string;
            description
                "Attribute port-id for assignment";
          } //port

          leaf card {
            type string;
            description
                "Attribute slot-number for assignment";
          } //card

        } //container assignment

        container description {
          description
              "Description for this customer";
          leaf description-string {
            type string {
              length "1..80";
            }
          } //description-string

        } //container description

        container tod-suite {
          status "obsolete";
          description
              "Configure a time-of-day suite for this multi-service site";
          leaf tod-suite-name {
            type string {
              length "1..32";
            }
          } //tod-suite-name

        } //container tod-suite

        container egress {
          description
              "Specify egress parameters/policies";
          container policer-control-policy {
            description
                "Apply a policer control policy";
            leaf name {
              type string {
                length "1..32";
              }
            } //name

          } //container policer-control-policy

          container scheduler-policy {
            description
                "Specify a scheduler-policy";
            leaf scheduler-policy-name {
              type string {
                length "1..32";
              }
            } //scheduler-policy-name

          } //container scheduler-policy

          container agg-rate {
            presence
                "Configure aggregate rate limit";
            leaf limit-unused-bandwidth {
              type boolean;
              description
                  "Specify whether to enable limit unused bandwidth";
            }

            leaf queue-frame-based-accounting {
              type boolean;
              description
                  "Specify whether to enable queue frame based accounting";
            }

            container rate {
              description
                  "Specify rate limit for agg-rate";
              leaf kilobits-per-second {
                type string;
                description
                    "[1..6400000000|max] Kbps";
              } //kilobits-per-second

            } //container rate

          } //container agg-rate

          container scheduler-override {
            presence
                "Apply a scheduler override";
            list scheduler {
              key "scheduler-name";
              description
                  "Configure a scheduler override";
              leaf scheduler-name {
                type string {
                  length "1..32";
                }
              } //scheduler-name

              container parent {
                description
                    "Specify the override weights for the scheduler";
                leaf weight {
                  type uint32 {
                    range "0..100";
                  }
                } //weight

                leaf cir-weight {
                  type uint32 {
                    range "0..100";
                  }
                } //cir-weight

              } //container parent

              container rate {
                description
                    "Specify rates (CIR and PIR)";
                leaf pir-rate {
                  type string;
                  description
                      "[1..6400000000|max]";
                } //pir-rate

                leaf cir {
                  type string;
                  description
                      "[0..6400000000|sum|max]";
                } //cir

              } //container rate

            } //list scheduler

          } //container scheduler-override

        } //container egress

        container ingress {
          description
              "Specify ingress parameters/policies";
          container policer-control-policy {
            description
                "Apply a policer control policy";
            leaf name {
              type string {
                length "1..32";
              }
            } //name

          } //container policer-control-policy

          container scheduler-policy {
            description
                "Specify a scheduler-policy";
            leaf scheduler-policy-name {
              type string {
                length "1..32";
              }
            } //scheduler-policy-name

          } //container scheduler-policy

          container scheduler-override {
            presence
                "Apply a scheduler override";
            list scheduler {
              key "scheduler-name";
              description
                  "Configure a scheduler override";
              leaf scheduler-name {
                type string {
                  length "1..32";
                }
              } //scheduler-name

              container parent {
                description
                    "Specify the override weights for the scheduler";
                leaf weight {
                  type uint32 {
                    range "0..100";
                  }
                } //weight

                leaf cir-weight {
                  type uint32 {
                    range "0..100";
                  }
                } //cir-weight

              } //container parent

              container rate {
                description
                    "Specify rates (CIR and PIR)";
                leaf pir-rate {
                  type string;
                  description
                      "[1..6400000000|max]";
                } //pir-rate

                leaf cir {
                  type string;
                  description
                      "[0..6400000000|sum|max]";
                } //cir

              } //container rate

            } //list scheduler

          } //container scheduler-override

        } //container ingress

      } //list multi-service-site

    } //list customer

  } //grouping alu-conf-svc-cust-r13

} //module  alu-conf-svc-cust-r13
