module alu-conf-port-sonetsdh-r13 {
  yang-version "1";

  namespace "urn:alcatel-lucent.com:sros:ns:yang:conf-port-sonetsdh-r13";

  prefix "conf-port-sonetsdh-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure SONET/SDH parameters for a port on 
       SR OS based routers. 
       
       Copyright 2014-2015 Alcatel-Lucent, 2016 Nokia. All rights reserved. 
       Reproduction of this document is authorized on the condition that the 
       foregoing copyright notice is included. 
       
       This alu-conf-port-sonetsdh-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-04-22";

  grouping alu-conf-port-sonetsdh-r13 {
    container sonet-sdh {
      description
          "Configure SONET/SDH parameters for a port";
      container clock-source {
        description
            "Configure the clock for transmitted data";
        leaf loop-timed-node-timed {
          type enumeration {
            enum loop-timed;
            enum node-timed;
          }
          description
              "keywords";
        } //loop-timed-node-timed

      } //container clock-source

      container framing {
        description
            "Configure SONET/SDH framing";
        leaf sonet-sdh {
          type enumeration {
            enum sonet;
            enum sdh;
          }
          description
              "keywords";
        } //sonet-sdh

      } //container framing

      list group {
        key "sonet-sdh-index payload";
        description
            "Configure the payload of the SONET/SDH group";
        leaf sonet-sdh-index {
          type string {
          }
          description
              "tug3-index";
        } //sonet-sdh-index

        leaf payload {
          type enumeration {
            enum tu3;
            enum vt2;
            enum vt15;
          }
          description
              "keywords";
        } //payload

      } //list group

      container hold-time {
        description
            "Configure SONET link dampening timers in 100s of milliseconds";
        leaf up {
          type uint32 {
            range "0..100";
          }
          description
              "[0..100] in 100s of milliseconds";
        } //up

        leaf down {
          type uint32 {
            range "0..100";
          }
          description
              "[0..100] in 100s of milliseconds";
        } //down

      } //container hold-time

      container loopback {
        description
            "Activate a loopback on the SONET port";
        leaf line-internal {
          type enumeration {
            enum line;
            enum internal;
          }
          description
              "keywords";
        } //line-internal

      } //container loopback

      container report-alarm {
        description
            "Enable/disable logging of SONET/SDH line and section alarms for a SONET/SDH 
             port";
        leaf lais {
          type boolean;
        } //lais

        leaf lrdi {
          type boolean;
        } //lrdi

        leaf ss1f {
          type boolean;
        } //ss1f

        leaf lb2er-sd {
          type boolean;
        } //lb2er-sd

        leaf lb2er-sf {
          type boolean;
        } //lb2er-sf

        leaf slof {
          type boolean;
        } //slof

        leaf slos {
          type boolean;
        } //slos

        leaf lrei {
          type boolean;
        } //lrei

        leaf loc {
          type boolean;
        } //loc

      } //container report-alarm

      leaf reset-port-on-path-down {
        type boolean;
        description
            "Enable/disable the resetting of the port when the path goes operationally down";
      }

      container section-trace {
        description
            "Configure the section trace bytes in the SONET section header";
        leaf increment-z0 {
          type boolean;
        } //increment-z0

        leaf byte {
          type string {
          }
          description
              "[0..255]";
        } //byte

        leaf string {
          type string {
            length "1..16";
          }
        } //string

      } //container section-trace

      leaf single-fiber {
        type boolean;
        description
            "Enable/disable single fiber";
      }

      container speed {
        description
            "Configure the speed of a SONET/SDH port to be either OC3 or OC12";
        leaf oc3-oc12 {
          type enumeration {
            enum oc3;
            enum oc12;
          }
          description
              "keywords";
        } //oc3-oc12

      } //container speed

      leaf suppress-lo-alarm {
        type boolean;
        description
            "Suppress lo order alarms";
      }

      list threshold {
        key "ber-sd-ber-sf";
        description
            "Configure the line signal degradation BER and line signal failure thresholds";
        leaf ber-sd-ber-sf {
          type enumeration {
            enum ber-sd;
            enum ber-sf;
          }
          description
              "keywords";
        } //ber-sd-ber-sf

        leaf rate {
          type uint32;
          description
              "3 - 9 for ber-sd, 3 - 6 for ber-sf";
        } //rate

      } //list threshold

      leaf tx-dus {
        type boolean;
        description
            "Enable/disable the forced transmit 0xF (dus/dnu) in S1 overhead byte";
      }

      list path {
        key "sonet-sdh-index";
        description
            "Configure SONET/SDH path properties";
        leaf sonet-sdh-index {
          type string {
          }
          description
              "sts12/sts3/tu3/vt2/vt15/sts1 sonet-sdh index";
        } //sonet-sdh-index

        container crc {
          description
              "Configure cyclic redundancy check";
          leaf crc-id {
            type enumeration {
              enum 16;
              enum 32;
            }
          } //crc-id

        } //container crc

        container description {
          description
              "Add/remove a text description";
          leaf long-description-string {
            type string {
              length "1..160";
            }
          } //long-description-string

        } //container description

        container egress-scheduler-policy {
          description
              "Configure an egress scheduler policy";
          leaf port-scheduler-policy-name {
            type string {
              length "1..32";
            }
          } //port-scheduler-policy-name

        } //container egress-scheduler-policy

        container encap-type {
          description
              "Configure an encap method";
          leaf encap-type-id {
            type enumeration {
              enum atm;
              enum bcp-null;
              enum bcp-dot1q;
              enum ipcp;
              enum ppp-auto;
              enum frame-relay;
              enum wan-mirror;
              enum cisco-hdlc;
            }
          } //encap-type-id

        } //container encap-type

        container load-balancing-algorithm {
          description
              "Configure Load Balancing Algorithm";
          leaf option {
            type enumeration {
              enum include-l4;
              enum exclude-l4;
            }
          } //option

        } //container load-balancing-algorithm

        container mac {
          description
              "Assign a MAC address to a SONET/SDH path";
          leaf ieee-address {
            type alu:ieee-address;
            description
                "xx:xx:xx:xx:xx:xx or xx-xx-xx-xx-xx-xx";
          } //ieee-address

        } //container mac

        container mode {
          description
              "Configure access/network mode";
          leaf access-network {
            type enumeration {
              enum access;
              enum network;
            }
            description
                "keywords";
          } //access-network

        } //container mode

        container mtu {
          description
              "Configure the maximum payload MTU size";
          leaf mtu {
            type int32 {
              range "512..9208";
            }
            description
                "[512..9208] bytes";
          } //mtu

        } //container mtu

        container payload {
          description
              "Configure the SONET/SDH path payload";
          leaf sts3-tug3-ds3-e3-vt2-vt15-ds1-e1 {
            type enumeration {
              enum sts3;
              enum tug3;
              enum ds3;
              enum e3;
              enum vt2;
              enum vt15;
              enum ds1;
              enum e1;
            }
            description
                "keywords";
          } //sts3-tug3-ds3-e3-vt2-vt15-ds1-e1

        } //container payload

        container report-alarm {
          description
              "Enable/disable logging of SONET/SDH path alarms";
          leaf pais {
            type boolean;
          } //pais

          leaf plop {
            type boolean;
          } //plop

          leaf prdi {
            type boolean;
          } //prdi

          leaf pplm {
            type boolean;
          } //pplm

          leaf prei {
            type boolean;
          } //prei

          leaf puneq {
            type boolean;
          } //puneq

          leaf plcd {
            type boolean;
          } //plcd

        } //container report-alarm

        leaf scramble {
          type boolean;
          description
              "Configure SONET/SDH payload scrambling";
        }

        leaf shutdown {
          type boolean;
          description
              "Administratively enable/disable the SONET/SDH path";
        }

        container signal-label {
          description
              "Configure C2 byte value";
          leaf value {
            type string {
            }
            description
                "[1..254] or [0x01..0xfe]";
          } //value

        } //container signal-label

        container trace-string {
          description
              "Configure the J1 path-trace inserted continuously at source";
          leaf trace-string {
            type string {
              length "1..62";
            }
            description
                "62 bytes for SONET or 15 bytes for SDH 
                 string 'zeros' will send all zeros in the J1 bytes";
          } //trace-string

        } //container trace-string

        container access {
          description
              "Configure access port parameters";
          container egress {
            description
                "Configure access egress port parameters";
            list vport {
              key "name";
              description
                  "Configure virtual port";
              leaf name {
                type string {
                  length "1..32";
                }
              } //name

              container description {
                description
                    "Add/remove a text description for the virtual port";
                leaf description-string {
                  type string {
                    length "1..80";
                  }
                } //description-string

              } //container description

              leaf egress-rate-modify {
                type boolean;
                description
                    "Enable/disable the egress rate modification";
              }

              list host-match {
                key "dest";
                description
                    "Configure host matching for the port egress vport";
                leaf dest {
                  type string {
                    length "1..32";
                  }
                } //dest

              } //list host-match

              leaf monitor-port-scheduler {
                type boolean;
                description
                    "Enable/Disable monitoring of port scheduler";
              }

              container port-scheduler-policy {
                description
                    "Configure port scheduler policy";
                leaf port-scheduler-policy-name {
                  type string {
                    length "1..32";
                  }
                } //port-scheduler-policy-name

              } //container port-scheduler-policy

              container scheduler-policy {
                description
                    "Apply an egress scheduler policy";
                leaf scheduler-policy-name {
                  type string {
                    length "1..32";
                  }
                } //scheduler-policy-name

              } //container scheduler-policy

              container agg-rate {
                presence
                    "Configure aggregate rate limit";
                leaf limit-unused-bandwidth {
                  type boolean;
                  description
                      "Specify whether to enable limit unused bandwidth";
                }

                container rate {
                  description
                      "Specify rate limit for agg-rate";
                  leaf kilobits-per-second {
                    type string;
                    description
                        "[1..6400000000|max] Kbps";
                  } //kilobits-per-second

                } //container rate

              } //container agg-rate

            } //list vport

          } //container egress

        } //container access

        container atm {
          description
              "Configure ATM properties";
          container cell-format {
            description
                "Configure the ATM cell-format";
            leaf cell-format {
              type enumeration {
                enum uni;
                enum nni;
              }
              description
                  "keywords - uni|nni";
            } //cell-format

          } //container cell-format

          container min-vp-vpi {
            description
                "Configure the ATM minimum vpi";
            leaf value {
              type uint32 {
                range "0..4095";
              }
              description
                  "[0..4095] (NNI) 
                   [0..255] (UNI)";
            } //value

          } //container min-vp-vpi

          list vp {
            key "vpi";
            description
                "Configure a VP shaper";
            leaf vpi {
              type uint16 {
                range "0..4095";
              }
            } //vpi

            leaf egress-traffic-desc {
              type int32 {
                range "1..1000";
              }
            } //egress-traffic-desc

          } //list vp

          container custom-buffer-mode {
            presence
                "Configure ATM port custom buffer parameters";
            container buffer-pool {
              description
                  "Configure ATM port buffer pool percentage";
              leaf percent {
                type uint32 {
                  range "1..100";
                }
                description
                    "[1..100]";
              } //percent

            } //container buffer-pool

            container vc-threshold {
              description
                  "Configure ATM port vc-threshold";
              leaf buffer-threshold {
                type uint32 {
                  range "190..117000";
                }
                description
                    "[190..117000]";
              } //buffer-threshold

            } //container vc-threshold

          } //container custom-buffer-mode

          container ilmi {
            description
                "Configure ILMI properties";
            leaf vpi-vci {
              type string;
              default "0/16";
              description
                  "vpi - [0..4095] (NNI) 
                   [0..255] (UNI) 
                   vci - [1|2|5..65535]";
            } //vpi-vci

            container keep-alive {
              description
                  "Configure the keepalive parameters";
              leaf poll-frequency {
                type uint32 {
                  range "1..255";
                }
              } //poll-frequency

              leaf poll-count {
                type uint64 {
                  range "1..255";
                }
              } //poll-count

              leaf test-frequency {
                type uint32 {
                  range "0..255";
                }
              } //test-frequency

            } //container keep-alive

            container protocol {
              description
                  "Configure the protocol";
              leaf protocol-type {
                type enumeration {
                  enum 4_0-user;
                  enum 4_0-network;
                  enum 3_1-user;
                  enum 3_1-network;
                }
              } //protocol-type

            } //container protocol

            leaf shutdown {
              type boolean;
              description
                  "Administratively enable/disable ILMI";
            }

            container egress {
              description
                  "Configure egress parameters";
              container traffic-desc {
                description
                    "Assign ATM traffic descriptor profile";
                leaf traffic-desc-profile-id {
                  type int32 {
                    range "1..1000";
                  }
                } //traffic-desc-profile-id

              } //container traffic-desc

            } //container egress

            container ingress {
              description
                  "Configure ingress parameters";
              container traffic-desc {
                description
                    "Assign ATM traffic descriptor profile";
                leaf traffic-desc-profile-id {
                  type int32 {
                    range "1..1000";
                  }
                } //traffic-desc-profile-id

              } //container traffic-desc

            } //container ingress

          } //container ilmi

        } //container atm

        container cisco-hdlc {
          description
              "Configure the Cisco-HDLC operational parameters";
          container down-count {
            description
                "Number of keep alive intervals that must pass without receiving a keep alive 
                 packet before the link is declared down";
            leaf down-count {
              type uint32 {
                range "3..16";
              }
            } //down-count

          } //container down-count

          container keepalive {
            description
                "Time interval at which keep-alive requests are issued";
            leaf time-interval {
              type uint32 {
                range "0..300";
              }
              description
                  "[0..300] seconds";
            } //time-interval

          } //container keepalive

          container up-count {
            description
                "Number of continual keepalive packets to be received to declare the link up";
            leaf up-count {
              type uint32 {
                range "1..3";
              }
            } //up-count

          } //container up-count

        } //container cisco-hdlc

        container egress-scheduler-override {
          description
              "Apply egress scheduler overrides";
          list level {
            key "priority-level";
            description
                "Configure priority level parameters";
            leaf priority-level {
              type uint32 {
                range "1..8";
              }
            } //priority-level

            leaf rate {
              type string;
              description
                  "[1..3200000000|max] Kbps";
            } //rate

            leaf percent-rate {
              type string;
              description
                  "[0.01..100.00]";
            } //percent-rate

            leaf cir {
              type string;
              description
                  "[0..3200000000|max] Kbps";
            } //cir

            leaf percent-cir {
              type string;
              description
                  "[0.00..100.00]";
            } //percent-cir

          } //list level

          container max-rate {
            description
                "Configure the maximum rate";
            leaf rate {
              type string;
              description
                  "[1..3200000000|max] Kbps";
            } //rate

            leaf percent {
              type string;
              description
                  "[0.01..100.00]";
            } //percent

          } //container max-rate

        } //container egress-scheduler-override

        container frame-relay {
          description
              "Configure the Frame Relay parameters";
          container lmi-type {
            description
                "Configure the LMI type";
            leaf ansi-itu-none-rev1 {
              type enumeration {
                enum ansi;
                enum itu;
                enum none;
                enum rev1;
              }
              description
                  "keywords";
            } //ansi-itu-none-rev1

          } //container lmi-type

          container mode {
            description
                "Configure the DCE/DTE mode of the Frame Relay interface";
            leaf dce-dte-bidir {
              type enumeration {
                enum dce;
                enum dte;
                enum bidir;
              }
              description
                  "keywords";
            } //dce-dte-bidir

          } //container mode

          container n391dte {
            description
                "Configure the number of DTE full status polling intervals for the LMI";
            leaf intervals {
              type int32 {
                range "1..255";
              }
            } //intervals

          } //container n391dte

          container n392dce {
            description
                "Configure the DCE error threshold for the LMI";
            leaf threshold {
              type int32 {
                range "1..10";
              }
            } //threshold

          } //container n392dce

          container n392dte {
            description
                "Configure the DTE error threshold for the LMI";
            leaf threshold {
              type int32 {
                range "1..10";
              }
            } //threshold

          } //container n392dte

          container n393dce {
            description
                "Configure the DCE monitored event count for the LMI";
            leaf count {
              type int32 {
                range "1..10";
              }
            } //count

          } //container n393dce

          container n393dte {
            description
                "Configure the DTE monitored event count for the LMI";
            leaf count {
              type int32 {
                range "1..10";
              }
            } //count

          } //container n393dte

          container t391dte {
            description
                "Configure the DTE keepalive timer value for the LMI";
            leaf keepalive {
              type int32 {
                range "5..30";
              }
              description
                  "[5..30 seconds]";
            } //keepalive

          } //container t391dte

          container t392dce {
            description
                "Configure the DCE keepalive timer value for the LMI";
            leaf keepalive {
              type int32 {
                range "5..30";
              }
              description
                  "[5..30 seconds]";
            } //keepalive

          } //container t392dce

          container frf-12 {
            presence
                "Enable/Disable FRF12 Headers";
            container fragment-threshold {
              description
                  "Configure FRF.12 fragmentation threshold";
              leaf threshold {
                type uint32 {
                  range "128..512";
                }
              } //threshold

            } //container fragment-threshold

            container egress {
              description
                  "Configure egress frf.12 parameters";
              container qos-profile {
                description
                    "Configure egress frf.12 qos-profile";
                leaf profile-id {
                  type int32;
                  description
                      "Attribute profile-id for qos-profile";
                } //profile-id

              } //container qos-profile

            } //container egress

          } //container frf-12

        } //container frame-relay

        container network {
          description
              "Configure network port parameters";
          container accounting-policy {
            description
                "Configure the accounting policy which applies to the network port";
            leaf policy-id {
              type uint32 {
                range "1..99";
              }
              description
                  "1-99";
            } //policy-id

          } //container accounting-policy

          leaf collect-stats {
            type boolean;
            description
                "Enable/disable the collection of statistical data";
          }

          container queue-policy {
            description
                "Configure the network policy";
            leaf name {
              type string {
                length "1..32";
              }
              default "default";
            } //name

          } //container queue-policy

        } //container network

        container ppp {
          description
              "Configure the LCP operational parameters for a PPP link";
          container keepalive {
            description
                "Configure the time interval at which keepalive requests are issued";
            leaf time-interval {
              type int32 {
                range "1..60";
              }
              description
                  "[1..60] seconds";
            } //time-interval

            leaf dropcount {
              type uint64 {
                range "1..255";
              }
            } //dropcount

          } //container keepalive

        } //container ppp

      } //list path

    } //container sonet-sdh

  } //grouping alu-conf-port-sonetsdh-r13

} //module  alu-conf-port-sonetsdh-r13
