module alu-conf-log-r13 {
  yang-version "1";

  namespace "urn:alcatel-lucent.com:sros:ns:yang:conf-log-r13";

  prefix "conf-log-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure event stream logging on SR OS 
       based routers. 
       
       Copyright 2014-2015 Alcatel-Lucent, 2016 Nokia. All rights reserved. 
       Reproduction of this document is authorized on the condition that the 
       foregoing copyright notice is included. 
       
       This alu-conf-log-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-04-03";

  grouping alu-conf-log-r13 {
    container log {
      description
          "Configure event stream logging";
      list event-control {
        key "application-id";
        description
            "Control operation of specific events";
        leaf application-id {
          type string {
            length "1..32";
          }
          description
              "Attribute application-id for event-control";
        } //application-id

        leaf event-name {
          type string {
            length "1..32";
          }
        } //event-name

        leaf event-number {
          type uint32;
        } //event-number

        leaf generate {
          type boolean;
          description
              "keyword - specifies action";
        } //generate

        leaf suppress {
          type boolean;
          description
              "keyword - specifies action";
        } //suppress

        leaf severity-level {
          type enumeration {
            enum cleared;
            enum indeterminate;
            enum critical;
            enum major;
            enum minor;
            enum warning;
          }
        } //severity-level

        leaf throttle {
          type boolean;
          description
              "keyword - specifies action";
        } //throttle

        leaf specific-throttle-rate {
          type uint32 {
            range "1..20000";
          }
        } //specific-throttle-rate

        leaf interval {
          type uint32 {
            range "1..1200";
          }
        } //interval

        leaf disable-specific-throttle {
          type boolean;
        } //disable-specific-throttle

        leaf repeat {
          type boolean;
          description
              "keyword - specifies action";
        } //repeat

        leaf no-repeat {
          type boolean;
          description
              "keyword - specifies action";
        } //no-repeat

      } //list event-control

      leaf event-damping {
        type boolean;
        description
            "Enable/disable change event damping";
      }

      container route-preference {
        description
            "Configure routing preference";
        leaf primary {
          type enumeration {
            enum inband;
            enum outband;
          }
        } //primary

        leaf secondary {
          type enumeration {
            enum inband;
            enum outband;
            enum none;
          }
        } //secondary

      } //container route-preference

      container throttle-rate {
        description
            "Configure event throttling rate";
        leaf events {
          type uint32 {
            range "1..20000";
          }
          description
              "[1..20000] : Default 2000";
        } //events

        leaf interval {
          type uint32 {
            range "1..1200";
          }
          description
              "[1..1200] : Default 1";
        } //interval

      } //container throttle-rate

      list accounting-policy {
        key "acct-policy-id";
        description
            "Configure an accounting-policy";
        leaf acct-policy-id {
          type uint64 {
            range "1..99";
          }
        } //acct-policy-id

        container collection-interval {
          description
              "Configure the accounting collection interval";
          leaf minutes {
            type uint32 {
              range "1..120";
            }
          } //minutes

        } //container collection-interval

        leaf default {
          type boolean;
          description
              "Configure default accounting policy to be used with all objects for the given 
               type that do not have an accounting policy";
        }

        container description {
          description
              "Description for this accounting policy";
          leaf description-string {
            type string {
              length "1..80";
            }
          } //description-string

        } //container description

        leaf include-system-info {
          type boolean;
          description
              "Enable/disable the inclusion of system information in accounting policy 
               records";
        }

        container record {
          description
              "Configure the accounting record type to be forwarded to the configured 
               accounting file";
          leaf record-name {
            type enumeration {
              enum aa-admit-deny;
              enum aa-app-group;
              enum aa-application;
              enum aa-partition;
              enum aa-performance;
              enum aa-protocol;
              enum aa-subscriber-app-group;
              enum aa-subscriber-application;
              enum aa-subscriber-protocol;
              enum combined-ldp-lsp-egress;
              enum combined-mpls-lsp-egress;
              enum combined-mpls-lsp-ingress;
              enum combined-network-ing-egr-octets;
              enum combined-queue-group;
              enum combined-sdp-ingress-egress;
              enum combined-service-ing-egr-octets;
              enum combined-service-ingress;
              enum compact-service-ingress-octets;
              enum complete-pm;
              enum complete-sdp-ingress-egress;
              enum complete-service-ingress-egress;
              enum complete-subscriber-ingress-egress;
              enum custom-record-aa-sub;
              enum custom-record-service;
              enum custom-record-subscriber;
              enum network-egress-octets;
              enum network-egress-packets;
              enum network-ingress-octets;
              enum network-ingress-packets;
              enum queue-group-octets;
              enum queue-group-packets;
              enum saa;
              enum service-egress-octets;
              enum service-egress-packets;
              enum service-ingress-octets;
              enum service-ingress-packets;
              enum video;
              enum complete-ethernet-port;
              enum extended-service-ingress-egress;
              enum complete-network-ing-egr;
            }
          } //record-name

        } //container record

        leaf shutdown {
          type boolean;
          description
              "Administratively enable/disable the policy";
        }

        container to {
          description
              "Specify log destination";
          leaf file {
            type uint16 {
              range "1..99";
            }
          } //file

          leaf no-file {
            type boolean;
          } //no-file

        } //container to

        container custom-record {
          presence
              "Configure the accounting policy custom record";
          container ref-aa-specific-counter {
            description
                "Configure a reference aa counter";
            leaf any {
              type boolean;
            } //any

          } //container ref-aa-specific-counter

          container significant-change {
            description
                "Configure the significant change required to generate the record";
            leaf delta {
              type uint32;
            } //delta

          } //container significant-change

          container aa-specific {
            presence
                "Configure aa info for this custom record";
            container aa-sub-attributes {
              presence
                  "Configure AA subscriber attribute info";
              leaf all {
                type boolean;
                description
                    "Include all subscriber attributes";
              }

              leaf app-profile {
                type boolean;
                description
                    "Include/exclude application profile";
              }

              leaf app-service-options {
                type boolean;
                description
                    "Include/exclude application service options";
              }

            } //container aa-sub-attributes

            container aa-sub-counters {
              presence
                  "Configure AA subscriber counter info";
              leaf all {
                type boolean;
                description
                    "include all counters";
              }

              leaf long-duration-flow-count {
                type boolean;
                description
                    "include/exclude the long duration flow count";
              }

              leaf medium-duration-flow-count {
                type boolean;
                description
                    "include/exclude the medium duration flow count";
              }

              leaf short-duration-flow-count {
                type boolean;
                description
                    "include/exclude the short duration flow count";
              }

              leaf total-flow-duration {
                type boolean;
                description
                    "include/exclude the total flow duration count";
              }

              leaf total-flows-completed-count {
                type boolean;
                description
                    "include/exclude the total flows completed count";
              }

            } //container aa-sub-counters

            container from-aa-sub-counters {
              presence
                  "Configure AA from subscriber counter info";
              leaf all {
                type boolean;
                description
                    "include all counters";
              }

              leaf flows-active-count {
                type boolean;
                description
                    "include/exclude the flows active count";
              }

              leaf flows-admitted-count {
                type boolean;
                description
                    "include/exclude the flows admitted count";
              }

              leaf flows-denied-count {
                type boolean;
                description
                    "include/exclude the flows denied count";
              }

              leaf forwarding-class {
                type boolean;
                description
                    "include/exclude the forwarding-class";
              }

              leaf max-throughput-octet-count {
                type boolean;
                description
                    "include/exclude maximum throughput as measured in octet count";
              }

              leaf max-throughput-packet-count {
                type boolean;
                description
                    "include/exclude maximum throughput as measured in packet count";
              }

              leaf max-throughput-timestamp {
                type boolean;
                description
                    "include/exclude the timestamp of the maximum throughput";
              }

              leaf octets-admitted-count {
                type boolean;
                description
                    "include/exclude the octets admitted count";
              }

              leaf octets-denied-count {
                type boolean;
                description
                    "include/exclude the octets denied count";
              }

              leaf packets-admitted-count {
                type boolean;
                description
                    "include/exclude the packets admitted count";
              }

              leaf packets-denied-count {
                type boolean;
                description
                    "include/exclude the packets-denied count";
              }

            } //container from-aa-sub-counters

            container to-aa-sub-counters {
              presence
                  "Configure AA to subscriber counter info";
              leaf all {
                type boolean;
                description
                    "include all counters";
              }

              leaf flows-active-count {
                type boolean;
                description
                    "include/exclude the flows active count";
              }

              leaf flows-admitted-count {
                type boolean;
                description
                    "include/exclude the flows admitted count";
              }

              leaf flows-denied-count {
                type boolean;
                description
                    "include/exclude the flows denied count";
              }

              leaf forwarding-class {
                type boolean;
                description
                    "include/exclude the forwarding-class";
              }

              leaf max-throughput-octet-count {
                type boolean;
                description
                    "include/exclude maximum throughput as measured in octet count";
              }

              leaf max-throughput-packet-count {
                type boolean;
                description
                    "include/exclude maximum throughput as measured in packet count";
              }

              leaf max-throughput-timestamp {
                type boolean;
                description
                    "include/exclude the timestamp of the maximum throughput";
              }

              leaf octets-admitted-count {
                type boolean;
                description
                    "include/exclude the octets admitted count";
              }

              leaf octets-denied-count {
                type boolean;
                description
                    "include/exclude the octets denied count";
              }

              leaf packets-admitted-count {
                type boolean;
                description
                    "include/exclude the packets admitted count";
              }

              leaf packets-denied-count {
                type boolean;
                description
                    "include/exclude the packets-denied-count";
              }

            } //container to-aa-sub-counters

          } //container aa-specific

          list override-counter {
            key "override-counter-id";
            description
                "Configure an override counter";
            leaf override-counter-id {
              type uint32 {
                range "1..8";
              }
            } //override-counter-id

            container e-counters {
              presence
                  "Configure egress counters for this override";
              leaf all {
                type boolean;
                description
                    "include all counters";
              }

              leaf in-profile-octets-discarded-count {
                type boolean;
                description
                    "include/exclude the in profile octets discarded count";
              }

              leaf in-profile-octets-forwarded-count {
                type boolean;
                description
                    "include/exclude the in profile octets forwarded count";
              }

              leaf in-profile-packets-discarded-count {
                type boolean;
                description
                    "include/exclude the in profile packets discarded count";
              }

              leaf in-profile-packets-forwarded-count {
                type boolean;
                description
                    "include/exclude the in profile packets forwarded count";
              }

              leaf out-profile-octets-discarded-count {
                type boolean;
                description
                    "include/exclude the out profile octets discarded count";
              }

              leaf out-profile-octets-forwarded-count {
                type boolean;
                description
                    "include/exclude the out profile octets forwarded count";
              }

              leaf out-profile-packets-discarded-count {
                type boolean;
                description
                    "include/exclude the out profile packets discarded count";
              }

              leaf out-profile-packets-forwarded-count {
                type boolean;
                description
                    "include/exclude the out profile packets forwarded count";
              }

            } //container e-counters

            container i-counters {
              presence
                  "Configure ingress counters for this override";
              leaf all {
                type boolean;
                description
                    "include all counters";
              }

              leaf all-octets-offered-count {
                type boolean;
                description
                    "include/exclude the all octets offered count";
              }

              leaf all-packets-offered-count {
                type boolean;
                description
                    "include/exclude the all packets offered count";
              }

              leaf high-octets-discarded-count {
                type boolean;
                description
                    "include/exclude the high octets discarded count";
              }

              leaf high-packets-discarded-count {
                type boolean;
                description
                    "include/exclude the high packets discarded count";
              }

              leaf in-profile-octets-forwarded-count {
                type boolean;
                description
                    "include/exclude the in profile octets forwarded count";
              }

              leaf in-profile-packets-forwarded-count {
                type boolean;
                description
                    "include/exclude the in profile packets forwarded count";
              }

              leaf low-octets-discarded-count {
                type boolean;
                description
                    "include/exclude the low octets discarded count";
              }

              leaf low-packets-discarded-count {
                type boolean;
                description
                    "include/exclude the low packets discarded count";
              }

              leaf out-profile-octets-forwarded-count {
                type boolean;
                description
                    "include/exclude the out profile octets forwarded count";
              }

              leaf out-profile-packets-forwarded-count {
                type boolean;
                description
                    "include/exclude the out profile packets forwarded count";
              }

            } //container i-counters

          } //list override-counter

          list queue {
            key "queue-id";
            description
                "Configure a queue";
            leaf queue-id {
              type int32 {
                range "1..32";
              }
            } //queue-id

            container e-counters {
              presence
                  "Configure egress counters for this queue";
              leaf all {
                type boolean;
                description
                    "include all counters";
              }

              leaf in-profile-octets-discarded-count {
                type boolean;
                description
                    "include/exclude the in profile octets discarded count";
              }

              leaf in-profile-octets-forwarded-count {
                type boolean;
                description
                    "include/exclude the in profile octets forwarded count";
              }

              leaf in-profile-packets-discarded-count {
                type boolean;
                description
                    "include/exclude the in profile packets discarded count";
              }

              leaf in-profile-packets-forwarded-count {
                type boolean;
                description
                    "include/exclude the in profile packets forwarded count";
              }

              leaf out-profile-octets-discarded-count {
                type boolean;
                description
                    "include/exclude the out profile octets discarded count";
              }

              leaf out-profile-octets-forwarded-count {
                type boolean;
                description
                    "include/exclude the out profile octets forwarded count";
              }

              leaf out-profile-packets-discarded-count {
                type boolean;
                description
                    "include/exclude the out profile packets discarded count";
              }

              leaf out-profile-packets-forwarded-count {
                type boolean;
                description
                    "include/exclude the out profile packets forwarded count";
              }

            } //container e-counters

            container i-counters {
              presence
                  "Configure ingress counters for this queue";
              leaf all {
                type boolean;
                description
                    "include all counters";
              }

              leaf all-octets-offered-count {
                type boolean;
                description
                    "include/exclude the all octets offered count";
              }

              leaf all-packets-offered-count {
                type boolean;
                description
                    "include/exclude the all packets offered count";
              }

              leaf high-octets-discarded-count {
                type boolean;
                description
                    "include/exclude the high octets discarded count";
              }

              leaf high-octets-offered-count {
                type boolean;
                description
                    "include/exclude the high octets offered count";
              }

              leaf high-packets-discarded-count {
                type boolean;
                description
                    "include/exclude the high packets discarded count";
              }

              leaf high-packets-offered-count {
                type boolean;
                description
                    "include/exclude the high packets offered count";
              }

              leaf in-profile-octets-forwarded-count {
                type boolean;
                description
                    "include/exclude the in profile octets forwarded count";
              }

              leaf in-profile-packets-forwarded-count {
                type boolean;
                description
                    "include/exclude the in profile packets forwarded count";
              }

              leaf low-octets-discarded-count {
                type boolean;
                description
                    "include/exclude the low octets discarded count";
              }

              leaf low-octets-offered-count {
                type boolean;
                description
                    "include/exclude the low octets offered count";
              }

              leaf low-packets-discarded-count {
                type boolean;
                description
                    "include/exclude the low packets discarded count";
              }

              leaf low-packets-offered-count {
                type boolean;
                description
                    "include/exclude the low packets offered count";
              }

              leaf out-profile-octets-forwarded-count {
                type boolean;
                description
                    "include/exclude the out profile octets forwarded count";
              }

              leaf out-profile-packets-forwarded-count {
                type boolean;
                description
                    "include/exclude the out profile packets forwarded count";
              }

              leaf uncoloured-octets-offered-count {
                type boolean;
                description
                    "include/exclude the uncoloured octets offered count";
              }

              leaf uncoloured-packets-offered-count {
                type boolean;
                description
                    "include/exclude the uncoloured packets offered count";
              }

            } //container i-counters

          } //list queue

          container ref-override-counter {
            description
                "Configure a reference override counter";
            leaf ref-override-counter-id {
              type uint32 {
                range "1..8";
              }
            } //ref-override-counter-id

            leaf all {
              type boolean;
            } //all

            container e-counters {
              presence
                  "Configure egress counters for this queue";
              leaf all {
                type boolean;
                description
                    "include all counters";
              }

              leaf in-profile-octets-discarded-count {
                type boolean;
                description
                    "include/exclude the in profile octets discarded count";
              }

              leaf in-profile-octets-forwarded-count {
                type boolean;
                description
                    "include/exclude the in profile octets forwarded count";
              }

              leaf in-profile-packets-discarded-count {
                type boolean;
                description
                    "include/exclude the in profile packets discarded count";
              }

              leaf in-profile-packets-forwarded-count {
                type boolean;
                description
                    "include/exclude the in profile packets forwarded count";
              }

              leaf out-profile-octets-discarded-count {
                type boolean;
                description
                    "include/exclude the out profile octets discarded count";
              }

              leaf out-profile-octets-forwarded-count {
                type boolean;
                description
                    "include/exclude the out profile octets forwarded count";
              }

              leaf out-profile-packets-discarded-count {
                type boolean;
                description
                    "include/exclude the out profile packets discarded count";
              }

              leaf out-profile-packets-forwarded-count {
                type boolean;
                description
                    "include/exclude the out profile packets forwarded count";
              }

            } //container e-counters

            container i-counters {
              presence
                  "Configure ingress counters for this queue";
              leaf all {
                type boolean;
                description
                    "include all counters";
              }

              leaf all-octets-offered-count {
                type boolean;
                description
                    "include/exclude the all octets offered count";
              }

              leaf all-packets-offered-count {
                type boolean;
                description
                    "include/exclude the all packets offered count";
              }

              leaf high-octets-discarded-count {
                type boolean;
                description
                    "include/exclude the high octets discarded count";
              }

              leaf high-packets-discarded-count {
                type boolean;
                description
                    "include/exclude the high packets discarded count";
              }

              leaf in-profile-octets-forwarded-count {
                type boolean;
                description
                    "include/exclude the in profile octets forwarded count";
              }

              leaf in-profile-packets-forwarded-count {
                type boolean;
                description
                    "include/exclude the in profile packets forwarded count";
              }

              leaf low-octets-discarded-count {
                type boolean;
                description
                    "include/exclude the low octets discarded count";
              }

              leaf low-packets-discarded-count {
                type boolean;
                description
                    "include/exclude the low packets discarded count";
              }

              leaf out-profile-octets-forwarded-count {
                type boolean;
                description
                    "include/exclude the out profile octets forwarded count";
              }

              leaf out-profile-packets-forwarded-count {
                type boolean;
                description
                    "include/exclude the out profile packets forwarded count";
              }

            } //container i-counters

          } //container ref-override-counter

          container ref-queue {
            description
                "Configure a reference queue";
            leaf queue-id {
              type int32 {
                range "1..32";
              }
            } //queue-id

            leaf all {
              type boolean;
            } //all

            container e-counters {
              presence
                  "Configure egress counters for this queue";
              leaf all {
                type boolean;
                description
                    "include all counters";
              }

              leaf in-profile-octets-discarded-count {
                type boolean;
                description
                    "include/exclude the in profile octets discarded count";
              }

              leaf in-profile-octets-forwarded-count {
                type boolean;
                description
                    "include/exclude the in profile octets forwarded count";
              }

              leaf in-profile-packets-discarded-count {
                type boolean;
                description
                    "include/exclude the in profile packets discarded count";
              }

              leaf in-profile-packets-forwarded-count {
                type boolean;
                description
                    "include/exclude the in profile packets forwarded count";
              }

              leaf out-profile-octets-discarded-count {
                type boolean;
                description
                    "include/exclude the out profile octets discarded count";
              }

              leaf out-profile-octets-forwarded-count {
                type boolean;
                description
                    "include/exclude the out profile octets forwarded count";
              }

              leaf out-profile-packets-discarded-count {
                type boolean;
                description
                    "include/exclude the out profile packets discarded count";
              }

              leaf out-profile-packets-forwarded-count {
                type boolean;
                description
                    "include/exclude the out profile packets forwarded count";
              }

            } //container e-counters

            container i-counters {
              presence
                  "Configure ingress counters for this queue";
              leaf all {
                type boolean;
                description
                    "include all counters";
              }

              leaf all-octets-offered-count {
                type boolean;
                description
                    "include/exclude the all octets offered count";
              }

              leaf all-packets-offered-count {
                type boolean;
                description
                    "include/exclude the all packets offered count";
              }

              leaf high-octets-discarded-count {
                type boolean;
                description
                    "include/exclude the high octets discarded count";
              }

              leaf high-octets-offered-count {
                type boolean;
                description
                    "include/exclude the high octets offered count";
              }

              leaf high-packets-discarded-count {
                type boolean;
                description
                    "include/exclude the high packets discarded count";
              }

              leaf high-packets-offered-count {
                type boolean;
                description
                    "include/exclude the high packets offered count";
              }

              leaf in-profile-octets-forwarded-count {
                type boolean;
                description
                    "include/exclude the in profile octets forwarded count";
              }

              leaf in-profile-packets-forwarded-count {
                type boolean;
                description
                    "include/exclude the in profile packets forwarded count";
              }

              leaf low-octets-discarded-count {
                type boolean;
                description
                    "include/exclude the low octets discarded count";
              }

              leaf low-octets-offered-count {
                type boolean;
                description
                    "include/exclude the low octets offered count";
              }

              leaf low-packets-discarded-count {
                type boolean;
                description
                    "include/exclude the low packets discarded count";
              }

              leaf low-packets-offered-count {
                type boolean;
                description
                    "include/exclude the low packets offered count";
              }

              leaf out-profile-octets-forwarded-count {
                type boolean;
                description
                    "include/exclude the out profile octets forwarded count";
              }

              leaf out-profile-packets-forwarded-count {
                type boolean;
                description
                    "include/exclude the out profile packets forwarded count";
              }

              leaf uncoloured-octets-offered-count {
                type boolean;
                description
                    "include/exclude the uncoloured octets offered count";
              }

              leaf uncoloured-packets-offered-count {
                type boolean;
                description
                    "include/exclude the uncoloured packets offered count";
              }

            } //container i-counters

          } //container ref-queue

        } //container custom-record

      } //list accounting-policy

      container app-route-notifications {
        description
            "Configure local application route notifications";
        container cold-start-wait {
          description
              "Configure cold start wait time";
          leaf seconds {
            type uint32 {
              range "1..300";
            }
            description
                "[1..300] : Default 0";
          } //seconds

        } //container cold-start-wait

        container route-recovery-wait {
          description
              "Configure route recovery wait time";
          leaf seconds {
            type uint32 {
              range "1..100";
            }
            description
                "[1..100] : Default 0";
          } //seconds

        } //container route-recovery-wait

      } //container app-route-notifications

      container event-handling {
        description
            "Configure an EHS handling";
        list handler {
          key "event-handler-name";
          description
              "Configure EHS handler";
          leaf event-handler-name {
            type string {
              length "1..32";
            }
          } //event-handler-name

          container description {
            description
                "Description for the EHS handler";
            leaf description-string {
              type string {
                length "1..80";
              }
            } //description-string

          } //container description

          leaf shutdown {
            type boolean;
            description
                "Administratively enabled/disabled the EHS handler";
          }

          container action-list {
            description
                "EHS handler action-list";
            list entry {
              key "entry-id";
              description
                  "Configure EHS handler entry";
              leaf entry-id {
                type uint32 {
                  range "1..1500";
                }
              } //entry-id

              container description {
                description
                    "Description for EHS handler entry";
                leaf description-string {
                  type string {
                    length "1..80";
                  }
                } //description-string

              } //container description

              container min-delay {
                description
                    "Specifies minimum delay in seconds between subsequent executions of the 
                     script-policy specified in this entry";
                leaf min-delay-id {
                  type uint32 {
                    range "1..4294967295";
                  }
                  description
                      "1..604800";
                } //min-delay-id

              } //container min-delay

              container script-policy {
                description
                    "Script-policy parameters for this EHS handler";
                leaf policy-name {
                  type string {
                    length "1..32";
                  }
                } //policy-name

                leaf owner {
                  type string {
                    length "1..32";
                  }
                  default "TiMOS CLI";
                  description
                      "[32 chars max] Default - \"TiMOS CLI\"";
                } //owner

              } //container script-policy

              leaf shutdown {
                type boolean;
                description
                    "Administratively enabled/disabled the EHS handler entry";
              }

            } //list entry

          } //container action-list

        } //list handler

      } //container event-handling

      container event-trigger {
        description
            "Configure an EHS triggering";
        list event {
          key "application-id event-name-id";
          description
              "Configure EHS event";
          leaf application-id {
            type string {
              length "1..32";
            }
            description
                "Attribute application-id for event";
          } //application-id

          leaf event-name-id {
            type string;
            description
                "0..4294967295 | 32 chars max";
          } //event-name-id

          container description {
            description
                "Description for the EHS event";
            leaf description-string {
              type string {
                length "1..80";
              }
            } //description-string

          } //container description

          leaf shutdown {
            type boolean;
            description
                "Administratively enabled/disabled the EHS event";
          }

          list trigger-entry {
            key "entry-id";
            description
                "Configure EHS event trigger-entry";
            leaf entry-id {
              type uint32 {
                range "1..1500";
              }
            } //entry-id

            container debounce {
              description
                  "Specify the debounce value to be used in EHS event trigger-entry";
              leaf debounce-id {
                type uint32 {
                  range "2..15";
                }
              } //debounce-id

              leaf within {
                type uint32 {
                  range "1..604800";
                }
              } //within

            } //container debounce

            container description {
              description
                  "Description for the event trigger-entry";
              leaf description-string {
                type string {
                  length "1..80";
                }
              } //description-string

            } //container description

            container event-handler {
              description
                  "Specify event-handler to be used in EHS event trigger-entry";
              leaf event-handler {
                type string {
                  length "1..32";
                }
              } //event-handler

            } //container event-handler

            container log-filter {
              description
                  "Specify filter to be used in EHS event trigger-entry";
              leaf filter-id {
                type uint32 {
                  range "1..1500";
                }
              } //filter-id

            } //container log-filter

            leaf shutdown {
              type boolean;
              description
                  "Administratively enabled/disabled the EHS event trigger-entry";
            }

          } //list trigger-entry

        } //list event

      } //container event-trigger

      list file-id {
        key "log-file-id";
        description
            "Define log and billing files associated with a file-id";
        leaf log-file-id {
          type uint16 {
            range "1..99";
          }
        } //log-file-id

        container description {
          description
              "Description for the log file";
          leaf description-string {
            type string {
              length "1..80";
            }
          } //description-string

        } //container description

        container location {
          description
              "Specify the location for a log file";
          leaf cflash-id {
            type string;
            description
                "Attribute cflash-id for location";
          } //cflash-id

          leaf backup-cflash-id {
            type string;
            description
                "Attribute backup-cflash-id for location";
          } //backup-cflash-id

        } //container location

        container rollover {
          description
              "Define rollover and retention periods for an event log or accounting file";
          leaf minutes {
            type uint32 {
              range "5..10080";
            }
          } //minutes

          leaf retention {
            type uint16 {
              range "1..500";
            }
          } //retention

        } //container rollover

      } //list file-id

      list filter {
        key "filter-id";
        description
            "Configure an event filter";
        leaf filter-id {
          type uint32 {
            range "1..1500";
          }
        } //filter-id

        container default-action {
          description
              "Specify the default action for the event filter";
          leaf drop-forward {
            type enumeration {
              enum drop;
              enum forward;
            }
            description
                "keywords - specify match action";
          } //drop-forward

        } //container default-action

        container description {
          description
              "Description string for the event filter";
          leaf description-string {
            type string {
              length "1..80";
            }
          } //description-string

        } //container description

        list entry {
          key "entry-id";
          description
              "Configure an event filter entry";
          leaf entry-id {
            type uint32 {
              range "1..999";
            }
          } //entry-id

          container action {
            description
                "Specify the action for this event filter entry";
            leaf drop-forward {
              type enumeration {
                enum drop;
                enum forward;
              }
              description
                  "keywords - specify match action";
            } //drop-forward

          } //container action

          container description {
            description
                "Description for this event filter entry";
            leaf description-string {
              type string {
                length "1..80";
              }
            } //description-string

          } //container description

          container match {
            presence
                "Specify match conditions for this event filter entry";
            container application {
              description
                  "Specify application id to match";
              leaf eq-neq {
                type enumeration {
                  enum eq;
                  enum neq;
                }
                description
                    "operator";
              } //eq-neq

              leaf application-id {
                type string {
                  length "1..32";
                }
                description
                    "Attribute application-id for application";
              } //application-id

            } //container application

            container message {
              description
                  "Specify pattern to match message";
              leaf eq-neq {
                type enumeration {
                  enum eq;
                  enum neq;
                }
              } //eq-neq

              leaf pattern {
                type string {
                  length "1..400";
                }
              } //pattern

              leaf regexp {
                type boolean;
                description
                    "keyword : use regular expression match";
              } //regexp

            } //container message

            container number {
              description
                  "Specify event-id number to match";
              leaf eq-neq-lt-lte-gt-gte {
                type enumeration {
                  enum eq;
                  enum neq;
                  enum lt;
                  enum lte;
                  enum gt;
                  enum gte;
                }
                description
                    "operator";
              } //eq-neq-lt-lte-gt-gte

              leaf event-id {
                type uint32 {
                  range "1..4294967295";
                }
              } //event-id

            } //container number

            container router {
              description
                  "Specify router context string to match";
              leaf eq-neq {
                type enumeration {
                  enum eq;
                  enum neq;
                }
                description
                    "operator";
              } //eq-neq

              leaf router-instance {
                type string {
                  length "1..32";
                }
                default "Base";
              } //router-instance

              leaf regexp {
                type boolean;
                description
                    "keyword: use regular expression match";
              } //regexp

            } //container router

            container severity {
              description
                  "Specify severity level to match";
              leaf eq-neq-lt-lte-gt-gte {
                type enumeration {
                  enum eq;
                  enum neq;
                  enum lt;
                  enum lte;
                  enum gt;
                  enum gte;
                }
                description
                    "operator";
              } //eq-neq-lt-lte-gt-gte

              leaf severity-level {
                type enumeration {
                  enum cleared;
                  enum indeterminate;
                  enum critical;
                  enum major;
                  enum minor;
                  enum warning;
                }
              } //severity-level

            } //container severity

            container subject {
              description
                  "Specify subject string to match";
              leaf eq-neq {
                type enumeration {
                  enum eq;
                  enum neq;
                }
                description
                    "operator";
              } //eq-neq

              leaf subject {
                type string {
                  length "1..32";
                }
              } //subject

              leaf regexp {
                type boolean;
                description
                    "keyword: use regular expression match";
              } //regexp

            } //container subject

          } //container match

        } //list entry

      } //list filter

      list log-id {
        key "log-id";
        description
            "Configure an event log destination";
        leaf log-id {
          type uint16 {
            range "1..101";
          }
        } //log-id

        container description {
          description
              "Description for this log-id";
          leaf description-string {
            type string {
              length "1..80";
            }
          } //description-string

        } //container description

        container filter {
          description
              "Specify filter to be used";
          leaf filter-id {
            type uint32 {
              range "1..1500";
            }
          } //filter-id

        } //container filter

        container from {
          description
              "Specify the source event stream directed to this destination";
          leaf main {
            type boolean;
            description
                "keyword - specifies 'main' source stream";
          } //main

          leaf security {
            type boolean;
            description
                "keyword - specifies 'security' source stream";
          } //security

          leaf change {
            type boolean;
            description
                "keyword - specifies 'change' source stream";
          } //change

          leaf debug-trace {
            type boolean;
            description
                "keyword - specifies 'debug-trace' source stream";
          } //debug-trace

        } //container from

        container netconf-stream {
          description
              "Configuer a NETCONF stream";
          leaf stream-name {
            type string;
          } //stream-name

        } //container netconf-stream

        container python-policy {
          description
              "Configure a Python policy to process syslog messages";
          leaf policy-name {
            type string;
          } //policy-name

        } //container python-policy

        leaf shutdown {
          type boolean;
          description
              "Administratively enable/disable the event log";
        }

        container time-format {
          description
              "Specify whether time should be displayed in local or UTC";
          leaf local-utc {
            type enumeration {
              enum local;
              enum utc;
            }
            default "utc";
            description
                "keywords (Default - utc)";
          } //local-utc

        } //container time-format

        container to {
          description
              "Configure the destination type for this event log";
          leaf console {
            type boolean;
            description
                "keyword - specifies console as destination";
          } //console

          leaf syslog {
            type uint16 {
              range "1..10";
            }
          } //syslog

          leaf snmp {
            type boolean;
            description
                "keyword - specifies SNMP as destination";
          } //snmp

          leaf file {
            type uint16 {
              range "1..99";
            }
          } //file

          leaf memory {
            type boolean;
            description
                "keyword - specifies memory as destination";
          } //memory

          leaf session {
            type boolean;
            description
                "keyword - specifies telnet session as destination";
          } //session

          leaf netconf {
            type boolean;
            description
                "keyword - specifies NETCONF as destination";
          } //netconf

          leaf cli {
            type boolean;
            description
                "keyword - set the destination to any subscribed CLI session";
          } //cli

          leaf size {
            type string;
          } //size

        } //container to

      } //list log-id

      list snmp-trap-group {
        key "log-id";
        description
            "Configure SNMP trap receivers and their operational parameters for a given 
             log-id";
        leaf log-id {
          type uint16 {
            range "1..100";
          }
        } //log-id

        container description {
          description
              "Description for this SNMP trap group";
          leaf description-string {
            type string {
              length "1..80";
            }
          } //description-string

        } //container description

        list trap-target {
          key "name";
          description
              "Configure SNMP notification receiver and operation parameters";
          leaf name {
            type string {
              length "1..28";
            }
          } //name

          leaf address {
            type string;
            description
                "Attribute ip-address for trap-target";
          } //address

          leaf port {
            type uint16;
            default 162;
            description
                "[0..65535] Default: 162";
          } //port

          leaf snmpv1-snmpv2c-snmpv3 {
            type enumeration {
              enum snmpv1;
              enum snmpv2c;
              enum snmpv3;
            }
            default "snmpv3";
            description
                "keywords - specify message processing model 
                 Default: snmpv3";
          } //snmpv1-snmpv2c-snmpv3

          leaf notify-community {
            type string {
              length "1..31";
            }
          } //notify-community

          leaf security-level {
            type enumeration {
              enum no-auth-no-privacy;
              enum auth-no-privacy;
              enum privacy;
            }
          } //security-level

          leaf replay {
            type boolean;
            description
                "keyword - enable retransmit of missed notifications";
          } //replay

        } //list trap-target

      } //list snmp-trap-group

      list syslog {
        key "syslog-id";
        description
            "Configure a target syslog host";
        leaf syslog-id {
          type uint16 {
            range "1..10";
          }
        } //syslog-id

        container address {
          description
              "Specify target syslog host address";
          leaf ip-address {
            type string;
            description
                "Attribute ip-address for address";
          } //ip-address

        } //container address

        container description {
          description
              "Description for this target syslog host";
          leaf description-string {
            type string {
              length "1..80";
            }
          } //description-string

        } //container description

        container facility {
          description
              "Configure the facility code that is used for the messages associated with this 
               syslog-id";
          leaf syslog-facility {
            type enumeration {
              enum kernel;
              enum user;
              enum mail;
              enum systemd;
              enum auth;
              enum syslogd;
              enum printer;
              enum netnews;
              enum uucp;
              enum cron;
              enum authpriv;
              enum ftp;
              enum ntp;
              enum logaudit;
              enum logalert;
              enum cron2;
              enum local0;
              enum local1;
              enum local2;
              enum local3;
              enum local4;
              enum local5;
              enum local6;
              enum local7;
            }
          } //syslog-facility

        } //container facility

        container level {
          description
              "Configure the syslog message severity level threshold";
          leaf syslog-level {
            type enumeration {
              enum emergency;
              enum alert;
              enum critical;
              enum error;
              enum warning;
              enum notice;
              enum info;
              enum debug;
            }
          } //syslog-level

        } //container level

        container log-prefix {
          description
              "Configure a string to be prepended to every log message sent to the target 
               syslog host";
          leaf log-prefix-string {
            type string {
              length "1..32";
            }
          } //log-prefix-string

        } //container log-prefix

        container port {
          description
              "Configure the UDP port used to generate syslog messages";
          leaf port {
            type uint16;
          } //port

        } //container port

      } //list syslog

    } //container log

  } //grouping alu-conf-log-r13

} //module  alu-conf-log-r13
