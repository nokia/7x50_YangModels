submodule nokia-state-svc-vprn {

    yang-version "1.1";

    belongs-to nokia-state { prefix "state"; }

    import ietf-inet-types                { prefix "inet"; }
    import ietf-yang-types                { prefix "yang"; }
    import nokia-sros-yang-extensions     { prefix "sros-ext"; }
    import nokia-types-bgp                { prefix "types-bgp"; }
    import nokia-types-eth-cfm            { prefix "types-eth-cfm"; }
    import nokia-types-igmp               { prefix "types-igmp"; }
    import nokia-types-ipsec              { prefix "types-ipsec"; }
    import nokia-types-isa                { prefix "types-isa"; }
    import nokia-types-l2tp               { prefix "types-l2tp"; }
    import nokia-types-log                { prefix "types-log"; }
    import nokia-types-nat                { prefix "types-nat"; }
    import nokia-types-pim                { prefix "types-pim"; }
    import nokia-types-ppp                { prefix "types-ppp"; }
    import nokia-types-qos                { prefix "types-qos"; }
    import nokia-types-router             { prefix "types-router"; }
    import nokia-types-services           { prefix "types-services"; }
    import nokia-types-sros               { prefix "types-sros"; }
    import nokia-types-subscriber-mgmt    { prefix "types-submgt"; }
    import nokia-types-system             { prefix "types-system"; }
    import nokia-types-wlan               { prefix "types-wlan"; }
    import nokia-types-wlangw             { prefix "types-wlangw"; }

    include nokia-state-eth-cfm;
    include nokia-state-service;
    include nokia-state-svc-nat;
    include nokia-state-svc-vprn-dhcp-server;
    include nokia-state-svc-vprn-isis;
    include nokia-state-svc-vprn-msdp;
    include nokia-state-svc-vprn-ospf;
    include nokia-state-svc-vprn-ospf3;
    include nokia-state-svc-vprn-radius;
    include nokia-state-svc-vprn-rip;
    include nokia-state-svc-vprn-ripng;
    include nokia-state-svc-vprn-sub-if;
    include nokia-state-svc-vprn-twamp-light;
    include nokia-state-svc-vprn-vdo-if;

    sros-ext:sros-major-release "rel19";

    organization "Nokia";

    contact
        "Nokia SR OS Support
         Web: <http://www.nokia.com>";

    description
        "Nokia YANG Data model with operational state for vprn services on SR OS based routers.

         Copyright 2016 Nokia. All rights reserved. Reproduction of this document
         is authorized on the condition that the foregoing copyright notice is included.

         This nokia-state-svc-vprn YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-06-25";

    grouping state-svc-vprn {
        list vprn {
            key "service-name";
            description "Enter the vprn list instance";

            leaf service-name {
                type types-services:service-name;
                description "Service name";
            }

            leaf oper-service-id {
                type types-services:service-id;
                description "Service identifier";
            }

            leaf oper-state {
                type types-sros:oper-state;
                description "Operational state.";
            }

            leaf sap-count {
                type int32;
                description "Number of SAPs";
            }

            leaf sdp-bind-count {
                type int32;
                description "Number of SDP binds";
            }

            leaf template-used {
                type string;
                description "Template used to create this service";
            }

            leaf creation-origin {
                type types-sros:creation-origin;
                description "Creation origin of the service";
            }

            leaf vrtr-id {
                type int32;
                description "The virtual router index.";
            }

            leaf oper-router-id {
                type types-sros:ipv4-address;
                description "Indicates the operational router-id.";
            }

            leaf oper-route-distinguisher-type {
                type enumeration {
                    enum "none"                         { value 0; }
                    enum "configured"                   { value 1; }
                    enum "auto"                         { value 4; }
                }
                description "Indicates the route-distinguisher origin.";
            }

            leaf oper-route-distinguisher {
                type string;
                description "Indicates the operational route-distinguisher.";
            }

            container nat {
                description "Enter the nat context";

                leaf outside-dnat-only-routes-counter {
                    type yang:gauge32;
                    description
                        "the actual number of routes used to direct
                         downstream traffic from this outside virtual router instance
                         to a NAT ISA card in Destination NAT operation";
                }

                container inside {
                    description "Enter the inside context";

                    container large-scale {
                        description "Enter the large-scale context";

                        container nat44 {
                            description "Enter the nat44 context";

                            container deterministic {
                                description "Enter the deterministic context";

                                list policy-map {
                                    key "source-prefix";
                                    description "Enter the policy-map list instance";

                                    leaf source-prefix {
                                        type types-sros:ipv4-unicast-prefix;
                                        description "Source prefix that adds traffic to NAT pool";
                                    }

                                    leaf oper-state {
                                        type types-sros:up-down-status;
                                    }

                                    list map {
                                        key "from to";
                                        description "Enter the map list instance";

                                        leaf from {
                                            type types-sros:ipv4-address;
                                            description "Beginning of the range for IPv4 addresses that is mapped on the inside to outside IPv4 addresses";
                                        }

                                        leaf to {
                                            type types-sros:ipv4-address;
                                            description "Ending of the range for IPv4 addresses that is mapped on the inside to outside IPv4 addresses";
                                        }

                                        leaf oper-state {
                                            type types-sros:up-down-status;
                                        }

                                    } // list map

                                } // list policy-map

                            } // container deterministic

                            list subscriber {
                                key "id nat-policy";
                                description "Large-Scale Classic Nat44 subscribers";

                                leaf id {
                                    type uint32;
                                    description "Identifier of this subscriber";
                                }

                                leaf nat-policy {
                                    type types-sros:named-item;
                                    description "NAT Policy associated with this subscriber";
                                }

                                leaf name {
                                    type types-sros:named-item;
                                    description
                                        "Subscriber's identification string.

                                         A string enclosed by square brackets [] indicates an automatically system-generated name";
                                }

                                leaf type {
                                    type types-nat:sub-type;
                                    description "Type of this subscriber";
                                }

                                leaf inside-ip-prefix {
                                    type types-sros:ip-prefix;
                                    description "Inside IP prefix";
                                }

                                leaf nat-group {
                                    type uint8;
                                    description "Identifier of the NAT Integrated Service Adaptor group";
                                }

                                leaf group-member {
                                    type types-nat:bb-group-member;
                                    description "Identifier of the NAT group member";
                                }

                                container statistics {

                                    container protocol {

                                        container icmp {

                                            leaf port-usage {
                                                type types-sros:percent;
                                                description "ICMP port usage of this NAT subscriber and policy";
                                            }

                                            leaf port-usage-high {
                                                type boolean;
                                                description "ICMP port usage has reached configured limit";
                                            }

                                        } // container icmp

                                        container tcp {

                                            leaf port-usage {
                                                type types-sros:percent;
                                                description "TCP port usage of this NAT subscriber and policy";
                                            }

                                            leaf port-usage-high {
                                                type boolean;
                                                description "TCP port usage has reached configured limit";
                                            }

                                        } // container tcp

                                        container udp {

                                            leaf port-usage {
                                                type types-sros:percent;
                                                description "UDP port usage of this NAT subscriber and policy";
                                            }

                                            leaf port-usage-high {
                                                type boolean;
                                                description "UDP port usage has reached configured limit";
                                            }

                                        } // container udp

                                    } // container protocol

                                    container sessions {

                                        leaf usage {
                                            type types-sros:percent;
                                            description "Session usage of this NAT subscriber and policy";
                                        }

                                        leaf usage-high {
                                            type boolean;
                                            description "Session usage has reached configured limit";
                                        }

                                        leaf active {
                                            type uint32;
                                            description "Number of active sessions of this NAT subscriber and policy";
                                        }

                                        leaf reserved {
                                            type uint32;
                                            description "Number of active prioritized sessions of this subscriber and policy";
                                        }

                                        leaf peak {
                                            type uint32;
                                            description "Maximum number of sessions that were active together up to this point in time";
                                        }

                                    } // container sessions

                                } // container statistics

                                list port-block {
                                    key "outside-router-instance outside-ip-address start";
                                    description "Port block allocated to the Large-Scale Classic Nat44 subscriber";

                                    leaf outside-router-instance {
                                        type types-sros:router-instance;
                                        description "Outside router instance";
                                    }

                                    leaf outside-ip-address {
                                        type types-sros:ipv4-address;
                                        description "Outside IP address";
                                    }

                                    leaf start {
                                        type uint32;
                                        description "Start of the port block allocated to the subscriber";
                                    }

                                    leaf end {
                                        type uint32;
                                        description "End of the port block allocated to the subscriber";
                                    }

                                } // list port-block

                            } // list subscriber

                        } // container nat44

                        container dual-stack-lite {
                            description "Enter the dual-stack-lite context";

                            container deterministic {
                                description "Enter the deterministic context";

                                list policy-map {
                                    key "source-prefix";
                                    description "Enter the policy-map list instance";

                                    leaf source-prefix {
                                        type types-sros:ipv6-unicast-prefix;
                                        description "Source prefix that adds traffic to NAT pool";
                                    }

                                    leaf oper-state {
                                        type types-sros:up-down-status;
                                    }

                                    list map {
                                        key "from to";
                                        description "Enter the map list instance";

                                        leaf from {
                                            type types-sros:ipv6-prefix;
                                            description "Beginning of the range for IPv6 addresses that is mapped on the inside to outside IPv6addresses";
                                        }

                                        leaf to {
                                            type types-sros:ipv6-prefix;
                                            description "Ending of the range for IPv6 addresses that is mapped on the inside to outside IPv6 addresses";
                                        }

                                        leaf oper-state {
                                            type types-sros:up-down-status;
                                        }

                                    } // list map

                                } // list policy-map

                            } // container deterministic

                            list subscriber {
                                key "id nat-policy";
                                description "Dual-Stack-Lite NAT subscribers";

                                leaf id {
                                    type uint32;
                                    description "Identifier of this subscriber";
                                }

                                leaf nat-policy {
                                    type types-sros:named-item;
                                    description "NAT Policy associated with this subscriber";
                                }

                                leaf name {
                                    type types-sros:named-item;
                                    description
                                        "Subscriber's identification string.

                                         A string enclosed by square brackets [] indicates an automatically system-generated name";
                                }

                                leaf type {
                                    type types-nat:sub-type;
                                    description "Type of this subscriber";
                                }

                                leaf inside-ip-prefix {
                                    type types-sros:ip-prefix;
                                    description "Inside IP prefix";
                                }

                                leaf nat-group {
                                    type uint8;
                                    description "Identifier of the NAT Integrated Service Adaptor group";
                                }

                                leaf group-member {
                                    type types-nat:bb-group-member;
                                    description "Identifier of the NAT group member";
                                }

                                container statistics {

                                    container protocol {

                                        container icmp {

                                            leaf port-usage {
                                                type types-sros:percent;
                                                description "ICMP port usage of this NAT subscriber and policy";
                                            }

                                            leaf port-usage-high {
                                                type boolean;
                                                description "ICMP port usage has reached configured limit";
                                            }

                                        } // container icmp

                                        container tcp {

                                            leaf port-usage {
                                                type types-sros:percent;
                                                description "TCP port usage of this NAT subscriber and policy";
                                            }

                                            leaf port-usage-high {
                                                type boolean;
                                                description "TCP port usage has reached configured limit";
                                            }

                                        } // container tcp

                                        container udp {

                                            leaf port-usage {
                                                type types-sros:percent;
                                                description "UDP port usage of this NAT subscriber and policy";
                                            }

                                            leaf port-usage-high {
                                                type boolean;
                                                description "UDP port usage has reached configured limit";
                                            }

                                        } // container udp

                                    } // container protocol

                                    container sessions {

                                        leaf usage {
                                            type types-sros:percent;
                                            description "Session usage of this NAT subscriber and policy";
                                        }

                                        leaf usage-high {
                                            type boolean;
                                            description "Session usage has reached configured limit";
                                        }

                                        leaf active {
                                            type uint32;
                                            description "Number of active sessions of this NAT subscriber and policy";
                                        }

                                        leaf reserved {
                                            type uint32;
                                            description "Number of active prioritized sessions of this subscriber and policy";
                                        }

                                        leaf peak {
                                            type uint32;
                                            description "Maximum number of sessions that were active together up to this point in time";
                                        }

                                    } // container sessions

                                } // container statistics

                                list port-block {
                                    key "outside-router-instance outside-ip-address start";
                                    description "Port block allocated to the Dual-Stack-Lite NAT subscriber";

                                    leaf outside-router-instance {
                                        type types-sros:router-instance;
                                        description "Outside router instance";
                                    }

                                    leaf outside-ip-address {
                                        type types-sros:ipv4-address;
                                        description "Outside IP address";
                                    }

                                    leaf start {
                                        type uint32;
                                        description "Start of the port block allocated to the subscriber";
                                    }

                                    leaf end {
                                        type uint32;
                                        description "End of the port block allocated to the subscriber";
                                    }

                                } // list port-block

                            } // list subscriber

                        } // container dual-stack-lite

                        container nat64 {
                            description "Enter the nat64 context";

                            list subscriber {
                                key "id nat-policy";
                                description "NAT64 subscribers";

                                leaf id {
                                    type uint32;
                                    description "Identifier of this subscriber";
                                }

                                leaf nat-policy {
                                    type types-sros:named-item;
                                    description "NAT Policy associated with this subscriber";
                                }

                                leaf name {
                                    type types-sros:named-item;
                                    description
                                        "Subscriber's identification string.

                                         A string enclosed by square brackets [] indicates an automatically system-generated name";
                                }

                                leaf type {
                                    type types-nat:sub-type;
                                    description "Type of this subscriber";
                                }

                                leaf inside-ip-prefix {
                                    type types-sros:ip-prefix;
                                    description "Inside IP prefix";
                                }

                                leaf nat-group {
                                    type uint8;
                                    description "Identifier of the NAT Integrated Service Adaptor group";
                                }

                                leaf group-member {
                                    type types-nat:bb-group-member;
                                    description "Identifier of the NAT group member";
                                }

                                container statistics {

                                    container protocol {

                                        container icmp {

                                            leaf port-usage {
                                                type types-sros:percent;
                                                description "ICMP port usage of this NAT subscriber and policy";
                                            }

                                            leaf port-usage-high {
                                                type boolean;
                                                description "ICMP port usage has reached configured limit";
                                            }

                                        } // container icmp

                                        container tcp {

                                            leaf port-usage {
                                                type types-sros:percent;
                                                description "TCP port usage of this NAT subscriber and policy";
                                            }

                                            leaf port-usage-high {
                                                type boolean;
                                                description "TCP port usage has reached configured limit";
                                            }

                                        } // container tcp

                                        container udp {

                                            leaf port-usage {
                                                type types-sros:percent;
                                                description "UDP port usage of this NAT subscriber and policy";
                                            }

                                            leaf port-usage-high {
                                                type boolean;
                                                description "UDP port usage has reached configured limit";
                                            }

                                        } // container udp

                                    } // container protocol

                                    container sessions {

                                        leaf usage {
                                            type types-sros:percent;
                                            description "Session usage of this NAT subscriber and policy";
                                        }

                                        leaf usage-high {
                                            type boolean;
                                            description "Session usage has reached configured limit";
                                        }

                                        leaf active {
                                            type uint32;
                                            description "Number of active sessions of this NAT subscriber and policy";
                                        }

                                        leaf reserved {
                                            type uint32;
                                            description "Number of active prioritized sessions of this subscriber and policy";
                                        }

                                        leaf peak {
                                            type uint32;
                                            description "Maximum number of sessions that were active together up to this point in time";
                                        }

                                    } // container sessions

                                } // container statistics

                                list port-block {
                                    key "outside-router-instance outside-ip-address start";
                                    description "Port block allocated to the NAT64 subscriber";

                                    leaf outside-router-instance {
                                        type types-sros:router-instance;
                                        description "Outside router instance";
                                    }

                                    leaf outside-ip-address {
                                        type types-sros:ipv4-address;
                                        description "Outside IP address";
                                    }

                                    leaf start {
                                        type uint32;
                                        description "Start of the port block allocated to the subscriber";
                                    }

                                    leaf end {
                                        type uint32;
                                        description "End of the port block allocated to the subscriber";
                                    }

                                } // list port-block

                            } // list subscriber

                        } // container nat64

                    } // container large-scale

                } // container inside

                container outside {
                    description "Enter the outside context";

                    list pool {
                        key "name";
                        description "Enter the pool list instance";

                        leaf name {
                            type types-sros:named-item;
                            description "NAT pool name";
                        }

                        leaf oper-mode {
                            type types-nat:pool-mode;
                            description "Mode of operation";
                        }

                        container large-scale {
                            description "Enter the large-scale context";

                            container redundancy {
                                description "Enter the redundancy context";

                                leaf state {
                                    type enumeration {
                                        enum "down"                         { value 0; }
                                        enum "down-held"                    { value 1; }
                                        enum "standby"                      { value 2; }
                                        enum "standby-held"                 { value 3; }
                                        enum "active"                       { value 4; }
                                        enum "active-held"                  { value 5; }
                                        enum "active-sick"                  { value 6; }
                                        enum "needs-audit"                  { value 7; }
                                        enum "disabled-up"                  { value 8; }
                                        enum "disabled-down"                { value 9; }
                                    }
                                    description "Dual-homing state in a multi-chassis redundancy environment";
                                }

                            } // container redundancy

                            list group-member {
                                key "group-member";
                                description "LSN member info";

                                leaf group-member {
                                    type types-nat:bb-group-member;
                                    description "group member ID";
                                }

                                leaf block-usage {
                                    type types-sros:percent;
                                    description "Port block usage in large-scale NAT";
                                }

                                leaf high-watermark-reached {
                                    type boolean;
                                    description "High watermark reached for the large-scale NAT block usage";
                                }

                            } // list group-member

                        } // container large-scale

                        container l2-aware {
                            description "Enter the l2-aware context";

                            leaf block-usage {
                                type types-sros:percent;
                                description "Port block usage in L2-aware NAT";
                            }

                            leaf high-watermark-reached {
                                type boolean;
                                description "High watermark reached for the l2-aware block usage";
                            }

                        } // container l2-aware

                        list address-range {
                            key "start end";
                            description "Enter the address-range list instance";

                            leaf start {
                                type types-sros:ipv4-unicast-address;
                                description "Start address of this range";
                            }

                            leaf end {
                                type types-sros:ipv4-unicast-address;
                                description "End address of this range";
                            }

                            leaf allocated-blocks {
                                type uint32;
                                description "Number of allocated blocks";
                            }

                        } // list address-range

                    } // list pool

                    container large-scale {
                        description "Large-scale";

                        list block {
                            key "address first-port";
                            description "Large-scale subscriber blocks";

                            leaf address {
                                type types-sros:ipv4-unicast-address;
                                description "Outside IP address";
                            }

                            leaf first-port {
                                type types-nat:port-number;
                                description "First outside port";
                            }

                            leaf last-port {
                                type types-nat:port-number;
                                description "Last outside port";
                            }

                            leaf nat-policy {
                                type types-sros:named-item;
                                description "NAT policy";
                            }

                            leaf nat-pool {
                                type types-sros:named-item;
                                description "NAT pool";
                            }

                            leaf subscriber-id {
                                type uint32;
                                description "Subscriber ID";
                            }

                            leaf allocation-time {
                                type types-sros:date-time;
                                description "Allocation time";
                            }

                            container inside {
                                description "Inside information";

                                leaf router-instance {
                                    type types-sros:router-instance;
                                    description "Inside service";
                                }

                                leaf address {
                                    type types-sros:ip-address;
                                    description "Inside address";
                                }

                            } // container inside

                        } // list block

                    } // container large-scale

                } // container outside

                container map {
                    description "Enter the map context";

                    list map-domain {
                        key "domain-name";
                        description "Add a list entry for map-domain";

                        leaf domain-name {
                            type leafref {
                                path "../../../../../nat/map-t/domain/name";
                            }
                            description "MAP domain name";
                        }

                        container statistics {
                            description "Statistics";

                            container upstream {
                                description "Upstream statistics";

                                leaf forwarded-packets {
                                    type yang:counter64;
                                    description "Number of packets forwarded in the upstream direction";
                                }

                                leaf forwarded-octets {
                                    type yang:counter64;
                                    description "Number of octets forwarded in the upstream direction";
                                }

                                leaf dropped-packets {
                                    type yang:counter64;
                                    description "Number of packets dropped in the upstream direction";
                                }

                                leaf dropped-octets {
                                    type yang:counter64;
                                    description "Number of octets dropped in the upstream direction";
                                }

                            } // container upstream

                            container downstream {
                                description "Downstream statistics";

                                leaf forwarded-packets {
                                    type yang:counter64;
                                    description "Number of packets forwarded in the downstream direction";
                                }

                                leaf forwarded-octets {
                                    type yang:counter64;
                                    description "Number of octets forwarded in the downstream direction";
                                }

                                leaf dropped-packets {
                                    type yang:counter64;
                                    description "Number of packets dropped in the downstream direction";
                                }

                                leaf dropped-octets {
                                    type yang:counter64;
                                    description "Number of octets dropped in the downstream direction";
                                }

                            } // container downstream

                        } // container statistics

                    } // list map-domain

                } // container map

            } // container nat

            container gtp {
                description "Enter the gtp context";

                list control-plane-peer {
                    key "remote-address udp-port";
                    description "A GTP-c peer";

                    leaf remote-address {
                        type types-sros:ip-address;
                        description "IP Address of the GTP-C peer";
                    }

                    leaf udp-port {
                        type types-sros:tcp-udp-port;
                        description "UDP port used by the GTP-C peer";
                    }

                    leaf local-address {
                        type types-sros:ip-address;
                        description "Local IP address";
                    }

                    leaf oper-state {
                        type types-wlangw:mobile-gateway-state;
                        description "Connection state";
                    }

                    leaf profile {
                        type types-sros:named-item;
                        description "Profile";
                    }

                    leaf gtp-c-version {
                        type uint32 {
                            range "1..2";
                        }
                        description "GTP-C protocol version";
                    }

                    leaf interface-type {
                        type types-wlangw:mobile-gateway-connection;
                        description "Interface type";
                    }

                    leaf restart-count {
                        type uint32;
                        description "Number of times this connection is restarted";
                    }

                    leaf up-time {
                        type yang:date-and-time;
                        description "Moment when this connection was created";
                    }

                    container statistics {
                        description "Protocol statistics for this connection";

                        leaf tx-echo-requests {
                            type yang:counter32;
                            description "Echo request transmitted";
                        }

                        leaf tx-echo-responses {
                            type yang:counter32;
                            description "Echo response transmitted";
                        }

                        leaf rx-echo-requests {
                            type yang:counter32;
                            description "Echo request received";
                        }

                        leaf rx-echo-responses {
                            type yang:counter32;
                            description "Echo response received";
                        }

                        leaf rx-version-not-supported {
                            type yang:counter32;
                            description "Version not supported";
                        }

                        leaf rx-malformed-packets {
                            type yang:counter32;
                            description "Malformed packets";
                        }

                        leaf rx-unknown-packets {
                            type yang:counter32;
                            description "Unknown packets";
                        }

                        leaf rx-missing-ie-packets {
                            type yang:counter32;
                            description "Packets with missing IEs";
                        }

                        leaf peer-restarts {
                            type yang:counter32;
                            description "Peer restarts";
                        }

                        leaf peer-restart-counter {
                            type yang:counter32;
                            description "Peer restarts counter";
                        }

                        leaf path-management-failures {
                            type yang:counter32;
                            description "Path management failures";
                        }

                        leaf create-pdp-request {
                            type yang:counter32;
                            description "Create-PDP-context requests";
                        }

                        leaf create-pdp-response {
                            type yang:counter32;
                            description "Create-PDP-context responses";
                        }

                        leaf delete-pdp-request {
                            type yang:counter32;
                            description "Delete-PDP-context requests";
                        }

                        leaf delete-pdp-response {
                            type yang:counter32;
                            description "Delete-PDP-context responses";
                        }

                        leaf modify-pdp-request {
                            type yang:counter32;
                            description "Modify-PDP-context requests";
                        }

                        leaf modify-pdp-response {
                            type yang:counter32;
                            description "Modify-PDP-context responses";
                        }

                        leaf create-session-request {
                            type yang:counter32;
                            description "Create-session requests";
                        }

                        leaf create-session-response {
                            type yang:counter32;
                            description "Create-session responses";
                        }

                        leaf delete-session-request {
                            type yang:counter32;
                            description "Delete-session requests";
                        }

                        leaf delete-session-response {
                            type yang:counter32;
                            description "Delete-session responses";
                        }

                        leaf create-bearer-request {
                            type yang:counter32;
                            description "Create-bearer requests";
                        }

                        leaf create-bearer-response {
                            type yang:counter32;
                            description "Create-bearer responses";
                        }

                        leaf delete-bearer-request {
                            type yang:counter32;
                            description "Delete-bearer requests";
                        }

                        leaf delete-bearer-response {
                            type yang:counter32;
                            description "Delete-bearer responses";
                        }

                        leaf update-bearer-request {
                            type yang:counter32;
                            description "Update-bearer requests";
                        }

                        leaf update-bearer-response {
                            type yang:counter32;
                            description "Update-bearer responses";
                        }

                        leaf modify-bearer-request {
                            type yang:counter32;
                            description "Modify-bearer requests";
                        }

                        leaf modify-bearer-response {
                            type yang:counter32;
                            description "Modify-bearer responses";
                        }

                        leaf release-access-bearers-request {
                            type yang:counter32;
                            description "Release-access-bearers requests";
                        }

                        leaf release-access-bearers-response {
                            type yang:counter32;
                            description "Release-access-bearers responses";
                        }

                        leaf downlink-notification {
                            type yang:counter32;
                            description "Downlink-notification";
                        }

                        leaf downlink-notification-ack {
                            type yang:counter32;
                            description "Downlink-notification ack";
                        }

                        leaf downlink-notification-fail {
                            type yang:counter32;
                            description "Downlink notification fail";
                        }

                        leaf stop-paging {
                            type yang:counter32;
                            description "Stop-paging indication";
                        }

                        leaf change-notification-request {
                            type yang:counter32;
                            description "Change-notification requests";
                        }

                        leaf change-notification-response {
                            type yang:counter32;
                            description "Change-notification responses";
                        }

                        leaf bearers {
                            type yang:counter32;
                            description "Number of bearers";
                        }

                    } // container statistics

                } // list control-plane-peer

                list dsm-peer {
                    key "remote-address udp-port local-address";
                    description "A DSM GTP-c peer";

                    leaf remote-address {
                        type types-sros:ip-address;
                        description "IP Address of the GTP-C peer";
                    }

                    leaf udp-port {
                        type types-sros:tcp-udp-port;
                        description "UDP port used by the GTP-C peer";
                    }

                    leaf local-address {
                        type types-sros:ip-address;
                        description "Local IP address";
                    }

                    leaf oper-state {
                        type types-wlangw:mobile-gateway-state;
                        description "Connection state";
                    }

                    leaf profile {
                        type types-sros:named-item;
                        description "Profile";
                    }

                    leaf gtp-c-version {
                        type uint32 {
                            range "1..2";
                        }
                        description "GTP-C protocol version";
                    }

                    leaf interface-type {
                        type types-wlangw:mobile-gateway-connection;
                        description "Interface type";
                    }

                    leaf restart-count {
                        type uint32;
                        description "Number of times this connection is restarted";
                    }

                    leaf up-time {
                        type yang:date-and-time;
                        description "Moment when this connection was created";
                    }

                    container statistics {
                        description "Protocol statistics for this connection";

                        leaf parse-error {
                            type yang:counter64;
                            description "Packets dropped because of parse errors";
                        }

                        leaf no-resources {
                            type yang:counter64;
                            description "Number of packets dropped because not enough resources were available";
                        }

                        leaf peer-restart {
                            type yang:counter64;
                            description "Number of times the peer connection was restarted";
                        }

                        leaf session-dropped {
                            type yang:counter64;
                            description "Number of sessions dropped";
                        }

                        container gtp-v1 {
                            description "GTPv1 statistics";

                            leaf invalid {
                                type yang:counter64;
                                description "Invalid";
                            }

                            leaf failed {
                                type yang:counter64;
                                description "Failed";
                            }

                            leaf ignored {
                                type yang:counter64;
                                description "Ignored";
                            }

                            leaf echo-request {
                                type yang:counter64;
                                description "Echo requests";
                            }

                            leaf echo-response {
                                type yang:counter64;
                                description "Echo responses";
                            }

                            leaf create-pdp-context-request {
                                type yang:counter64;
                                description "Create-PDP-context requests";
                            }

                            leaf create-pdp-context-response {
                                type yang:counter64;
                                description "Create-PDP-context responses";
                            }

                            leaf create-pdp-context-timeout {
                                type yang:counter64;
                                description "Timed out create-PDP-context requests";
                            }

                            leaf delete-pdp-context-request {
                                type yang:counter64;
                                description "Delete-PDP-context requests";
                            }

                            leaf delete-pdp-context-response {
                                type yang:counter64;
                                description "Delete-PDP-context responses";
                            }

                            leaf delete-pdp-context-request-invalid {
                                type yang:counter64;
                                description "Invalid delete-PDP-context requests";
                            }

                            leaf delete-pdp-context-timeout {
                                type yang:counter64;
                                description "Timed out delete-pdp-context requests";
                            }

                            leaf version-not-supported {
                                type yang:counter64;
                                description "Version not supported";
                            }

                        } // container gtp-v1

                        container gtp-v2 {
                            description "GTPv2 statistics";

                            leaf invalid {
                                type yang:counter64;
                                description "Invalid";
                            }

                            leaf failed {
                                type yang:counter64;
                                description "Failed";
                            }

                            leaf ignored {
                                type yang:counter64;
                                description "Ignored";
                            }

                            leaf echo-request {
                                type yang:counter64;
                                description "Echo requests";
                            }

                            leaf echo-response {
                                type yang:counter64;
                                description "Echo responses";
                            }

                            leaf create-session-request {
                                type yang:counter64;
                                description "Create-session requests";
                            }

                            leaf create-session-response {
                                type yang:counter64;
                                description "Create-session responses";
                            }

                            leaf create-session-timeout {
                                type yang:counter64;
                                description "Timed oud create-session requests";
                            }

                            leaf delete-session-request {
                                type yang:counter64;
                                description "Delete-session requests";
                            }

                            leaf delete-session-response {
                                type yang:counter64;
                                description "Delete-session responses";
                            }

                            leaf delete-session-timeout {
                                type yang:counter64;
                                description "Timed out delete-session requests";
                            }

                            leaf delete-bearer-request {
                                type yang:counter64;
                                description "Delete-bearer requests";
                            }

                            leaf delete-bearer-response {
                                type yang:counter64;
                                description "Delete-bearer responses";
                            }

                            leaf delete-bearer-request-invalid {
                                type yang:counter64;
                                description "Invalid delete-bearer requests";
                            }

                            leaf version-not-supported {
                                type yang:counter64;
                                description "Version not supported";
                            }

                        } // container gtp-v2

                        container gtp-u {
                            description "GTP-U statistics";

                            leaf invalid {
                                type yang:counter64;
                                description "Invalid";
                            }

                            leaf failed {
                                type yang:counter64;
                                description "Failed";
                            }

                            leaf ignored {
                                type yang:counter64;
                                description "Ignored";
                            }

                            leaf error-indication {
                                type yang:counter64;
                                description "Error-indications";
                            }

                            leaf forward-upstream {
                                type yang:counter64;
                                description "Number of packets forwarded upstream";
                            }

                            leaf forward-downstream {
                                type yang:counter64;
                                description "Number of packets forwarded downstream";
                            }

                        } // container gtp-u

                    } // container statistics

                } // list dsm-peer

                container dns-cache {
                    description "DNS cache for APN based GTP peer lookups";

                    list a-record {
                        key "name index";
                        description "A-record cache entry";

                        leaf name {
                            type string;
                            description "Record name";
                        }

                        leaf index {
                            type uint32;
                            description "Index to distinguish multiple entries with the same name";
                        }

                        leaf address {
                            type types-sros:ip-address;
                            description "Resolved address";
                        }

                        leaf ttl {
                            type uint32;
                            description "Remaining time this entry is valid";
                        }

                    } // list a-record

                    list snaptr-record {
                        key "name order index";
                        description "SNAPTR-record cache entry";

                        leaf name {
                            type string;
                            description "Record name";
                        }

                        leaf order {
                            type uint32;
                            description "Ordinal indicating in which order entries with the same name should be processed";
                        }

                        leaf index {
                            type uint32;
                            description "Index to distinguish entries with the same name and order";
                        }

                        leaf preference {
                            type uint32;
                            description "Number indicating preference of this entry, lower numbers mean higher preference";
                        }

                        leaf service {
                            type string;
                            description "Service associated with this entry";
                        }

                        leaf next-lookup {
                            type enumeration {
                                enum "dns-srv"                      { value 1; }
                                enum "dns-a"                        { value 2; }
                                enum "dns-naptr"                    { value 3; }
                            }
                            description "The record type to be used in the next lookup";
                        }

                        leaf next-lookup-name {
                            type string;
                            description "The record name to be used in the next lookup";
                        }

                        leaf ttl {
                            type uint32;
                            description "Remaining time this entry is valid";
                        }

                    } // list snaptr-record

                    list srv-record {
                        key "name priority index";
                        description "SRV-record cache entry";

                        leaf name {
                            type string;
                            description "Record name";
                        }

                        leaf priority {
                            type uint32 {
                                range "0..65535";
                            }
                            description "Ordinal indicating in which order entries with the same name should be processed";
                        }

                        leaf index {
                            type uint32;
                            description "Index to distinguish entries with the same name and priority";
                        }

                        leaf weight {
                            type uint32 {
                                range "0..65535";
                            }
                            description "Weight used in determining which entry to use when multiple entries have the same priority. Entries with higher weight should have a higher probability of being used.";
                        }

                        leaf port {
                            type types-sros:tcp-udp-port;
                            description "Port of this service on the target host";
                        }

                        leaf target {
                            type string;
                            description "Domain name of the target host";
                        }

                        leaf ttl {
                            type uint32;
                            description "Remaining time this entry is valid";
                        }

                    } // list srv-record

                } // container dns-cache

            } // container gtp

            container l2tp {
                description "Enter the l2tp context";

                container statistics {

                    leaf last-cleared {
                        type yang:date-and-time;
                        description "Indicates when the statistics were cleared.";
                    }

                    leaf total-tunnels {
                        type yang:counter32;
                        description
                            "The total number of tunnels set up attempts since the last
                             re-initialization of the local network management subsystem,
                             or the last time the system statistics were cleared.";
                    }

                    leaf failed-tunnels {
                        type yang:counter32;
                        description
                            "The total number of tunnels that failed to reach the established
                             state since the last re-initialization of the local network
                             management subsystem, or the last time the system statistics were
                             cleared.";
                    }

                    leaf failed-authentication {
                        type yang:counter32;
                        description
                            "The total number of tunnels that failed authentication
                             since the last re-initialization of the local network
                             management subsystem, or the last time the system statistics were
                             cleared.";
                    }

                    leaf actual-tunnels {
                        type yang:counter32;
                        description "The actual number of tunnels.";
                    }

                    leaf active-tunnels {
                        type yang:counter32;
                        description "The number of tunnels currently established.";
                    }

                    leaf total-sessions {
                        type yang:counter32;
                        description
                            "The total number of session set up attempts since the last
                             re-initialization of the local network management subsystem,
                             or the last time the system statistics were cleared.";
                    }

                    leaf failed-sessions {
                        type yang:counter32;
                        description
                            "The total number of sessions that failed to reach the established
                             state since the last re-initialization of the local network
                             management subsystem, or the last time the system statistics were
                             cleared.";
                    }

                    leaf actual-sessions {
                        type yang:counter32;
                        description "The actual number of sessions.";
                    }

                    leaf active-sessions {
                        type yang:counter32;
                        description "The number of sessions currently established.";
                    }

                    leaf blacklist-len {
                        type yang:gauge32;
                        description
                            "The actual number of tunnels and peers in the tunnel
                             selection blacklist.";
                    }

                    leaf unavailable-tunnel-ids {
                        type yang:gauge32;
                        description
                            "The number of tunnel identifiers that is unavailable for the
                             L2TP protocol because they are used by some other application.";
                    }

                } // container statistics

                list oper-group {
                    key "tunnel-group-name";
                    description "Group operationally in use.";

                    leaf tunnel-group-name {
                        type types-sros:named-item-64 {
                            length "1..63";
                        }
                        description "Tunnel group name";
                    }

                    leaf oper-state {
                        type types-l2tp:group-oper-state;
                        description "The operational state of the tunnel group.";
                    }

                    leaf session-limit {
                        type types-l2tp:base-session-limit;
                        description "The administrative session limit of this tunnel group.";
                    }

                    leaf oper-session-limit {
                        type uint32;
                        description "The operational session limit of this tunnel group.";
                    }

                    leaf session-assign-method {
                        type types-l2tp:base-session-assign-method;
                        description
                            "The latest actual method use for the authentication
                             of the tunnels in this tunnel group.";
                    }

                    container statistics {
                        description "Statistics of the operational group";

                        leaf last-cleared {
                            type yang:date-and-time;
                            description "Indicates when the statistics were cleared.";
                        }

                        leaf total-tunnels {
                            type yang:counter32;
                            description
                                "The total number of tunnel set up attempts
                                 in this tunnel group since the last re-initialization
                                 of the local network management subsystem, or the last
                                 time the system statistics were cleared.";
                        }

                        leaf failed-tunnels {
                            type yang:counter32;
                            description
                                "The total number of tunnels in this tunnel group
                                 that failed to reach the established state since the last
                                 re-initialization of the local network management subsystem,
                                 or the last time the system statistics were cleared.";
                        }

                        leaf auth-failed-tunnels {
                            type yang:counter32;
                            description
                                "The total number of tunnels in this tunnel group
                                 that failed authentication since the last re-initialization
                                 of the local network management subsystem, or the last time
                                 the system statistics were cleared.";
                        }

                        leaf active-tunnels {
                            type yang:gauge32;
                            description
                                "The total number of tunnels currently established
                                 in this tunnel group.";
                        }

                        leaf tunnels {
                            type yang:gauge32;
                            description "The actual number of tunnels in this tunnel group.";
                        }

                        leaf total-sessions {
                            type yang:counter32;
                            description
                                "The total number of session creation attempts
                                 in this tunnel group since the last re-initialization
                                 of the local network management subsystem, or the last
                                 time the system statistics were cleared.";
                        }

                        leaf failed-sessions {
                            type yang:counter32;
                            description
                                "The total number of sessions in this tunnel group
                                 that failed to reach the established state since the last
                                 re-initialization of the local network management subsystem,
                                 or the last time the system statistics were cleared.";
                        }

                        leaf active-sessions {
                            type yang:gauge32;
                            description
                                "The total number of sessions currently established
                                 in this tunnel group.";
                        }

                        leaf sessions {
                            type yang:gauge32;
                            description "The actual number of sessions in this tunnel group.";
                        }

                        leaf rx-control-octets {
                            type yang:counter64;
                            units "octets";
                            description
                                "The number of control-channel octets received by the
                                 current tunnels in this tunnel group.";
                        }

                        leaf rx-control-packets {
                            type yang:counter32;
                            units "packets";
                            description
                                "The number of control-channel packets received by the
                                 current tunnels in this tunnel group.";
                        }

                        leaf errored-packets {
                            type yang:gauge32;
                            units "packets";
                            description
                                "The accumulated number of control packets that were
                                 received by the current tunnel endpoints in this tunnel group.";
                        }

                        leaf tx-control-octets {
                            type yang:counter64;
                            units "octets";
                            description
                                "The number of control-channel octets transmitted by the
                                 current tunnels in this tunnel group.";
                        }

                        leaf tx-control-packets {
                            type yang:counter32;
                            units "packets";
                            description
                                "The number of control-channel packets transmitted by the
                                 current tunnels in this tunnel group.";
                        }

                        leaf transmission-errors {
                            type yang:gauge32;
                            units "packets";
                            description
                                "The accumulated number of control packet transmission errors
                                 on the current tunnels in this tunnel group.";
                        }

                    } // container statistics

                } // list oper-group

                list tunnel {
                    key "tunnel-conn-id";
                    description "L2TP tunnel.";

                    leaf tunnel-conn-id {
                        type types-l2tp:connection-id;
                        description "The local connection-id of the control channel of the tunnel.";
                    }

                    leaf oper-state {
                        type types-l2tp:tunnel-oper-state;
                        description "The operational state of the tunnel.";
                    }

                    leaf start-time {
                        type yang:date-and-time;
                        description "The time when this tunnel reached the state wait-reply or wait-connected.";
                    }

                    leaf established-time {
                        type yang:date-and-time;
                        description "The time when this tunnel reached an active state.";
                    }

                    leaf idle-time {
                        type yang:date-and-time;
                        description "The time when this tunnel entered the state idle.";
                    }

                    leaf closed-time {
                        type yang:date-and-time;
                        description "The time when this tunnel entered the state closed or closed-by-peer.";
                    }

                    leaf stop-ccn-result {
                        type types-l2tp:stop-ccn-result;
                        description "The result of a transmitted or received StopCCN message.";
                    }

                    leaf general-error {
                        type types-l2tp:general-error;
                        description "The general error of a transmitted or received StopCCN message.";
                    }

                    leaf error-message {
                        type string {
                            length "1..255";
                        }
                        description "Describes the L2TP error condition in human readable form.";
                    }

                    leaf act-receive-window-size {
                        type uint32;
                        description "The actual receive window size.";
                    }

                    leaf blacklist-state {
                        type types-l2tp:blacklist-state;
                        description "Indicates if this tunnel is deemed reachable or not.";
                    }

                    leaf blacklist-time {
                        type yang:date-and-time;
                        description "The time when this tunnel was placed in the tunnel-selection-blacklist.";
                    }

                    leaf blacklist-remain-time {
                        type uint32;
                        units "seconds";
                        description "Indicates how long the tunnel must still remain in the tunnel-selection-blacklist.";
                    }

                    leaf oper-session-limit {
                        type uint32;
                        description "The operational session limit of this tunnel.";
                    }

                    container connection {
                        description "Connection state of the operational tunnel";

                        leaf rem-conn-id {
                            type types-l2tp:connection-id;
                            description "The remote connection-id of control channel.";
                        }

                        leaf loc-tunnel-id {
                            type types-l2tp:tunnel-id;
                            description "The local tunnel-id.";
                        }

                        leaf rem-tunnel-id {
                            type types-l2tp:tunnel-id;
                            description "The remote tunnel-id.";
                        }

                        leaf transport-type {
                            type types-l2tp:transport-type;
                            description "The transport type used to carry L2TP messages.";
                        }

                        leaf peer {
                            type types-sros:ip-address;
                            description "The peer address";
                        }

                        leaf rem-udp-port {
                            type inet:port-number;
                            description "The remote UDP port of this L2TP tunnel.";
                        }

                        leaf tx-dst-address {
                            type types-sros:ip-address;
                            description
                                "The address used as destination IP address for transmitting
                                 L2TP control messages";
                        }

                        leaf tx-dst-udp-port {
                            type inet:port-number;
                            description "The destination UDP port used while transmitting L2TP control messages.";
                        }

                        leaf rx-src-address {
                            type types-sros:ip-address;
                            description
                                "The address found as source IP address in received L2TP control
                                 messages";
                        }

                        leaf rx-src-udp-port {
                            type inet:port-number;
                            description "The source UDP port found in received L2TP control messages.";
                        }

                        leaf local-address {
                            type types-sros:ip-address;
                            description "The local address";
                        }

                        leaf loc-udp-port {
                            type inet:port-number;
                            description "The local UDP port of this L2TP tunnel.";
                        }

                        leaf local-name {
                            type types-sros:named-item-64;
                            description "The local host name.";
                        }

                        leaf remote-name {
                            type types-sros:named-item-64;
                            description "The remote host name.";
                        }

                    } // container connection

                    container parameters {
                        description "Parameters of the operational tunnel";

                        leaf protocol {
                            type types-l2tp:protocol-version;
                            description "The protocol version being used";
                        }

                        leaf tunnel-group-name {
                            type types-sros:named-item-64;
                            description "The name of the tunnel group to which this tunnel belongs";
                        }

                        leaf assignment-id {
                            type types-sros:named-item {
                                length "1..32";
                            }
                            description "The identifier assigned to this tunnel.";
                        }

                        leaf preference {
                            type uint32;
                            description "The preference of the tunnel.";
                        }

                        leaf hello-interval {
                            type types-l2tp:base-hello-interval;
                            description "The hello interval.";
                        }

                        leaf idle-timeout {
                            type types-l2tp:base-idle-timeout;
                            description "The idle timeout.";
                        }

                        leaf destruct-timeout {
                            type types-l2tp:base-destruct-timeout;
                            description "The destruction timeout.";
                        }

                        leaf max-retries-estab {
                            type types-l2tp:base-max-retries;
                            description "The maximum number of retries when the tunnel is established.";
                        }

                        leaf max-retries-not-estab {
                            type types-l2tp:base-max-retries;
                            description "The maximum number of retries when the tunnel is not established.";
                        }

                        leaf radius-accounting-policy {
                            type types-sros:named-item;
                            description "The RADIUS accounting policy.";
                        }

                        leaf challenge {
                            type boolean;
                            description "Indicates if challenge-response authentication is used or not.";
                        }

                        leaf avp-hiding {
                            type types-l2tp:base-avp-hiding;
                            description "The AVP hiding.";
                        }

                        leaf session-limit {
                            type types-l2tp:base-session-limit;
                            description "The administrative session limit of this L2TP tunnel";
                        }

                        leaf df-bit-lac {
                            type boolean;
                            description "Indicates if the DF (don't fragment) bit is set in data traffic transmitted as LAC.";
                        }

                    } // container parameters

                    container failover {
                        description "Failover state of the operational tunnel";

                        leaf failover-state {
                            type types-l2tp:failover-state;
                            description "The failover state of this tunnel.";
                        }

                        leaf recovery-conn-id {
                            type types-l2tp:connection-id;
                            description "The connection-id of the recovery tunnel.";
                        }

                        leaf recovery-state {
                            type types-l2tp:recovery-state;
                            description "The failover state of a recovery tunnel.";
                        }

                        leaf recovered-conn-id {
                            type types-l2tp:connection-id;
                            description "The connection-id of the recovered tunnel.";
                        }

                        leaf recovery-method {
                            type types-l2tp:base-failover-recovery-method;
                            description "The recovery method.";
                        }

                        leaf track-srrp {
                            type uint32;
                            description "The SRRP instance used for recovery.";
                        }

                        leaf ctrl-msg-behavior {
                            type types-l2tp:control-msg-behavior;
                            description "The behavior of the system with respect to L2TP control traffic.";
                        }

                        leaf requested-recovery-time {
                            type types-l2tp:recovery-time;
                            description "The recovery time requested to the peer system.";
                        }

                        leaf peer-recovery-time {
                            type types-l2tp:recovery-time;
                            description "The recovery time requested by the peer system.";
                        }

                    } // container failover

                    container l2tpv3 {
                        description "L2tpv3 state of the operational tunnel";

                        leaf cookie-length {
                            type types-l2tp:base-v3-cookie-length;
                            description "The cookie length.";
                        }

                        leaf digest-type {
                            type types-l2tp:base-v3-digest-type;
                            description "The digest type";
                        }

                        leaf local-nonce {
                            type types-l2tp:nonce;
                            description "The nonce AVP added to the outgoing control messages.";
                        }

                        leaf remote-nonce {
                            type types-l2tp:nonce;
                            description "The nonce AVP found in incoming control messages.";
                        }

                        leaf rem-router-id {
                            type types-sros:ipv4-address;
                            description "The filter used on remote router ID.";
                        }

                        leaf public-tcp-mss-adjust {
                            type types-l2tp:base-v3-tcp-mss-adjust;
                            description "The TCP maximum segment size (MSS) on public network.";
                        }

                        leaf private-tcp-mss-adjust {
                            type types-l2tp:base-v3-tcp-mss-adjust;
                            description "The TCP maximum segment size (MSS) on private network.";
                        }

                        container pw-cap-list {
                            description "The Pseudo Wire capture list";

                            leaf ethernet {
                                type boolean;
                                description "Ethernet pseudo-wire encapsulation is accepted";
                            }

                            leaf ethernet-vlan {
                                type boolean;
                                description "Ethernet VLAN pseudo-wire encapsulation is accepted";
                            }

                        } // container pw-cap-list

                    } // container l2tpv3

                    container statistics {
                        description "Statistics of the operational tunnel";

                        leaf last-cleared {
                            type yang:date-and-time;
                            description "The time when the statistics were cleared.";
                        }

                        leaf total-sessions {
                            type yang:counter32;
                            description
                                "The total number of session creation attempts
                                 in this tunnel since the last re-initialization
                                 of the local network management subsystem, or the last
                                 time the system statistics were cleared.";
                        }

                        leaf failed-sessions {
                            type yang:counter32;
                            description
                                "The total number of sessions in this tunnel
                                 that failed to reach the established state since the last
                                 re-initialization of the local network management subsystem,
                                 or the last time the system statistics were cleared.";
                        }

                        leaf active-sessions {
                            type yang:gauge32;
                            description
                                "The total number of sessions currently established
                                 in this tunnel.";
                        }

                        leaf sessions {
                            type yang:gauge32;
                            description "The actual number of sessions in this tunnel.";
                        }

                        leaf rx-control-octets {
                            type yang:counter64;
                            units "octets";
                            description
                                "The number of control-channel octets received by the
                                 tunnel.";
                        }

                        leaf rx-control-packets {
                            type yang:counter32;
                            units "packets";
                            description
                                "The number of control-channel packets received by the
                                 tunnel.";
                        }

                        leaf errored-packets {
                            type yang:gauge32;
                            units "packets";
                            description
                                "The accumulated number of control packets that were
                                 received by the current tunnel endpoints in this tunnel group.";
                        }

                        leaf tx-control-octets {
                            type yang:counter64;
                            units "octets";
                            description
                                "The number of control-channel octets transmitted by the
                                 tunnel.";
                        }

                        leaf tx-control-packets {
                            type yang:counter32;
                            units "packets";
                            description
                                "The number of control-channel packets transmitted by the
                                 tunnel.";
                        }

                        leaf transmission-errors {
                            type yang:gauge32;
                            units "packets";
                            description
                                "The accumulated number of control packet transmission errors
                                 for the tunnel.";
                        }

                        leaf fsm-msg-accepted {
                            type yang:counter32;
                            units "packets";
                            description
                                "The number of Finite State Machine (FSM) messages that were
                                 accepted on this tunnel since the last re-initialization of the local
                                 network management subsystem, or the last time the tunnel statistics were
                                 cleared.";
                        }

                        leaf fsm-msg-duplicates {
                            type yang:counter32;
                            units "packets";
                            description
                                "The number of duplicate Finite State Machine (FSM) messages that
                                 were received on this tunnel since the last re-initialization of the local
                                 network management subsystem, or the last time the tunnel statistics were
                                 cleared.";
                        }

                        leaf fsm-msg-out-of-rx-window {
                            type yang:counter32;
                            units "packets";
                            description
                                "The number of Finite State Machine (FSM) messages that were received
                                 out of the receive window on this tunnel since the last re-initialization of
                                 the local network management subsystem, or the last time the tunnel statistics
                                 were cleared.";
                        }

                        leaf max-unsent-queue-length {
                            type yang:gauge32;
                            units "packets";
                            description
                                "The maximum length of the unsent message queue on this tunnel since the last
                                 re-initialization of the local network management subsystem, or the last time
                                 the tunnel statistics were cleared.";
                        }

                        leaf cur-unsent-queue-length {
                            type yang:gauge32;
                            units "packets";
                            description "The current length of the unsent message queue on this tunnel.";
                        }

                        leaf max-ack-queue-length {
                            type yang:gauge32;
                            units "packets";
                            description
                                "The maximum length of the to-be-acknowledged message queue on this tunnel since
                                 the last re-initialization of the local network management subsystem, or the
                                 last time the tunnel statistics were cleared.";
                        }

                        leaf cur-ack-queue-length {
                            type yang:gauge32;
                            units "packets";
                            description "The current length of the to-be-acknowledged  message queue on this tunnel.";
                        }

                        leaf cur-window-size {
                            type yang:gauge32;
                            description "The current size of the receive window on this tunnel.";
                        }

                        list protocol {
                            key "type id";
                            description "Protocol statistics of the operational tunnel";

                            leaf type {
                                type types-l2tp:proto-stats-type;
                                description "The statistics type.";
                            }

                            leaf id {
                                type uint32 {
                                    range "0..69|4294967294|4294967295";
                                }
                                description "The counter id.";
                            }

                            leaf name {
                                type types-sros:display-string;
                                description "The human-readable identifier of the statistic.";
                            }

                            leaf value {
                                type yang:counter32;
                                description "The counter value";
                            }

                        } // list protocol

                    } // container statistics

                } // list tunnel

                list session {
                    key "session-conn-id";
                    description "L2TP session";

                    leaf session-conn-id {
                        type types-l2tp:connection-id;
                        description "The local connection-id of the session.";
                    }

                    leaf oper-state {
                        type types-l2tp:session-oper-state;
                        description "The operational state of the session.";
                    }

                    leaf start-time {
                        type yang:date-and-time;
                        description "The time when this session reached the state idle, wait-tunnel, wait-reply or wait-acceptance.";
                    }

                    leaf established-time {
                        type yang:date-and-time;
                        description "The time when this session entered the state established.";
                    }

                    leaf closed-time {
                        type yang:date-and-time;
                        description "The time when this session entered the state closed or closed-by-peer.";
                    }

                    leaf cdn-result {
                        type types-l2tp:cdn-result;
                        description "The result of a transmitted or received CDN message.";
                    }

                    leaf general-error {
                        type types-l2tp:general-error;
                        description "The general error of a transmitted or received CDN message.";
                    }

                    leaf error-message {
                        type string {
                            length "0..255";
                        }
                        description "Describes an L2TP error condition in human readable form.";
                    }

                    leaf mlppp-bundle {
                        type types-l2tp:mlppp-bundle-index;
                        description "The index of the MLPPP bundle to which this session belongs.";
                    }

                    leaf pw-type {
                        type types-l2tp:pseudo-wire-type;
                        description "The pseudo-wire type of the session.";
                    }

                    container connection {
                        description "Connection state of the session.";

                        leaf loc-tunnel-id {
                            type types-l2tp:tunnel-id;
                            description "The local tunnel-id.";
                        }

                        leaf rem-tunnel-id {
                            type types-l2tp:tunnel-id;
                            description "The remote tunnel-id.";
                        }

                        leaf loc-session-id {
                            type types-l2tp:session-id;
                            description "The local session-id.";
                        }

                        leaf rem-session-id {
                            type types-l2tp:session-id;
                            description "The remote session-id.";
                        }

                        leaf rem-connection-id {
                            type types-l2tp:connection-id;
                            description "The remote connection-id of the session.";
                        }

                        leaf control-connection-id {
                            type types-l2tp:connection-id;
                            description "The local connection-id of the control connection of the tunnel.";
                        }

                    } // container connection

                    container l2tpv3 {
                        description "L2TPv3 state of the session.";

                        leaf rx-cookie {
                            type binary {
                                length "1..8";
                            }
                            description "The cookie found in received data packets.";
                        }

                        leaf tx-cookie {
                            type binary {
                                length "1..8";
                            }
                            description "The cookie used in transmitted data packets.";
                        }

                        leaf endpoint-id {
                            type binary {
                                length "1..250";
                            }
                            description "The endpoint identification of the session.";
                        }

                        leaf endpoint-description {
                            type types-sros:display-string-or-empty {
                                length "0..80";
                            }
                            description "The endpoint description of the session.";
                        }

                        leaf seq-num-in-rx {
                            type types-l2tp:seq-num-present-in-packet-type;
                            description "Indicates in which received packets sequence numbers are present.";
                        }

                        leaf seq-num-in-tx {
                            type types-l2tp:seq-num-present-in-packet-type;
                            description "Indicates in which received packets sequence numbers are present.";
                        }

                        leaf l2-sub-layer-in-rx {
                            type boolean;
                            description "Indicates if the l2 sub-layer is present in received packets.";
                        }

                        leaf l2-sub-layer-in-tx {
                            type boolean;
                            description "Indicates if the l2 sub-layer is present in transmitted packets.";
                        }

                    } // container l2tpv3

                    container statistics {
                        description "Session statistics";

                        container ethernet-tunnel {
                            description "Ethernet tunnel statistics";

                            leaf rx-packets {
                                type yang:counter64;
                                units "packets";
                                description "The the number of packets received.";
                            }

                            leaf rx-octets {
                                type yang:counter64;
                                units "octets";
                                description "The number of octets received.";
                            }

                            leaf rx-errors {
                                type yang:counter64;
                                units "packets";
                                description "The number of packets dropped while receiving.";
                            }

                            leaf rx-cookie-mismatch {
                                type yang:counter64;
                                units "packets";
                                description
                                    "The number of packets dropped because the received cookie value
                                     did not match the cookie value negotiated during session establishment.";
                            }

                            leaf rx-session-id-mismatch {
                                type yang:counter64;
                                units "packets";
                                description
                                    "The number of packets dropped because the received session-id
                                     did not match the session-id negotiated during session establishment.";
                            }

                            leaf tx-packets {
                                type yang:counter64;
                                units "packets";
                                description "The number of packets transmitted.";
                            }

                            leaf tx-octets {
                                type yang:counter64;
                                units "octets";
                                description "The number of octets transmitted.";
                            }

                            leaf tx-errors {
                                type yang:counter64;
                                units "packets";
                                description "The number of packets dropped while transmitting.";
                            }

                        } // container ethernet-tunnel

                    } // container statistics

                } // list session

                list oper-ethernet-tunnel {
                    key "tunnel-group-name vc-id";
                    description "An ethernet tunnel";

                    leaf tunnel-group-name {
                        type types-sros:named-item-64 {
                            length "1..63";
                        }
                        description "The name of the tunnel group to which this ethernet tunnel belongs";
                    }

                    leaf vc-id {
                        type types-services:vc-id;
                        description "The virtual circuit identifier of the ethernet tunnel";
                    }

                    leaf loc-conn-id {
                        type types-l2tp:connection-id;
                        description "The local connection-id of the ethernet tunnel.";
                    }

                    leaf down-reason {
                        type string {
                            length "0..80";
                        }
                        description "The reason for the ethernet tunnel not being established.";
                    }

                    leaf reconnect-timeout {
                        type types-l2tp:base-v3-reconnect-timeout;
                        description "The reconnect timeout for an ethernet tunnel.";
                    }

                    leaf remaining-time {
                        type uint32;
                        units "seconds";
                        description "The remaining time before a reconnection attempt is made.";
                    }

                    leaf sap-id {
                        type types-sros:sap;
                        description "The SAP-id.";
                    }

                    leaf sap-service-name {
                        type types-sros:named-item-64;
                        description "The service of the SAP.";
                    }

                    leaf control-conn-id {
                        type types-l2tp:connection-id;
                        description "The control connection-id of the L2TP tunnel controling the ethernet tunnel.";
                    }

                    leaf matches-config {
                        type boolean;
                        description
                            "Indicates if the operational settings of the ethernet tunnel match the tunnel
                             group configuration.";
                    }

                } // list oper-ethernet-tunnel

                list udp-peer {
                    key "ip-address udp-port";
                    description "An UDP peer";

                    leaf ip-address {
                        type types-sros:ip-address;
                        description "The peer address";
                    }

                    leaf udp-port {
                        type inet:port-number;
                        description "The UDP port.";
                    }

                    leaf draining {
                        type boolean;
                        description "Indicates if this peer is being drained.";
                    }

                    leaf reachability {
                        type types-l2tp:peer-reachability;
                        description "Indicates if this peer is deemed reachable or not.";
                    }

                    leaf unreachable-time {
                        type yang:date-and-time;
                        description "The time when this peer was deemed unreachable for the last time.";
                    }

                    leaf remaining-time {
                        type uint32;
                        units "seconds";
                        description "The remaining time that the peer will remain in the selection-blacklist.";
                    }

                    leaf roles-capability {
                        type types-l2tp:peer-roles;
                        description "The roles the peer can take.";
                    }

                    leaf actual-roles {
                        type types-l2tp:peer-roles;
                        description "The roles the peer currently has.";
                    }

                    container statistics {
                        description "Statistics of the peer.";

                        leaf tunnels {
                            type yang:gauge32;
                            description "The actual number of tunnels associated with this peer.";
                        }

                        leaf active-tunnels {
                            type yang:gauge32;
                            description "The actual number of tunnels associated with this peer that are currently established.";
                        }

                        leaf sessions {
                            type yang:gauge32;
                            description "The actual number of sessions associated with this peer.";
                        }

                        leaf active-sessions {
                            type yang:gauge32;
                            description "The actual number of sessions associated with this peer that are currently established.";
                        }

                        leaf rx-control-octets {
                            type yang:counter64;
                            units "octets";
                            description
                                "The number of control channel octets received from this peer since the last re-initialization
                                 of the local network management subsystem, or the last time the tunnel statistics were cleared.";
                        }

                        leaf rx-control-packets {
                            type yang:counter32;
                            units "packets";
                            description
                                "The number of control channel packets received from this peer since the last re-initialization
                                 of the local network management subsystem, or the last time the tunnel statistics were cleared.";
                        }

                        leaf errored-packets {
                            type yang:counter32;
                            units "packets";
                            description
                                "The number of errored packets received from this peer since the last re-initialization
                                 of the local network management subsystem, or the last time the tunnel statistics were cleared.";
                        }

                        leaf tx-control-octets {
                            type yang:counter64;
                            units "octets";
                            description
                                "The number of control channel octets transmitted to this peer since the last re-initialization
                                 of the local network management subsystem, or the last time the tunnel statistics were cleared.";
                        }

                        leaf tx-control-packets {
                            type yang:counter32;
                            units "packets";
                            description
                                "The number of control channel packets transmitted to this peer since the last re-initialization
                                 of the local network management subsystem, or the last time the tunnel statistics were cleared.";
                        }

                        leaf transmission-errors {
                            type yang:counter32;
                            units "packets";
                            description
                                "The number of packets transmission error for this peer since the last re-initialization
                                 of the local network management subsystem, or the last time the tunnel statistics were cleared.";
                        }

                        leaf fsm-msg-accepted {
                            type yang:counter32;
                            units "packets";
                            description
                                "The number of Finite State Machine messages from this peer accepted since the last re-initialization
                                 of the local network management subsystem, or the last time the tunnel statistics were cleared.";
                        }

                        leaf fsm-msg-duplicates {
                            type yang:counter32;
                            units "packets";
                            description
                                "The number of duplicate Finite State Machine messages from this peer received since the last re-initialization
                                 of the local network management subsystem, or the last time the tunnel statistics were cleared.";
                        }

                        leaf fsm-msg-out-of-rx-window {
                            type yang:counter32;
                            units "packets";
                            description
                                "The number of Finite State Machine (FSM) messages that were received
                                 out of the receive window from this peer since the last re-initialization of
                                 the local network management subsystem, or the last time the tunnel statistics
                                 were cleared.";
                        }

                        leaf last-cleared {
                            type yang:date-and-time;
                            description "The time when the statistics were cleared for the last time.";
                        }

                        list protocol {
                            key "type id";
                            description "Protocol statistics of the peer";

                            leaf type {
                                type types-l2tp:proto-stats-type;
                                description "The statistics type.";
                            }

                            leaf id {
                                type uint32 {
                                    range "0..69|4294967294|4294967295";
                                }
                                description "The counter id.";
                            }

                            leaf name {
                                type types-sros:display-string;
                                description "The human-readable identifier of the statistic.";
                            }

                            leaf value {
                                type yang:counter32;
                                description "The counter value";
                            }

                        } // list protocol

                    } // container statistics

                } // list udp-peer

                list ip-peer {
                    key "ip-address";
                    description "IP peer";

                    leaf ip-address {
                        type types-sros:ip-address;
                        description "The peer address";
                    }

                    leaf draining {
                        type boolean;
                        description "Indicates if this peer is being drained.";
                    }

                    leaf reachability {
                        type types-l2tp:peer-reachability;
                        description "Indicates if this peer is deemed reachable or not.";
                    }

                    leaf unreachable-time {
                        type yang:date-and-time;
                        description "The time when this peer was deemed unreachable for the last time.";
                    }

                    leaf remaining-time {
                        type uint32;
                        units "seconds";
                        description "The remaining time that the peer will remain in the selection-blacklist.";
                    }

                    leaf roles-capability {
                        type types-l2tp:peer-roles;
                        description "The roles the peer can take.";
                    }

                    leaf actual-roles {
                        type types-l2tp:peer-roles;
                        description "The roles the peer currently has.";
                    }

                    container statistics {
                        description "Statistics of the peer.";

                        leaf tunnels {
                            type yang:gauge32;
                            description "The actual number of tunnels associated with this peer.";
                        }

                        leaf active-tunnels {
                            type yang:gauge32;
                            description "The actual number of tunnels associated with this peer that are currently established.";
                        }

                        leaf sessions {
                            type yang:gauge32;
                            description "The actual number of sessions associated with this peer.";
                        }

                        leaf active-sessions {
                            type yang:gauge32;
                            description "The actual number of sessions associated with this peer that are currently established.";
                        }

                        leaf rx-control-octets {
                            type yang:counter64;
                            units "octets";
                            description
                                "The number of control channel octets received from this peer since the last re-initialization
                                 of the local network management subsystem, or the last time the tunnel statistics were cleared.";
                        }

                        leaf rx-control-packets {
                            type yang:counter32;
                            units "packets";
                            description
                                "The number of control channel packets received from this peer since the last re-initialization
                                 of the local network management subsystem, or the last time the tunnel statistics were cleared.";
                        }

                        leaf errored-packets {
                            type yang:counter32;
                            units "packets";
                            description
                                "The number of errored packets received from this peer since the last re-initialization
                                 of the local network management subsystem, or the last time the tunnel statistics were cleared.";
                        }

                        leaf tx-control-octets {
                            type yang:counter64;
                            units "octets";
                            description
                                "The number of control channel octets transmitted to this peer since the last re-initialization
                                 of the local network management subsystem, or the last time the tunnel statistics were cleared.";
                        }

                        leaf tx-control-packets {
                            type yang:counter32;
                            units "packets";
                            description
                                "The number of control channel packets transmitted to this peer since the last re-initialization
                                 of the local network management subsystem, or the last time the tunnel statistics were cleared.";
                        }

                        leaf transmission-errors {
                            type yang:counter32;
                            units "packets";
                            description
                                "The number of packets transmission error for this peer since the last re-initialization
                                 of the local network management subsystem, or the last time the tunnel statistics were cleared.";
                        }

                        leaf fsm-msg-accepted {
                            type yang:counter32;
                            units "packets";
                            description
                                "The number of Finite State Machine messages from this peer accepted since the last re-initialization
                                 of the local network management subsystem, or the last time the tunnel statistics were cleared.";
                        }

                        leaf fsm-msg-duplicates {
                            type yang:counter32;
                            units "packets";
                            description
                                "The number of duplicate Finite State Machine messages from this peer received since the last re-initialization
                                 of the local network management subsystem, or the last time the tunnel statistics were cleared.";
                        }

                        leaf fsm-msg-out-of-rx-window {
                            type yang:counter32;
                            units "packets";
                            description
                                "The number of Finite State Machine (FSM) messages that were received
                                 out of the receive window from this peer since the last re-initialization of
                                 the local network management subsystem, or the last time the tunnel statistics
                                 were cleared.";
                        }

                        leaf last-cleared {
                            type yang:date-and-time;
                            description "The time when the statistics were cleared for the last time.";
                        }

                        list protocol {
                            key "type id";
                            description "Protocol statistics of the peer";

                            leaf type {
                                type types-l2tp:proto-stats-type;
                                description "The statistics type.";
                            }

                            leaf id {
                                type uint32 {
                                    range "0..69|4294967294|4294967295";
                                }
                                description "The counter id.";
                            }

                            leaf name {
                                type types-sros:display-string;
                                description "The human-readable identifier of the statistic.";
                            }

                            leaf value {
                                type yang:counter32;
                                description "The counter value";
                            }

                        } // list protocol

                    } // container statistics

                } // list ip-peer

                list vas-tunnel {
                    key "tunnel-conn-id";
                    description "VAS tunnel";

                    leaf tunnel-conn-id {
                        type types-l2tp:connection-id;
                        description "The connection-id of the VAS tunnel.";
                    }

                    leaf transport-type {
                        type types-l2tp:transport-type;
                        description "The transport type used to carry L2TP messages.";
                    }

                    leaf local-address {
                        type types-sros:ip-address;
                        description "The local address";
                    }

                    leaf loc-udp-port {
                        type inet:port-number;
                        description "The local UDP port of this VAS tunnel.";
                    }

                    leaf remote-address {
                        type types-sros:ip-address;
                        description "The remote address";
                    }

                    leaf rem-udp-port {
                        type inet:port-number;
                        description "The remote UDP port of this VAS tunnel.";
                    }

                    leaf base-router {
                        type types-sros:router-instance;
                        description "The virtual router instance used as the base of the VAS tunnel.";
                    }

                    leaf loc-tunnel-id {
                        type types-l2tp:tunnel-id;
                        description "The local tunnel-id.";
                    }

                    leaf rem-tunnel-id {
                        type types-l2tp:tunnel-id;
                        description "The remote tunnel-id.";
                    }

                    leaf rem-conn-id {
                        type types-l2tp:connection-id;
                        description "The remote connection-id of the VAS tunnel.";
                    }

                    list vas-session {
                        key "session-conn-id";
                        description "VAS session";

                        leaf session-conn-id {
                            type types-l2tp:connection-id;
                            description "The connection-id of the VAS session.";
                        }

                        leaf loc-session-id {
                            type types-l2tp:session-id;
                            description "The local session-id.";
                        }

                        leaf rem-session-id {
                            type types-l2tp:session-id;
                            description "The remote session-id.";
                        }

                        leaf rem-conn-id {
                            type types-l2tp:connection-id;
                            description "The remote connection-id of the VAS session.";
                        }

                    } // list vas-session

                } // list vas-tunnel

                list mlppp-bundle {
                    key "bundle-index";
                    description "MLPPP bundle";

                    leaf bundle-index {
                        type uint32;
                        description "The bundle index";
                    }

                    leaf service-name {
                        type types-sros:named-item-64;
                        description "The service to which this MLPPP bundle belongs.";
                    }

                    leaf forwarding-tunnel-id {
                        type types-l2tp:tunnel-id;
                        description
                            "The id of the LTS (L2TP Tunnel Stitching) tunnel if this bundle
                             is associated with PPP sessions that are stiched to another L2TP tunnel.";
                    }

                    leaf user-name {
                        type types-sros:named-item;
                        description
                            "The user name of the subscriber associated with this MLPPP bundle or another
                             string used to identify that subscriber.";
                    }

                    container local-endpoint {
                        description "The local endpoint identifier.";

                        leaf endpoint-class {
                            type types-ppp:mlppp-endpoint-class;
                            description "Endpoint class";
                        }

                        leaf endpoint-id {
                            type binary {
                                length "1..20";
                            }
                            description "Endpoint identifier";
                        }

                        leaf description {
                            type types-sros:description;
                            description "The endpoint description.";
                        }

                    } // container local-endpoint

                    container remote-endpoint {
                        description "The remote endpoint identifier.";

                        leaf endpoint-class {
                            type types-ppp:mlppp-endpoint-class;
                            description "Endpoint class";
                        }

                        leaf endpoint-id {
                            type binary {
                                length "1..20";
                            }
                            description "Endpoint identifier";
                        }

                        leaf description {
                            type types-sros:description;
                            description "The endpoint description.";
                        }

                    } // container remote-endpoint

                    list link {
                        key "session-conn-id";
                        description "Link of the MLPPP bundle";

                        leaf session-conn-id {
                            type types-l2tp:connection-id;
                            description "The local connection-id of the session.";
                        }

                        leaf oper-state {
                            type types-l2tp:session-oper-state;
                            description "The operational state of the session.";
                        }

                    } // list link

                } // list mlppp-bundle

            } // container l2tp

            container igmp {
                description "Enter the igmp context";

                leaf oper-state {
                    type types-sros:oper-state;
                    description "The current operating state of this IGMP protocol instance on this router.";
                }

                list interface {
                    key "ip-interface-name";
                    description "Enter the interface list instance";

                    leaf ip-interface-name {
                        type types-sros:interface-name;
                        description "Interface name.";
                    }

                    leaf oper-state {
                        type types-sros:oper-state;
                        description "The current operating state of the IGMP protocol on this interface.";
                    }

                    leaf oper-version {
                        type types-igmp:igmp-version;
                        description "The operational version of the IGMP which is running on this interface.";
                    }

                    leaf group-count {
                        type int32;
                        description "The number of multicast groups which have been learned on this interface.";
                    }

                    leaf next-general-query-time {
                        type uint32;
                        units "seconds";
                        description
                            "The time remaining before the general query is sent on this interface
                             if this router is the querier.";
                    }

                    leaf maximum-groups-until-now {
                        type uint32;
                        description "The highest value that 'group-count' had till now.";
                    }

                    leaf querier {
                        type types-sros:ipv4-address;
                        description "The address of the IGMP Querier on the IP subnet to which this interface is attached.";
                    }

                    leaf querier-up-time {
                        type uint32;
                        units "seconds";
                        description "The time since 'querier' was last elected as querier.";
                    }

                    leaf querier-expiry-time {
                        type uint32;
                        units "seconds";
                        description "The time remaining before querier is aged out.";
                    }

                    leaf redundant-multicast-forwarder {
                        type boolean;
                        description
                            "This interface is the forwarding interface
                             of a pair of redundant multicast interfaces.";
                    }

                    container mcac {
                        description "Enter the mcac context";

                        leaf in-use-mandatory-bandwidth {
                            type uint32;
                            units "kilobps";
                            description
                                "The in-use bandwidth for the mandatory channels for this
                                 protocol interface instance.";
                        }

                        leaf in-use-optional-bandwidth {
                            type uint32;
                            units "kilobps";
                            description
                                "The in-use bandwidth for the optional channels for this
                                 protocol interface instance.";
                        }

                        leaf available-mandatory-bandwidth {
                            type uint32;
                            units "kilobps";
                            description
                                "The pre-reserved bandwidth for the mandatory channels for
                                 this interface instance.";
                        }

                        leaf available-optional-bandwidth {
                            type uint32;
                            units "kilobps";
                            description "The available bandwidth for this interface instance.";
                        }

                        leaf values-in-transit {
                            type boolean;
                            description
                                "The operational (available and in-use mandatory/optional) value for the
                                 following objects is in transition due to configuration change:
                                 - available-mandatory-bandwidth
                                 - available-bandwidth
                                 - in-use-mandatory-bandwidth
                                 - in-use-optional-bandwidth.";
                        }

                    } // container mcac

                    container static {
                        description "Enter the static context";

                        list group-range {
                            key "start end step";
                            description "Enter the group-range list instance";

                            leaf start {
                                type types-sros:ipv4-multicast-address;
                                description "IP address for the start of the static group range";
                            }

                            leaf end {
                                type types-sros:ipv4-multicast-address;
                                description "IP address for the end of the static group range";
                            }

                            leaf step {
                                type types-sros:ipv4-address;
                                description "Step interval in the group-range address";
                            }

                            leaf group-count {
                                type uint32;
                                description "The number of groups in the group-range.";
                            }

                        } // list group-range

                    } // container static

                    container statistics {

                        container received {
                            description "Received message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                        } // container received

                        container transmitted {
                            description "Transmit message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                            leaf errors {
                                type yang:counter32;
                                description "Transmission Errors.";
                            }

                        } // container transmitted

                        container error {
                            description "Error message statistics.";

                            leaf bad-length {
                                type yang:counter32;
                                description "Bad length.";
                            }

                            leaf bad-ip-checksum {
                                type yang:counter32;
                                description "Bad Ip checksum.";
                            }

                            leaf unknown-type {
                                type yang:counter32;
                                description "Unknown type.";
                            }

                            leaf wrong-version {
                                type yang:counter32;
                                description "Wrong version.";
                            }

                            leaf import-policy-drops {
                                type yang:counter32;
                                description
                                    "Number of times we matched the host IP address or group or
                                     source addresses specified in the import policy.";
                            }

                            leaf missing-router-alert {
                                type yang:counter32;
                                description "Router alert flag is not set.";
                            }

                            leaf bad-encoding {
                                type yang:counter32;
                                description "Badly encoded.";
                            }

                            leaf local-scope {
                                type yang:counter32;
                                description "Link-local scope multicast group address.";
                            }

                            leaf mcac-policy-drops {
                                type yang:counter32;
                                description
                                    "Number of times a join is dropped because of applying a
                                     multicast CAC policy.";
                            }

                            leaf reached-maximum-number-groups {
                                type yang:counter32;
                                description
                                    "Number of times a join is dropped because we reached the maximum
                                     number of groups.";
                            }

                            leaf reached-maximum-number-group-sources {
                                type yang:counter32;
                                description
                                    "Number of times a join is dropped because we reached the maximum
                                     number group-source combinations.";
                            }

                            leaf reached-maximum-number-sources {
                                type yang:counter32;
                                description
                                    "Number of times a join is dropped because we reached the maximum
                                     number of sources per group.";
                            }

                            leaf out-of-memory-drops {
                                type yang:counter32;
                                description "Number of times a join is dropped because we ran out of memory.";
                            }

                            leaf mcs-failures {
                                type yang:counter32;
                                description "Number of times a group could not be synced through multi chassis synchronisation (MCS).";
                            }

                            leaf non-local {
                                type yang:counter32;
                                description "Non-local sender source IP address.";
                            }

                        } // container error

                    } // container statistics

                    list group {
                        key "group-address";
                        description "Multicast group membership information that joined on the interface.";

                        leaf group-address {
                            type types-sros:ipv4-multicast-address;
                            description "Group address of static IGMP multicast channel";
                        }

                        leaf group-type {
                            type types-igmp:learn-type;
                        }

                        leaf filter-mode {
                            type types-igmp:filter-mode;
                        }

                        leaf expiry-time {
                            type uint32;
                            units "seconds";
                            description "The time left before multicast group timeout.";
                        }

                        leaf up-time {
                            type uint32;
                            units "seconds";
                            description "The time elapsed since this entry was created.";
                        }

                        leaf v1-host-timer {
                            type uint32;
                            units "seconds";
                            description
                                "The time remaining until the local router will assume that
                                 there are no longer any version 1 members.";
                        }

                        leaf v2-host-timer {
                            type uint32;
                            units "seconds";
                            description
                                "The time remaining until the local router will assume that
                                 there are no longer any version 2 members.";
                        }

                        leaf igmp-compatibility-mode {
                            type types-igmp:igmp-version;
                            description "Compatibility with older version routers.";
                        }

                        leaf last-reporter {
                            type types-sros:ip-address;
                            description
                                "The last host address which has sent the report to join
                                 the multicast group.";
                        }

                        list source {
                            key "source-address";
                            description "List of multicast source information of the multicast group.";

                            leaf source-address {
                                type types-sros:ipv4-address;
                                description "Source address of multicast channel.";
                            }

                            leaf source-type {
                                type types-igmp:learn-type;
                            }

                            leaf forwarding-state {
                                type types-igmp:forwarding-state;
                                description "Traffic forwardeding state on this port.";
                            }

                            leaf expiry-time {
                                type uint32;
                                units "seconds";
                                description "The time left before multicast group timeout.";
                            }

                            leaf up-time {
                                type uint32;
                                units "seconds";
                                description "The time elapsed since this entry was created.";
                            }

                        } // list source

                    } // list group

                } // list interface

                list group-interface {
                    key "group-interface-name";
                    description "Enter the group-interface list instance";

                    leaf group-interface-name {
                        type leafref {
                            path "../../../subscriber-interface/group-interface/group-interface-name";
                        }
                        description "Group interface name";
                    }

                    leaf oper-state {
                        type types-sros:oper-state;
                        description "The current operating state of the IGMP protocol on this group interface.";
                    }

                    container mcac {
                        description "Enter the mcac context";

                        leaf in-use-mandatory-bandwidth {
                            type uint32;
                            units "kilobps";
                            description
                                "The in-use bandwidth for the mandatory channels for this
                                 protocol interface instance.";
                        }

                        leaf in-use-optional-bandwidth {
                            type uint32;
                            units "kilobps";
                            description
                                "The in-use bandwidth for the optional channels for this
                                 protocol interface instance.";
                        }

                        leaf available-mandatory-bandwidth {
                            type uint32;
                            units "kilobps";
                            description
                                "The pre-reserved bandwidth for the mandatory channels for
                                 this interface instance.";
                        }

                        leaf available-optional-bandwidth {
                            type uint32;
                            units "kilobps";
                            description "The available bandwidth for this interface instance.";
                        }

                        leaf values-in-transit {
                            type boolean;
                            description
                                "The operational (available and in-use mandatory/optional) value for the
                                 following objects is in transition due to configuration change:
                                 - available-mandatory-bandwidth
                                 - available-bandwidth
                                 - in-use-mandatory-bandwidth
                                 - in-use-optional-bandwidth.";
                        }

                    } // container mcac

                    list sap {
                        key "sap-id";
                        description "List of saps.";

                        leaf sap-id {
                            type types-sros:sap;
                            description "SAP identifier.";
                        }

                        leaf oper-state {
                            type types-sros:oper-state;
                            description "The current operating state of the IGMP protocol on this interface.";
                        }

                        leaf oper-version {
                            type types-igmp:igmp-version;
                            description "The operational version of the IGMP which is running on this interface.";
                        }

                        leaf group-count {
                            type int32;
                            description "The number of multicast groups which have been learned on this interface.";
                        }

                        leaf next-general-query-time {
                            type uint32;
                            units "seconds";
                            description
                                "The time remaining before the general query is sent on this interface
                                 if this router is the querier.";
                        }

                        leaf maximum-groups-until-now {
                            type uint32;
                            description "The highest value that 'group-count' had till now.";
                        }

                        container statistics {

                            container received {
                                description "Received message statistics.";

                                leaf general-queries {
                                    type yang:counter32;
                                    description "General Queries.";
                                }

                                leaf group-queries {
                                    type yang:counter32;
                                    description "Group Specific Queries.";
                                }

                                leaf group-source-queries {
                                    type yang:counter32;
                                    description "Group and Source Specific Queries.";
                                }

                                leaf v1-reports {
                                    type yang:counter32;
                                    description "V1 Reports.";
                                }

                                leaf v2-reports {
                                    type yang:counter32;
                                    description "V2 Reports.";
                                }

                                leaf v3-reports {
                                    type yang:counter32;
                                    description "V3 Reports.";
                                }

                                leaf leaves {
                                    type yang:counter32;
                                    description "Leaves.";
                                }

                                leaf drops {
                                    type yang:counter32;
                                    description "Total number of dropped packets.";
                                }

                            } // container received

                            container transmitted {
                                description "Transmit message statistics.";

                                leaf general-queries {
                                    type yang:counter32;
                                    description "General Queries.";
                                }

                                leaf group-queries {
                                    type yang:counter32;
                                    description "Group Specific Queries.";
                                }

                                leaf group-source-queries {
                                    type yang:counter32;
                                    description "Group and Source Specific Queries.";
                                }

                                leaf v1-reports {
                                    type yang:counter32;
                                    description "V1 Reports.";
                                }

                                leaf v2-reports {
                                    type yang:counter32;
                                    description "V2 Reports.";
                                }

                                leaf v3-reports {
                                    type yang:counter32;
                                    description "V3 Reports.";
                                }

                                leaf leaves {
                                    type yang:counter32;
                                    description "Leaves.";
                                }

                                leaf drops {
                                    type yang:counter32;
                                    description "Total number of dropped packets.";
                                }

                                leaf errors {
                                    type yang:counter32;
                                    description "Transmission Errors.";
                                }

                            } // container transmitted

                            container error {
                                description "Error message statistics.";

                                leaf bad-length {
                                    type yang:counter32;
                                    description "Bad length.";
                                }

                                leaf bad-ip-checksum {
                                    type yang:counter32;
                                    description "Bad Ip checksum.";
                                }

                                leaf unknown-type {
                                    type yang:counter32;
                                    description "Unknown type.";
                                }

                                leaf wrong-version {
                                    type yang:counter32;
                                    description "Wrong version.";
                                }

                                leaf import-policy-drops {
                                    type yang:counter32;
                                    description
                                        "Number of times we matched the host IP address or group or
                                         source addresses specified in the import policy.";
                                }

                                leaf missing-router-alert {
                                    type yang:counter32;
                                    description "Router alert flag is not set.";
                                }

                                leaf bad-encoding {
                                    type yang:counter32;
                                    description "Badly encoded.";
                                }

                                leaf local-scope {
                                    type yang:counter32;
                                    description "Link-local scope multicast group address.";
                                }

                                leaf mcac-policy-drops {
                                    type yang:counter32;
                                    description
                                        "Number of times a join is dropped because of applying a
                                         multicast CAC policy.";
                                }

                                leaf reached-maximum-number-groups {
                                    type yang:counter32;
                                    description
                                        "Number of times a join is dropped because we reached the maximum
                                         number of groups.";
                                }

                                leaf reached-maximum-number-group-sources {
                                    type yang:counter32;
                                    description
                                        "Number of times a join is dropped because we reached the maximum
                                         number group-source combinations.";
                                }

                                leaf reached-maximum-number-sources {
                                    type yang:counter32;
                                    description
                                        "Number of times a join is dropped because we reached the maximum
                                         number of sources per group.";
                                }

                                leaf out-of-memory-drops {
                                    type yang:counter32;
                                    description "Number of times a join is dropped because we ran out of memory.";
                                }

                                leaf mcs-failures {
                                    type yang:counter32;
                                    description "Number of times a group could not be synced through multi chassis synchronisation (MCS).";
                                }

                                leaf non-local {
                                    type yang:counter32;
                                    description "Non-local sender source IP address.";
                                }

                            } // container error

                        } // container statistics

                        list group {
                            key "group-address";
                            description "Multicast group membership information that joined on the sap.";

                            leaf group-address {
                                type types-sros:ipv4-multicast-address;
                                description "Group address of static IGMP multicast channel";
                            }

                            leaf group-type {
                                type types-igmp:learn-type;
                            }

                            leaf filter-mode {
                                type types-igmp:filter-mode;
                            }

                            leaf expiry-time {
                                type uint32;
                                units "seconds";
                                description "The time left before multicast group timeout.";
                            }

                            leaf up-time {
                                type uint32;
                                units "seconds";
                                description "The time elapsed since this entry was created.";
                            }

                            leaf v1-host-timer {
                                type uint32;
                                units "seconds";
                                description
                                    "The time remaining until the local router will assume that
                                     there are no longer any version 1 members.";
                            }

                            leaf v2-host-timer {
                                type uint32;
                                units "seconds";
                                description
                                    "The time remaining until the local router will assume that
                                     there are no longer any version 2 members.";
                            }

                            leaf igmp-compatibility-mode {
                                type types-igmp:igmp-version;
                                description "Compatibility with older version routers.";
                            }

                            leaf last-reporter {
                                type types-sros:ip-address;
                                description
                                    "The last host address which has sent the report to join
                                     the multicast group.";
                            }

                            list source {
                                key "source-address";
                                description "List of multicast source information of the multicast group.";

                                leaf source-address {
                                    type types-sros:ipv4-address;
                                    description "Source address of multicast channel.";
                                }

                                leaf source-type {
                                    type types-igmp:learn-type;
                                }

                                leaf forwarding-state {
                                    type types-igmp:forwarding-state;
                                    description "Traffic forwardeding state on this port.";
                                }

                                leaf expiry-time {
                                    type uint32;
                                    units "seconds";
                                    description "The time left before multicast group timeout.";
                                }

                                leaf up-time {
                                    type uint32;
                                    units "seconds";
                                    description "The time elapsed since this entry was created.";
                                }

                            } // list source

                        } // list group

                    } // list sap

                    list host {
                        key "ip-address mac-address pppoe-session-id";
                        description "List of hosts.";

                        leaf ip-address {
                            type types-sros:ipv4-address;
                            description "The IP address of this host.";
                        }

                        leaf mac-address {
                            type yang:mac-address;
                            description "The MAC address of this host.";
                        }

                        leaf pppoe-session-id {
                            type uint32;
                            description "The PPPoE session id of this host.";
                        }

                        leaf oper-state {
                            type types-sros:oper-state;
                            description "The current operating state of the IGMP protocol on this interface.";
                        }

                        leaf oper-version {
                            type types-igmp:igmp-version;
                            description "The operational version of the IGMP which is running on this interface.";
                        }

                        leaf group-count {
                            type int32;
                            description "The number of multicast groups which have been learned on this interface.";
                        }

                        leaf next-general-query-time {
                            type uint32;
                            units "seconds";
                            description
                                "The time remaining before the general query is sent on this interface
                                 if this router is the querier.";
                        }

                        leaf maximum-groups-until-now {
                            type uint32;
                            description "The highest value that 'group-count' had till now.";
                        }

                        leaf subscriber-id {
                            type types-sros:named-item;
                            description "The subscriber identification of this subscriber host.";
                        }

                        leaf bonding-context-id {
                            type types-submgt:bonding-context-id;
                            description "The bonding context identifier of the session of this host.";
                        }

                        leaf bonding-connection-index {
                            type types-submgt:bonding-connection-index;
                            description "The bonding connection index of the session of this host.";
                        }

                        leaf igmp-policy {
                            type types-sros:named-item;
                            description "The igmp-policy in use.";
                        }

                        container statistics {

                            container received {
                                description "Received message statistics.";

                                leaf general-queries {
                                    type yang:counter32;
                                    description "General Queries.";
                                }

                                leaf group-queries {
                                    type yang:counter32;
                                    description "Group Specific Queries.";
                                }

                                leaf group-source-queries {
                                    type yang:counter32;
                                    description "Group and Source Specific Queries.";
                                }

                                leaf v1-reports {
                                    type yang:counter32;
                                    description "V1 Reports.";
                                }

                                leaf v2-reports {
                                    type yang:counter32;
                                    description "V2 Reports.";
                                }

                                leaf v3-reports {
                                    type yang:counter32;
                                    description "V3 Reports.";
                                }

                                leaf leaves {
                                    type yang:counter32;
                                    description "Leaves.";
                                }

                                leaf drops {
                                    type yang:counter32;
                                    description "Total number of dropped packets.";
                                }

                            } // container received

                            container transmitted {
                                description "Transmit message statistics.";

                                leaf general-queries {
                                    type yang:counter32;
                                    description "General Queries.";
                                }

                                leaf group-queries {
                                    type yang:counter32;
                                    description "Group Specific Queries.";
                                }

                                leaf group-source-queries {
                                    type yang:counter32;
                                    description "Group and Source Specific Queries.";
                                }

                                leaf v1-reports {
                                    type yang:counter32;
                                    description "V1 Reports.";
                                }

                                leaf v2-reports {
                                    type yang:counter32;
                                    description "V2 Reports.";
                                }

                                leaf v3-reports {
                                    type yang:counter32;
                                    description "V3 Reports.";
                                }

                                leaf leaves {
                                    type yang:counter32;
                                    description "Leaves.";
                                }

                                leaf drops {
                                    type yang:counter32;
                                    description "Total number of dropped packets.";
                                }

                                leaf errors {
                                    type yang:counter32;
                                    description "Transmission Errors.";
                                }

                            } // container transmitted

                            container error {
                                description "Error message statistics.";

                                leaf bad-length {
                                    type yang:counter32;
                                    description "Bad length.";
                                }

                                leaf bad-ip-checksum {
                                    type yang:counter32;
                                    description "Bad Ip checksum.";
                                }

                                leaf unknown-type {
                                    type yang:counter32;
                                    description "Unknown type.";
                                }

                                leaf wrong-version {
                                    type yang:counter32;
                                    description "Wrong version.";
                                }

                                leaf import-policy-drops {
                                    type yang:counter32;
                                    description
                                        "Number of times we matched the host IP address or group or
                                         source addresses specified in the import policy.";
                                }

                                leaf missing-router-alert {
                                    type yang:counter32;
                                    description "Router alert flag is not set.";
                                }

                                leaf bad-encoding {
                                    type yang:counter32;
                                    description "Badly encoded.";
                                }

                                leaf local-scope {
                                    type yang:counter32;
                                    description "Link-local scope multicast group address.";
                                }

                                leaf mcac-policy-drops {
                                    type yang:counter32;
                                    description
                                        "Number of times a join is dropped because of applying a
                                         multicast CAC policy.";
                                }

                                leaf reached-maximum-number-groups {
                                    type yang:counter32;
                                    description
                                        "Number of times a join is dropped because we reached the maximum
                                         number of groups.";
                                }

                                leaf reached-maximum-number-group-sources {
                                    type yang:counter32;
                                    description
                                        "Number of times a join is dropped because we reached the maximum
                                         number group-source combinations.";
                                }

                                leaf reached-maximum-number-sources {
                                    type yang:counter32;
                                    description
                                        "Number of times a join is dropped because we reached the maximum
                                         number of sources per group.";
                                }

                                leaf out-of-memory-drops {
                                    type yang:counter32;
                                    description "Number of times a join is dropped because we ran out of memory.";
                                }

                                leaf mcs-failures {
                                    type yang:counter32;
                                    description "Number of times a group could not be synced through multi chassis synchronisation (MCS).";
                                }

                                leaf non-local {
                                    type yang:counter32;
                                    description "Non-local sender source IP address.";
                                }

                                leaf redirection-drops {
                                    type yang:counter32;
                                    description
                                        "Number of times a Group is dropped because of a failure
                                         while applying a redirection policy for this host.";
                                }

                            } // container error

                            container multicast-reporter {
                                description "Multicast reporting destination statistics";

                                container reported {

                                    leaf successfully-joined-streams {
                                        type yang:counter32;
                                        description "Number of joins that were successful.";
                                    }

                                    leaf denied-streams {
                                        type yang:counter32;
                                        description "Number of joins that were denied.";
                                    }

                                    leaf dropped-streams {
                                        type yang:counter32;
                                        description "Number of streams that were dropped.";
                                    }

                                } // container reported

                                container not-reported {

                                    leaf successfully-joined-streams {
                                        type yang:counter32;
                                        description "Number of joins that were successful.";
                                    }

                                    leaf denied-streams {
                                        type yang:counter32;
                                        description "Number of joins that were denied.";
                                    }

                                    leaf dropped-streams {
                                        type yang:counter32;
                                        description "Number of streams that were dropped.";
                                    }

                                } // container not-reported

                            } // container multicast-reporter

                        } // container statistics

                        list group {
                            key "group-address";
                            description "Multicast group membership information that joined on the host.";

                            leaf group-address {
                                type types-sros:ipv4-multicast-address;
                                description "Group address of static IGMP multicast channel";
                            }

                            leaf group-type {
                                type types-igmp:learn-type;
                            }

                            leaf filter-mode {
                                type types-igmp:filter-mode;
                            }

                            leaf expiry-time {
                                type uint32;
                                units "seconds";
                                description "The time left before multicast group timeout.";
                            }

                            leaf up-time {
                                type uint32;
                                units "seconds";
                                description "The time elapsed since this entry was created.";
                            }

                            leaf v1-host-timer {
                                type uint32;
                                units "seconds";
                                description
                                    "The time remaining until the local router will assume that
                                     there are no longer any version 1 members.";
                            }

                            leaf v2-host-timer {
                                type uint32;
                                units "seconds";
                                description
                                    "The time remaining until the local router will assume that
                                     there are no longer any version 2 members.";
                            }

                            leaf igmp-compatibility-mode {
                                type types-igmp:igmp-version;
                                description "Compatibility with older version routers.";
                            }

                            leaf last-reporter {
                                type types-sros:ip-address;
                                description
                                    "The last host address which has sent the report to join
                                     the multicast group.";
                            }

                            list source {
                                key "source-address";
                                description "List of multicast source information of the multicast group.";

                                leaf source-address {
                                    type types-sros:ipv4-address;
                                    description "Source address of multicast channel.";
                                }

                                leaf source-type {
                                    type types-igmp:learn-type;
                                }

                                leaf forwarding-state {
                                    type types-igmp:forwarding-state;
                                    description "Traffic forwardeding state on this port.";
                                }

                                leaf expiry-time {
                                    type uint32;
                                    units "seconds";
                                    description "The time left before multicast group timeout.";
                                }

                                leaf up-time {
                                    type uint32;
                                    units "seconds";
                                    description "The time elapsed since this entry was created.";
                                }

                            } // list source

                        } // list group

                    } // list host

                } // list group-interface

                list forwarding-group-interface {
                    key "forwarding-service group-interface-name";
                    description "Enter the forwarding-group-interface list instance";

                    leaf forwarding-service {
                        type types-services:service-name;
                        description "Forwarding service for a subscriber interface in a retailer context";
                    }

                    leaf group-interface-name {
                        type leafref {
                            path "../../../../vprn[service-name=current()/../forwarding-service]/subscriber-interface/group-interface/group-interface-name";
                        }
                        description "Group interface name";
                    }

                    leaf oper-state {
                        type types-sros:oper-state;
                        description "The current operating state of the IGMP protocol on this group interface.";
                    }

                    container mcac {
                        description "Enter the mcac context";

                        leaf in-use-mandatory-bandwidth {
                            type uint32;
                            units "kilobps";
                            description
                                "The in-use bandwidth for the mandatory channels for this
                                 protocol interface instance.";
                        }

                        leaf in-use-optional-bandwidth {
                            type uint32;
                            units "kilobps";
                            description
                                "The in-use bandwidth for the optional channels for this
                                 protocol interface instance.";
                        }

                        leaf available-mandatory-bandwidth {
                            type uint32;
                            units "kilobps";
                            description
                                "The pre-reserved bandwidth for the mandatory channels for
                                 this interface instance.";
                        }

                        leaf available-optional-bandwidth {
                            type uint32;
                            units "kilobps";
                            description "The available bandwidth for this interface instance.";
                        }

                        leaf values-in-transit {
                            type boolean;
                            description
                                "The operational (available and in-use mandatory/optional) value for the
                                 following objects is in transition due to configuration change:
                                 - available-mandatory-bandwidth
                                 - available-bandwidth
                                 - in-use-mandatory-bandwidth
                                 - in-use-optional-bandwidth.";
                        }

                    } // container mcac

                    list sap {
                        key "sap-id";
                        description "List of saps.";

                        leaf sap-id {
                            type types-sros:sap;
                            description "SAP identifier.";
                        }

                        leaf oper-state {
                            type types-sros:oper-state;
                            description "The current operating state of the IGMP protocol on this interface.";
                        }

                        leaf oper-version {
                            type types-igmp:igmp-version;
                            description "The operational version of the IGMP which is running on this interface.";
                        }

                        leaf group-count {
                            type int32;
                            description "The number of multicast groups which have been learned on this interface.";
                        }

                        leaf next-general-query-time {
                            type uint32;
                            units "seconds";
                            description
                                "The time remaining before the general query is sent on this interface
                                 if this router is the querier.";
                        }

                        leaf maximum-groups-until-now {
                            type uint32;
                            description "The highest value that 'group-count' had till now.";
                        }

                        container statistics {

                            container received {
                                description "Received message statistics.";

                                leaf general-queries {
                                    type yang:counter32;
                                    description "General Queries.";
                                }

                                leaf group-queries {
                                    type yang:counter32;
                                    description "Group Specific Queries.";
                                }

                                leaf group-source-queries {
                                    type yang:counter32;
                                    description "Group and Source Specific Queries.";
                                }

                                leaf v1-reports {
                                    type yang:counter32;
                                    description "V1 Reports.";
                                }

                                leaf v2-reports {
                                    type yang:counter32;
                                    description "V2 Reports.";
                                }

                                leaf v3-reports {
                                    type yang:counter32;
                                    description "V3 Reports.";
                                }

                                leaf leaves {
                                    type yang:counter32;
                                    description "Leaves.";
                                }

                                leaf drops {
                                    type yang:counter32;
                                    description "Total number of dropped packets.";
                                }

                            } // container received

                            container transmitted {
                                description "Transmit message statistics.";

                                leaf general-queries {
                                    type yang:counter32;
                                    description "General Queries.";
                                }

                                leaf group-queries {
                                    type yang:counter32;
                                    description "Group Specific Queries.";
                                }

                                leaf group-source-queries {
                                    type yang:counter32;
                                    description "Group and Source Specific Queries.";
                                }

                                leaf v1-reports {
                                    type yang:counter32;
                                    description "V1 Reports.";
                                }

                                leaf v2-reports {
                                    type yang:counter32;
                                    description "V2 Reports.";
                                }

                                leaf v3-reports {
                                    type yang:counter32;
                                    description "V3 Reports.";
                                }

                                leaf leaves {
                                    type yang:counter32;
                                    description "Leaves.";
                                }

                                leaf drops {
                                    type yang:counter32;
                                    description "Total number of dropped packets.";
                                }

                                leaf errors {
                                    type yang:counter32;
                                    description "Transmission Errors.";
                                }

                            } // container transmitted

                            container error {
                                description "Error message statistics.";

                                leaf bad-length {
                                    type yang:counter32;
                                    description "Bad length.";
                                }

                                leaf bad-ip-checksum {
                                    type yang:counter32;
                                    description "Bad Ip checksum.";
                                }

                                leaf unknown-type {
                                    type yang:counter32;
                                    description "Unknown type.";
                                }

                                leaf wrong-version {
                                    type yang:counter32;
                                    description "Wrong version.";
                                }

                                leaf import-policy-drops {
                                    type yang:counter32;
                                    description
                                        "Number of times we matched the host IP address or group or
                                         source addresses specified in the import policy.";
                                }

                                leaf missing-router-alert {
                                    type yang:counter32;
                                    description "Router alert flag is not set.";
                                }

                                leaf bad-encoding {
                                    type yang:counter32;
                                    description "Badly encoded.";
                                }

                                leaf local-scope {
                                    type yang:counter32;
                                    description "Link-local scope multicast group address.";
                                }

                                leaf mcac-policy-drops {
                                    type yang:counter32;
                                    description
                                        "Number of times a join is dropped because of applying a
                                         multicast CAC policy.";
                                }

                                leaf reached-maximum-number-groups {
                                    type yang:counter32;
                                    description
                                        "Number of times a join is dropped because we reached the maximum
                                         number of groups.";
                                }

                                leaf reached-maximum-number-group-sources {
                                    type yang:counter32;
                                    description
                                        "Number of times a join is dropped because we reached the maximum
                                         number group-source combinations.";
                                }

                                leaf reached-maximum-number-sources {
                                    type yang:counter32;
                                    description
                                        "Number of times a join is dropped because we reached the maximum
                                         number of sources per group.";
                                }

                                leaf out-of-memory-drops {
                                    type yang:counter32;
                                    description "Number of times a join is dropped because we ran out of memory.";
                                }

                                leaf mcs-failures {
                                    type yang:counter32;
                                    description "Number of times a group could not be synced through multi chassis synchronisation (MCS).";
                                }

                                leaf non-local {
                                    type yang:counter32;
                                    description "Non-local sender source IP address.";
                                }

                            } // container error

                        } // container statistics

                        list group {
                            key "group-address";
                            description "Multicast group membership information that joined on the sap.";

                            leaf group-address {
                                type types-sros:ipv4-multicast-address;
                                description "Group address of static IGMP multicast channel";
                            }

                            leaf group-type {
                                type types-igmp:learn-type;
                            }

                            leaf filter-mode {
                                type types-igmp:filter-mode;
                            }

                            leaf expiry-time {
                                type uint32;
                                units "seconds";
                                description "The time left before multicast group timeout.";
                            }

                            leaf up-time {
                                type uint32;
                                units "seconds";
                                description "The time elapsed since this entry was created.";
                            }

                            leaf v1-host-timer {
                                type uint32;
                                units "seconds";
                                description
                                    "The time remaining until the local router will assume that
                                     there are no longer any version 1 members.";
                            }

                            leaf v2-host-timer {
                                type uint32;
                                units "seconds";
                                description
                                    "The time remaining until the local router will assume that
                                     there are no longer any version 2 members.";
                            }

                            leaf igmp-compatibility-mode {
                                type types-igmp:igmp-version;
                                description "Compatibility with older version routers.";
                            }

                            leaf last-reporter {
                                type types-sros:ip-address;
                                description
                                    "The last host address which has sent the report to join
                                     the multicast group.";
                            }

                            list source {
                                key "source-address";
                                description "List of multicast source information of the multicast group.";

                                leaf source-address {
                                    type types-sros:ipv4-address;
                                    description "Source address of multicast channel.";
                                }

                                leaf source-type {
                                    type types-igmp:learn-type;
                                }

                                leaf forwarding-state {
                                    type types-igmp:forwarding-state;
                                    description "Traffic forwardeding state on this port.";
                                }

                                leaf expiry-time {
                                    type uint32;
                                    units "seconds";
                                    description "The time left before multicast group timeout.";
                                }

                                leaf up-time {
                                    type uint32;
                                    units "seconds";
                                    description "The time elapsed since this entry was created.";
                                }

                            } // list source

                        } // list group

                    } // list sap

                    list host {
                        key "ip-address mac-address pppoe-session-id";
                        description "List of hosts.";

                        leaf ip-address {
                            type types-sros:ipv4-address;
                            description "The IP address of this host.";
                        }

                        leaf mac-address {
                            type yang:mac-address;
                            description "The MAC address of this host.";
                        }

                        leaf pppoe-session-id {
                            type uint32;
                            description "The PPPoE session id of this host.";
                        }

                        leaf oper-state {
                            type types-sros:oper-state;
                            description "The current operating state of the IGMP protocol on this interface.";
                        }

                        leaf oper-version {
                            type types-igmp:igmp-version;
                            description "The operational version of the IGMP which is running on this interface.";
                        }

                        leaf group-count {
                            type int32;
                            description "The number of multicast groups which have been learned on this interface.";
                        }

                        leaf next-general-query-time {
                            type uint32;
                            units "seconds";
                            description
                                "The time remaining before the general query is sent on this interface
                                 if this router is the querier.";
                        }

                        leaf maximum-groups-until-now {
                            type uint32;
                            description "The highest value that 'group-count' had till now.";
                        }

                        leaf subscriber-id {
                            type types-sros:named-item;
                            description "The subscriber identification of this subscriber host.";
                        }

                        leaf bonding-context-id {
                            type types-submgt:bonding-context-id;
                            description "The bonding context identifier of the session of this host.";
                        }

                        leaf bonding-connection-index {
                            type types-submgt:bonding-connection-index;
                            description "The bonding connection index of the session of this host.";
                        }

                        leaf igmp-policy {
                            type types-sros:named-item;
                            description "The igmp-policy in use.";
                        }

                        container statistics {

                            container received {
                                description "Received message statistics.";

                                leaf general-queries {
                                    type yang:counter32;
                                    description "General Queries.";
                                }

                                leaf group-queries {
                                    type yang:counter32;
                                    description "Group Specific Queries.";
                                }

                                leaf group-source-queries {
                                    type yang:counter32;
                                    description "Group and Source Specific Queries.";
                                }

                                leaf v1-reports {
                                    type yang:counter32;
                                    description "V1 Reports.";
                                }

                                leaf v2-reports {
                                    type yang:counter32;
                                    description "V2 Reports.";
                                }

                                leaf v3-reports {
                                    type yang:counter32;
                                    description "V3 Reports.";
                                }

                                leaf leaves {
                                    type yang:counter32;
                                    description "Leaves.";
                                }

                                leaf drops {
                                    type yang:counter32;
                                    description "Total number of dropped packets.";
                                }

                            } // container received

                            container transmitted {
                                description "Transmit message statistics.";

                                leaf general-queries {
                                    type yang:counter32;
                                    description "General Queries.";
                                }

                                leaf group-queries {
                                    type yang:counter32;
                                    description "Group Specific Queries.";
                                }

                                leaf group-source-queries {
                                    type yang:counter32;
                                    description "Group and Source Specific Queries.";
                                }

                                leaf v1-reports {
                                    type yang:counter32;
                                    description "V1 Reports.";
                                }

                                leaf v2-reports {
                                    type yang:counter32;
                                    description "V2 Reports.";
                                }

                                leaf v3-reports {
                                    type yang:counter32;
                                    description "V3 Reports.";
                                }

                                leaf leaves {
                                    type yang:counter32;
                                    description "Leaves.";
                                }

                                leaf drops {
                                    type yang:counter32;
                                    description "Total number of dropped packets.";
                                }

                                leaf errors {
                                    type yang:counter32;
                                    description "Transmission Errors.";
                                }

                            } // container transmitted

                            container error {
                                description "Error message statistics.";

                                leaf bad-length {
                                    type yang:counter32;
                                    description "Bad length.";
                                }

                                leaf bad-ip-checksum {
                                    type yang:counter32;
                                    description "Bad Ip checksum.";
                                }

                                leaf unknown-type {
                                    type yang:counter32;
                                    description "Unknown type.";
                                }

                                leaf wrong-version {
                                    type yang:counter32;
                                    description "Wrong version.";
                                }

                                leaf import-policy-drops {
                                    type yang:counter32;
                                    description
                                        "Number of times we matched the host IP address or group or
                                         source addresses specified in the import policy.";
                                }

                                leaf missing-router-alert {
                                    type yang:counter32;
                                    description "Router alert flag is not set.";
                                }

                                leaf bad-encoding {
                                    type yang:counter32;
                                    description "Badly encoded.";
                                }

                                leaf local-scope {
                                    type yang:counter32;
                                    description "Link-local scope multicast group address.";
                                }

                                leaf mcac-policy-drops {
                                    type yang:counter32;
                                    description
                                        "Number of times a join is dropped because of applying a
                                         multicast CAC policy.";
                                }

                                leaf reached-maximum-number-groups {
                                    type yang:counter32;
                                    description
                                        "Number of times a join is dropped because we reached the maximum
                                         number of groups.";
                                }

                                leaf reached-maximum-number-group-sources {
                                    type yang:counter32;
                                    description
                                        "Number of times a join is dropped because we reached the maximum
                                         number group-source combinations.";
                                }

                                leaf reached-maximum-number-sources {
                                    type yang:counter32;
                                    description
                                        "Number of times a join is dropped because we reached the maximum
                                         number of sources per group.";
                                }

                                leaf out-of-memory-drops {
                                    type yang:counter32;
                                    description "Number of times a join is dropped because we ran out of memory.";
                                }

                                leaf mcs-failures {
                                    type yang:counter32;
                                    description "Number of times a group could not be synced through multi chassis synchronisation (MCS).";
                                }

                                leaf non-local {
                                    type yang:counter32;
                                    description "Non-local sender source IP address.";
                                }

                                leaf redirection-drops {
                                    type yang:counter32;
                                    description
                                        "Number of times a Group is dropped because of a failure
                                         while applying a redirection policy for this host.";
                                }

                            } // container error

                            container multicast-reporter {
                                description "Multicast reporting destination statistics";

                                container reported {

                                    leaf successfully-joined-streams {
                                        type yang:counter32;
                                        description "Number of joins that were successful.";
                                    }

                                    leaf denied-streams {
                                        type yang:counter32;
                                        description "Number of joins that were denied.";
                                    }

                                    leaf dropped-streams {
                                        type yang:counter32;
                                        description "Number of streams that were dropped.";
                                    }

                                } // container reported

                                container not-reported {

                                    leaf successfully-joined-streams {
                                        type yang:counter32;
                                        description "Number of joins that were successful.";
                                    }

                                    leaf denied-streams {
                                        type yang:counter32;
                                        description "Number of joins that were denied.";
                                    }

                                    leaf dropped-streams {
                                        type yang:counter32;
                                        description "Number of streams that were dropped.";
                                    }

                                } // container not-reported

                            } // container multicast-reporter

                        } // container statistics

                        list group {
                            key "group-address";
                            description "Multicast group membership information that joined on the host.";

                            leaf group-address {
                                type types-sros:ipv4-multicast-address;
                                description "Group address of static IGMP multicast channel";
                            }

                            leaf group-type {
                                type types-igmp:learn-type;
                            }

                            leaf filter-mode {
                                type types-igmp:filter-mode;
                            }

                            leaf expiry-time {
                                type uint32;
                                units "seconds";
                                description "The time left before multicast group timeout.";
                            }

                            leaf up-time {
                                type uint32;
                                units "seconds";
                                description "The time elapsed since this entry was created.";
                            }

                            leaf v1-host-timer {
                                type uint32;
                                units "seconds";
                                description
                                    "The time remaining until the local router will assume that
                                     there are no longer any version 1 members.";
                            }

                            leaf v2-host-timer {
                                type uint32;
                                units "seconds";
                                description
                                    "The time remaining until the local router will assume that
                                     there are no longer any version 2 members.";
                            }

                            leaf igmp-compatibility-mode {
                                type types-igmp:igmp-version;
                                description "Compatibility with older version routers.";
                            }

                            leaf last-reporter {
                                type types-sros:ip-address;
                                description
                                    "The last host address which has sent the report to join
                                     the multicast group.";
                            }

                            list source {
                                key "source-address";
                                description "List of multicast source information of the multicast group.";

                                leaf source-address {
                                    type types-sros:ipv4-address;
                                    description "Source address of multicast channel.";
                                }

                                leaf source-type {
                                    type types-igmp:learn-type;
                                }

                                leaf forwarding-state {
                                    type types-igmp:forwarding-state;
                                    description "Traffic forwardeding state on this port.";
                                }

                                leaf expiry-time {
                                    type uint32;
                                    units "seconds";
                                    description "The time left before multicast group timeout.";
                                }

                                leaf up-time {
                                    type uint32;
                                    units "seconds";
                                    description "The time elapsed since this entry was created.";
                                }

                            } // list source

                        } // list group

                    } // list host

                } // list forwarding-group-interface

                list host {
                    key "ip-address mac-address pppoe-session-id";
                    description "List of subscriber management hosts.";

                    leaf ip-address {
                        type types-sros:ipv4-address;
                        description "The IP address of this host.";
                    }

                    leaf mac-address {
                        type yang:mac-address;
                        description "The MAC address of this host.";
                    }

                    leaf pppoe-session-id {
                        type uint32;
                        description "The PPPoE session id of this host.";
                    }

                    leaf group-interface-name {
                        type leafref {
                            path "../../group-interface/group-interface-name";
                        }
                        description "The group-interface this host belongs to.";
                    }

                    leaf forwarding-group-interface-service-name {
                        type leafref {
                            path "../../forwarding-group-interface/forwarding-service";
                        }
                        description "The service-name of the forwarding-group-interface this host belongs to.";
                    }

                    leaf forwarding-group-interface-name {
                        type leafref {
                            path "../../forwarding-group-interface/group-interface-name";
                        }
                        description "The name of the forwarding-group-interface this host belongs to.";
                    }

                } // list host

            } // container igmp

            container mld {
                description "Enter the mld context";

                leaf oper-state {
                    type types-sros:oper-state;
                    description "The current operating state of this MLD protocol instance on this router.";
                }

                list interface {
                    key "ip-interface-name";
                    description "Enter the interface list instance";

                    leaf ip-interface-name {
                        type types-sros:interface-name;
                        description "Interface name.";
                    }

                    leaf oper-state {
                        type types-sros:oper-state;
                        description "The current operating state of the MLD protocol on this interface.";
                    }

                    leaf oper-version {
                        type types-igmp:mld-version;
                        description "The operational version of the MLD which is running on this interface.";
                    }

                    leaf group-count {
                        type int32;
                        description "The number of multicast groups which have been learned on this interface.";
                    }

                    leaf next-general-query-time {
                        type uint32;
                        units "seconds";
                        description
                            "The time remaining before the general query is sent on this interface
                             if this router is the querier.";
                    }

                    leaf maximum-groups-until-now {
                        type int32;
                        description "The highest value that 'group-count' had till now.";
                    }

                    leaf querier {
                        type types-sros:ipv6-address;
                        description "The address of the MLD Querier on the IP subnet to which this interface is attached.";
                    }

                    leaf querier-up-time {
                        type uint32;
                        units "seconds";
                        description "The time since 'querier' was last elected as querier.";
                    }

                    leaf querier-expiry-time {
                        type uint32;
                        units "seconds";
                        description "The time remaining before querier is aged out.";
                    }

                    container mcac {
                        description "Enter the mcac context";

                        leaf in-use-mandatory-bandwidth {
                            type uint32;
                            units "kilobps";
                            description
                                "The in-use bandwidth for the mandatory channels for this
                                 protocol interface instance.";
                        }

                        leaf in-use-optional-bandwidth {
                            type uint32;
                            units "kilobps";
                            description
                                "The in-use bandwidth for the optional channels for this
                                 protocol interface instance.";
                        }

                        leaf available-mandatory-bandwidth {
                            type uint32;
                            units "kilobps";
                            description
                                "The pre-reserved bandwidth for the mandatory channels for
                                 this interface instance.";
                        }

                        leaf available-optional-bandwidth {
                            type uint32;
                            units "kilobps";
                            description "The available bandwidth for this interface instance.";
                        }

                        leaf values-in-transit {
                            type boolean;
                            description
                                "The operational (available and in-use mandatory/optional) value for the
                                 following objects is in transition due to configuration change:
                                 - available-mandatory-bandwidth
                                 - available-bandwidth
                                 - in-use-mandatory-bandwidth
                                 - in-use-optional-bandwidth.";
                        }

                    } // container mcac

                    container static {
                        description "Enter the static context";

                        list group-range {
                            key "start end step";
                            description "Enter the group-range list instance";

                            leaf start {
                                type types-sros:ipv6-multicast-address;
                                description "Start of group range of multicast channel";
                            }

                            leaf end {
                                type types-sros:ipv6-multicast-address;
                                description "End of group range for multicast channel";
                            }

                            leaf step {
                                type types-sros:ipv6-address;
                                description "Step interval for the group-range addresses";
                            }

                            leaf group-count {
                                type uint32;
                                description "The number of groups in the group-range.";
                            }

                        } // list group-range

                    } // container static

                    container statistics {

                        container received {
                            description "Received message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf leaves {
                                type yang:counter32;
                                description "Leaves.";
                            }

                            leaf drops {
                                type yang:counter32;
                                description "Total number of dropped packets.";
                            }

                        } // container received

                        container transmitted {
                            description "Transmit message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf leaves {
                                type yang:counter32;
                                description "Leaves.";
                            }

                            leaf drops {
                                type yang:counter32;
                                description "Total number of dropped packets.";
                            }

                            leaf errors {
                                type yang:counter32;
                                description "Transmission Errors.";
                            }

                        } // container transmitted

                        container error {
                            description "Error message statistics.";

                            leaf bad-length {
                                type yang:counter32;
                                description "Bad length.";
                            }

                            leaf bad-ip-checksum {
                                type yang:counter32;
                                description "Bad Ip checksum.";
                            }

                            leaf unknown-type {
                                type yang:counter32;
                                description "Unknown type.";
                            }

                            leaf wrong-version {
                                type yang:counter32;
                                description "Wrong version.";
                            }

                            leaf import-policy-drops {
                                type yang:counter32;
                                description
                                    "Number of times we matched the host IP address or group or
                                     source addresses specified in the import policy.";
                            }

                            leaf missing-router-alert {
                                type yang:counter32;
                                description "Router alert flag is not set.";
                            }

                            leaf bad-encoding {
                                type yang:counter32;
                                description "Badly encoded.";
                            }

                            leaf local-scope {
                                type yang:counter32;
                                description "Link-local scope multicast group address.";
                            }

                            leaf reserved-scope {
                                type yang:counter32;
                                description "Reserved scope multicast group address.";
                            }

                            leaf mcac-policy-drops {
                                type yang:counter32;
                                description
                                    "Number of times a join is dropped because of applying a
                                     multicast CAC policy.";
                            }

                            leaf reached-maximum-number-groups {
                                type yang:counter32;
                                description
                                    "Number of times a join is dropped because we reached the maximum
                                     number of groups.";
                            }

                            leaf reached-maximum-number-group-sources {
                                type yang:counter32;
                                description
                                    "Number of times a join is dropped because we reached the maximum
                                     number group-source combinations.";
                            }

                            leaf reached-maximum-number-sources {
                                type yang:counter32;
                                description
                                    "Number of times a join is dropped because we reached the maximum
                                     number of sources per group.";
                            }

                            leaf out-of-memory-drops {
                                type yang:counter32;
                                description "Number of times a join is dropped because we ran out of memory.";
                            }

                            leaf mcs-failures {
                                type yang:counter32;
                                description "Number of times a group could not be synced through multi chassis synchronisation (MCS).";
                            }

                            leaf non-local {
                                type yang:counter32;
                                description "Non-local sender source IP address.";
                            }

                        } // container error

                    } // container statistics

                    list group {
                        key "group-address";
                        description
                            "Multicast group membership information that joined on
                             the interface.";

                        leaf group-address {
                            type types-sros:ipv6-multicast-address;
                            description "Group address of multicast channel";
                        }

                        leaf group-type {
                            type types-igmp:learn-type;
                        }

                        leaf filter-mode {
                            type types-igmp:filter-mode;
                        }

                        leaf expiry-time {
                            type uint32;
                            units "seconds";
                            description "The time left before multicast group timeout.";
                        }

                        leaf up-time {
                            type uint32;
                            units "seconds";
                            description "The time elapsed since this entry was created.";
                        }

                        leaf v1-host-timer {
                            type uint32;
                            units "seconds";
                            description
                                "The time remaining until the local router will assume that
                                 there are no longer any version 1 members.";
                        }

                        leaf mld-compatibility-mode {
                            type types-igmp:mld-version;
                            description "Compatibility with older version routers.";
                        }

                        leaf last-reporter {
                            type types-sros:ip-address;
                            description
                                "The last host address which has sent the report to join
                                 the multicast group.";
                        }

                        list source {
                            key "source-address";
                            description
                                "List of multicast source information of
                                 the multicast group.";

                            leaf source-address {
                                type types-sros:ipv6-address;
                                description "Source address of multicast channel.";
                            }

                            leaf source-type {
                                type types-igmp:learn-type;
                            }

                            leaf forwarding-state {
                                type types-igmp:forwarding-state;
                                description "Traffic forwardeding state on this port.";
                            }

                            leaf expiry-time {
                                type uint32;
                                units "seconds";
                                description "The time left before multicast group timeout.";
                            }

                            leaf up-time {
                                type uint32;
                                units "seconds";
                                description "The time elapsed since this entry was created.";
                            }

                        } // list source

                    } // list group

                } // list interface

                list group-interface {
                    key "group-interface-name";
                    description "Enter the group-interface list instance";

                    leaf group-interface-name {
                        type leafref {
                            path "../../../subscriber-interface/group-interface/group-interface-name";
                        }
                        description "Group interface name";
                    }

                    leaf oper-state {
                        type types-sros:oper-state;
                        description "The current operating state of the MLD protocol on this group interface.";
                    }

                    container mcac {
                        description "Enter the mcac context";

                        leaf in-use-mandatory-bandwidth {
                            type uint32;
                            units "kilobps";
                            description
                                "The in-use bandwidth for the mandatory channels for this
                                 protocol interface instance.";
                        }

                        leaf in-use-optional-bandwidth {
                            type uint32;
                            units "kilobps";
                            description
                                "The in-use bandwidth for the optional channels for this
                                 protocol interface instance.";
                        }

                        leaf available-mandatory-bandwidth {
                            type uint32;
                            units "kilobps";
                            description
                                "The pre-reserved bandwidth for the mandatory channels for
                                 this interface instance.";
                        }

                        leaf available-optional-bandwidth {
                            type uint32;
                            units "kilobps";
                            description "The available bandwidth for this interface instance.";
                        }

                        leaf values-in-transit {
                            type boolean;
                            description
                                "The operational (available and in-use mandatory/optional) value for the
                                 following objects is in transition due to configuration change:
                                 - available-mandatory-bandwidth
                                 - available-bandwidth
                                 - in-use-mandatory-bandwidth
                                 - in-use-optional-bandwidth.";
                        }

                    } // container mcac

                    list sap {
                        key "sap-id";
                        description "List of saps.";

                        leaf sap-id {
                            type types-sros:sap;
                            description "SAP identifier.";
                        }

                        leaf oper-state {
                            type types-sros:oper-state;
                            description "The current operating state of the MLD protocol on this interface.";
                        }

                        leaf oper-version {
                            type types-igmp:mld-version;
                            description "The operational version of the MLD which is running on this interface.";
                        }

                        leaf group-count {
                            type int32;
                            description "The number of multicast groups which have been learned on this interface.";
                        }

                        leaf next-general-query-time {
                            type uint32;
                            units "seconds";
                            description
                                "The time remaining before the general query is sent on this interface
                                 if this router is the querier.";
                        }

                        leaf maximum-groups-until-now {
                            type int32;
                            description "The highest value that 'group-count' had till now.";
                        }

                        container statistics {

                            container received {
                                description "Received message statistics.";

                                leaf general-queries {
                                    type yang:counter32;
                                    description "General Queries.";
                                }

                                leaf group-queries {
                                    type yang:counter32;
                                    description "Group Specific Queries.";
                                }

                                leaf group-source-queries {
                                    type yang:counter32;
                                    description "Group and Source Specific Queries.";
                                }

                                leaf v1-reports {
                                    type yang:counter32;
                                    description "V1 Reports.";
                                }

                                leaf v2-reports {
                                    type yang:counter32;
                                    description "V2 Reports.";
                                }

                                leaf leaves {
                                    type yang:counter32;
                                    description "Leaves.";
                                }

                                leaf drops {
                                    type yang:counter32;
                                    description "Total number of dropped packets.";
                                }

                            } // container received

                            container transmitted {
                                description "Transmit message statistics.";

                                leaf general-queries {
                                    type yang:counter32;
                                    description "General Queries.";
                                }

                                leaf group-queries {
                                    type yang:counter32;
                                    description "Group Specific Queries.";
                                }

                                leaf group-source-queries {
                                    type yang:counter32;
                                    description "Group and Source Specific Queries.";
                                }

                                leaf v1-reports {
                                    type yang:counter32;
                                    description "V1 Reports.";
                                }

                                leaf v2-reports {
                                    type yang:counter32;
                                    description "V2 Reports.";
                                }

                                leaf leaves {
                                    type yang:counter32;
                                    description "Leaves.";
                                }

                                leaf drops {
                                    type yang:counter32;
                                    description "Total number of dropped packets.";
                                }

                                leaf errors {
                                    type yang:counter32;
                                    description "Transmission Errors.";
                                }

                            } // container transmitted

                            container error {
                                description "Error message statistics.";

                                leaf bad-length {
                                    type yang:counter32;
                                    description "Bad length.";
                                }

                                leaf bad-ip-checksum {
                                    type yang:counter32;
                                    description "Bad Ip checksum.";
                                }

                                leaf unknown-type {
                                    type yang:counter32;
                                    description "Unknown type.";
                                }

                                leaf wrong-version {
                                    type yang:counter32;
                                    description "Wrong version.";
                                }

                                leaf import-policy-drops {
                                    type yang:counter32;
                                    description
                                        "Number of times we matched the host IP address or group or
                                         source addresses specified in the import policy.";
                                }

                                leaf missing-router-alert {
                                    type yang:counter32;
                                    description "Router alert flag is not set.";
                                }

                                leaf bad-encoding {
                                    type yang:counter32;
                                    description "Badly encoded.";
                                }

                                leaf local-scope {
                                    type yang:counter32;
                                    description "Link-local scope multicast group address.";
                                }

                                leaf reserved-scope {
                                    type yang:counter32;
                                    description "Reserved scope multicast group address.";
                                }

                                leaf mcac-policy-drops {
                                    type yang:counter32;
                                    description
                                        "Number of times a join is dropped because of applying a
                                         multicast CAC policy.";
                                }

                                leaf reached-maximum-number-groups {
                                    type yang:counter32;
                                    description
                                        "Number of times a join is dropped because we reached the maximum
                                         number of groups.";
                                }

                                leaf reached-maximum-number-group-sources {
                                    type yang:counter32;
                                    description
                                        "Number of times a join is dropped because we reached the maximum
                                         number group-source combinations.";
                                }

                                leaf reached-maximum-number-sources {
                                    type yang:counter32;
                                    description
                                        "Number of times a join is dropped because we reached the maximum
                                         number of sources per group.";
                                }

                                leaf out-of-memory-drops {
                                    type yang:counter32;
                                    description "Number of times a join is dropped because we ran out of memory.";
                                }

                                leaf mcs-failures {
                                    type yang:counter32;
                                    description "Number of times a group could not be synced through multi chassis synchronisation (MCS).";
                                }

                                leaf non-local {
                                    type yang:counter32;
                                    description "Non-local sender source IP address.";
                                }

                            } // container error

                        } // container statistics

                        list group {
                            key "group-address";
                            description
                                "Multicast group membership information that joined on
                                 the sap.";

                            leaf group-address {
                                type types-sros:ipv6-multicast-address;
                                description "Group address of multicast channel";
                            }

                            leaf group-type {
                                type types-igmp:learn-type;
                            }

                            leaf filter-mode {
                                type types-igmp:filter-mode;
                            }

                            leaf expiry-time {
                                type uint32;
                                units "seconds";
                                description "The time left before multicast group timeout.";
                            }

                            leaf up-time {
                                type uint32;
                                units "seconds";
                                description "The time elapsed since this entry was created.";
                            }

                            leaf v1-host-timer {
                                type uint32;
                                units "seconds";
                                description
                                    "The time remaining until the local router will assume that
                                     there are no longer any version 1 members.";
                            }

                            leaf mld-compatibility-mode {
                                type types-igmp:mld-version;
                                description "Compatibility with older version routers.";
                            }

                            leaf last-reporter {
                                type types-sros:ip-address;
                                description
                                    "The last host address which has sent the report to join
                                     the multicast group.";
                            }

                            list source {
                                key "source-address";
                                description
                                    "List of multicast source information of
                                     the multicast group.";

                                leaf source-address {
                                    type types-sros:ipv6-address;
                                    description "Source address of multicast channel.";
                                }

                                leaf source-type {
                                    type types-igmp:learn-type;
                                }

                                leaf forwarding-state {
                                    type types-igmp:forwarding-state;
                                    description "Traffic forwardeding state on this port.";
                                }

                                leaf expiry-time {
                                    type uint32;
                                    units "seconds";
                                    description "The time left before multicast group timeout.";
                                }

                                leaf up-time {
                                    type uint32;
                                    units "seconds";
                                    description "The time elapsed since this entry was created.";
                                }

                            } // list source

                        } // list group

                    } // list sap

                    list host {
                        key "ip-address mac-address pppoe-session-id";
                        description "List of hosts.";

                        leaf ip-address {
                            type types-sros:ipv6-address;
                            description "The IP address of this host.";
                        }

                        leaf mac-address {
                            type yang:mac-address;
                            description "The MAC address of this host.";
                        }

                        leaf pppoe-session-id {
                            type uint32;
                            description "The PPPoE session id of this host.";
                        }

                        leaf oper-state {
                            type types-sros:oper-state;
                            description "The current operating state of the MLD protocol on this interface.";
                        }

                        leaf oper-version {
                            type types-igmp:mld-version;
                            description "The operational version of the MLD which is running on this interface.";
                        }

                        leaf group-count {
                            type int32;
                            description "The number of multicast groups which have been learned on this interface.";
                        }

                        leaf next-general-query-time {
                            type uint32;
                            units "seconds";
                            description
                                "The time remaining before the general query is sent on this interface
                                 if this router is the querier.";
                        }

                        leaf maximum-groups-until-now {
                            type int32;
                            description "The highest value that 'group-count' had till now.";
                        }

                        leaf subscriber-id {
                            type types-sros:named-item;
                            description "The subscriber identification of this subscriber host.";
                        }

                        leaf bonding-context-id {
                            type types-submgt:bonding-context-id;
                            description "The bonding context identifier of the session of this host.";
                        }

                        leaf bonding-connection-index {
                            type types-submgt:bonding-connection-index;
                            description "The bonding connection index of the session of this host.";
                        }

                        leaf mld-policy {
                            type types-sros:named-item;
                            description "The mld-policy in use.";
                        }

                        container statistics {

                            container received {
                                description "Received message statistics.";

                                leaf general-queries {
                                    type yang:counter32;
                                    description "General Queries.";
                                }

                                leaf group-queries {
                                    type yang:counter32;
                                    description "Group Specific Queries.";
                                }

                                leaf group-source-queries {
                                    type yang:counter32;
                                    description "Group and Source Specific Queries.";
                                }

                                leaf v1-reports {
                                    type yang:counter32;
                                    description "V1 Reports.";
                                }

                                leaf v2-reports {
                                    type yang:counter32;
                                    description "V2 Reports.";
                                }

                                leaf leaves {
                                    type yang:counter32;
                                    description "Leaves.";
                                }

                                leaf drops {
                                    type yang:counter32;
                                    description "Total number of dropped packets.";
                                }

                            } // container received

                            container transmitted {
                                description "Transmit message statistics.";

                                leaf general-queries {
                                    type yang:counter32;
                                    description "General Queries.";
                                }

                                leaf group-queries {
                                    type yang:counter32;
                                    description "Group Specific Queries.";
                                }

                                leaf group-source-queries {
                                    type yang:counter32;
                                    description "Group and Source Specific Queries.";
                                }

                                leaf v1-reports {
                                    type yang:counter32;
                                    description "V1 Reports.";
                                }

                                leaf v2-reports {
                                    type yang:counter32;
                                    description "V2 Reports.";
                                }

                                leaf leaves {
                                    type yang:counter32;
                                    description "Leaves.";
                                }

                                leaf drops {
                                    type yang:counter32;
                                    description "Total number of dropped packets.";
                                }

                                leaf errors {
                                    type yang:counter32;
                                    description "Transmission Errors.";
                                }

                            } // container transmitted

                            container error {
                                description "Error message statistics.";

                                leaf bad-length {
                                    type yang:counter32;
                                    description "Bad length.";
                                }

                                leaf bad-ip-checksum {
                                    type yang:counter32;
                                    description "Bad Ip checksum.";
                                }

                                leaf unknown-type {
                                    type yang:counter32;
                                    description "Unknown type.";
                                }

                                leaf wrong-version {
                                    type yang:counter32;
                                    description "Wrong version.";
                                }

                                leaf import-policy-drops {
                                    type yang:counter32;
                                    description
                                        "Number of times we matched the host IP address or group or
                                         source addresses specified in the import policy.";
                                }

                                leaf missing-router-alert {
                                    type yang:counter32;
                                    description "Router alert flag is not set.";
                                }

                                leaf bad-encoding {
                                    type yang:counter32;
                                    description "Badly encoded.";
                                }

                                leaf local-scope {
                                    type yang:counter32;
                                    description "Link-local scope multicast group address.";
                                }

                                leaf reserved-scope {
                                    type yang:counter32;
                                    description "Reserved scope multicast group address.";
                                }

                                leaf mcac-policy-drops {
                                    type yang:counter32;
                                    description
                                        "Number of times a join is dropped because of applying a
                                         multicast CAC policy.";
                                }

                                leaf reached-maximum-number-groups {
                                    type yang:counter32;
                                    description
                                        "Number of times a join is dropped because we reached the maximum
                                         number of groups.";
                                }

                                leaf reached-maximum-number-group-sources {
                                    type yang:counter32;
                                    description
                                        "Number of times a join is dropped because we reached the maximum
                                         number group-source combinations.";
                                }

                                leaf reached-maximum-number-sources {
                                    type yang:counter32;
                                    description
                                        "Number of times a join is dropped because we reached the maximum
                                         number of sources per group.";
                                }

                                leaf out-of-memory-drops {
                                    type yang:counter32;
                                    description "Number of times a join is dropped because we ran out of memory.";
                                }

                                leaf mcs-failures {
                                    type yang:counter32;
                                    description "Number of times a group could not be synced through multi chassis synchronisation (MCS).";
                                }

                                leaf non-local {
                                    type yang:counter32;
                                    description "Non-local sender source IP address.";
                                }

                                leaf redirection-drops {
                                    type yang:counter32;
                                    description
                                        "Number of times a Group is dropped because of a failure
                                         while applying a redirection policy for this host.";
                                }

                            } // container error

                        } // container statistics

                        list group {
                            key "group-address";
                            description
                                "Multicast group membership information that joined on
                                 the host.";

                            leaf group-address {
                                type types-sros:ipv6-multicast-address;
                                description "Group address of multicast channel";
                            }

                            leaf group-type {
                                type types-igmp:learn-type;
                            }

                            leaf filter-mode {
                                type types-igmp:filter-mode;
                            }

                            leaf expiry-time {
                                type uint32;
                                units "seconds";
                                description "The time left before multicast group timeout.";
                            }

                            leaf up-time {
                                type uint32;
                                units "seconds";
                                description "The time elapsed since this entry was created.";
                            }

                            leaf v1-host-timer {
                                type uint32;
                                units "seconds";
                                description
                                    "The time remaining until the local router will assume that
                                     there are no longer any version 1 members.";
                            }

                            leaf mld-compatibility-mode {
                                type types-igmp:mld-version;
                                description "Compatibility with older version routers.";
                            }

                            leaf last-reporter {
                                type types-sros:ip-address;
                                description
                                    "The last host address which has sent the report to join
                                     the multicast group.";
                            }

                            list source {
                                key "source-address";
                                description
                                    "List of multicast source information of
                                     the multicast group.";

                                leaf source-address {
                                    type types-sros:ipv6-address;
                                    description "Source address of multicast channel.";
                                }

                                leaf source-type {
                                    type types-igmp:learn-type;
                                }

                                leaf forwarding-state {
                                    type types-igmp:forwarding-state;
                                    description "Traffic forwardeding state on this port.";
                                }

                                leaf expiry-time {
                                    type uint32;
                                    units "seconds";
                                    description "The time left before multicast group timeout.";
                                }

                                leaf up-time {
                                    type uint32;
                                    units "seconds";
                                    description "The time elapsed since this entry was created.";
                                }

                            } // list source

                        } // list group

                    } // list host

                } // list group-interface

                list forwarding-group-interface {
                    key "forwarding-service group-interface-name";
                    description "Enter the forwarding-group-interface list instance";

                    leaf forwarding-service {
                        type types-services:service-name;
                        description "Forwarding service for a subscriber interface in a retailer context";
                    }

                    leaf group-interface-name {
                        type leafref {
                            path "../../../../vprn[service-name=current()/../forwarding-service]/subscriber-interface/group-interface/group-interface-name";
                        }
                        description "Group interface name";
                    }

                    leaf oper-state {
                        type types-sros:oper-state;
                        description "The current operating state of the MLD protocol on this group interface.";
                    }

                    container mcac {
                        description "Enter the mcac context";

                        leaf in-use-mandatory-bandwidth {
                            type uint32;
                            units "kilobps";
                            description
                                "The in-use bandwidth for the mandatory channels for this
                                 protocol interface instance.";
                        }

                        leaf in-use-optional-bandwidth {
                            type uint32;
                            units "kilobps";
                            description
                                "The in-use bandwidth for the optional channels for this
                                 protocol interface instance.";
                        }

                        leaf available-mandatory-bandwidth {
                            type uint32;
                            units "kilobps";
                            description
                                "The pre-reserved bandwidth for the mandatory channels for
                                 this interface instance.";
                        }

                        leaf available-optional-bandwidth {
                            type uint32;
                            units "kilobps";
                            description "The available bandwidth for this interface instance.";
                        }

                        leaf values-in-transit {
                            type boolean;
                            description
                                "The operational (available and in-use mandatory/optional) value for the
                                 following objects is in transition due to configuration change:
                                 - available-mandatory-bandwidth
                                 - available-bandwidth
                                 - in-use-mandatory-bandwidth
                                 - in-use-optional-bandwidth.";
                        }

                    } // container mcac

                    list sap {
                        key "sap-id";
                        description "List of saps.";

                        leaf sap-id {
                            type types-sros:sap;
                            description "SAP identifier.";
                        }

                        leaf oper-state {
                            type types-sros:oper-state;
                            description "The current operating state of the MLD protocol on this interface.";
                        }

                        leaf oper-version {
                            type types-igmp:mld-version;
                            description "The operational version of the MLD which is running on this interface.";
                        }

                        leaf group-count {
                            type int32;
                            description "The number of multicast groups which have been learned on this interface.";
                        }

                        leaf next-general-query-time {
                            type uint32;
                            units "seconds";
                            description
                                "The time remaining before the general query is sent on this interface
                                 if this router is the querier.";
                        }

                        leaf maximum-groups-until-now {
                            type int32;
                            description "The highest value that 'group-count' had till now.";
                        }

                        container statistics {

                            container received {
                                description "Received message statistics.";

                                leaf general-queries {
                                    type yang:counter32;
                                    description "General Queries.";
                                }

                                leaf group-queries {
                                    type yang:counter32;
                                    description "Group Specific Queries.";
                                }

                                leaf group-source-queries {
                                    type yang:counter32;
                                    description "Group and Source Specific Queries.";
                                }

                                leaf v1-reports {
                                    type yang:counter32;
                                    description "V1 Reports.";
                                }

                                leaf v2-reports {
                                    type yang:counter32;
                                    description "V2 Reports.";
                                }

                                leaf leaves {
                                    type yang:counter32;
                                    description "Leaves.";
                                }

                                leaf drops {
                                    type yang:counter32;
                                    description "Total number of dropped packets.";
                                }

                            } // container received

                            container transmitted {
                                description "Transmit message statistics.";

                                leaf general-queries {
                                    type yang:counter32;
                                    description "General Queries.";
                                }

                                leaf group-queries {
                                    type yang:counter32;
                                    description "Group Specific Queries.";
                                }

                                leaf group-source-queries {
                                    type yang:counter32;
                                    description "Group and Source Specific Queries.";
                                }

                                leaf v1-reports {
                                    type yang:counter32;
                                    description "V1 Reports.";
                                }

                                leaf v2-reports {
                                    type yang:counter32;
                                    description "V2 Reports.";
                                }

                                leaf leaves {
                                    type yang:counter32;
                                    description "Leaves.";
                                }

                                leaf drops {
                                    type yang:counter32;
                                    description "Total number of dropped packets.";
                                }

                                leaf errors {
                                    type yang:counter32;
                                    description "Transmission Errors.";
                                }

                            } // container transmitted

                            container error {
                                description "Error message statistics.";

                                leaf bad-length {
                                    type yang:counter32;
                                    description "Bad length.";
                                }

                                leaf bad-ip-checksum {
                                    type yang:counter32;
                                    description "Bad Ip checksum.";
                                }

                                leaf unknown-type {
                                    type yang:counter32;
                                    description "Unknown type.";
                                }

                                leaf wrong-version {
                                    type yang:counter32;
                                    description "Wrong version.";
                                }

                                leaf import-policy-drops {
                                    type yang:counter32;
                                    description
                                        "Number of times we matched the host IP address or group or
                                         source addresses specified in the import policy.";
                                }

                                leaf missing-router-alert {
                                    type yang:counter32;
                                    description "Router alert flag is not set.";
                                }

                                leaf bad-encoding {
                                    type yang:counter32;
                                    description "Badly encoded.";
                                }

                                leaf local-scope {
                                    type yang:counter32;
                                    description "Link-local scope multicast group address.";
                                }

                                leaf reserved-scope {
                                    type yang:counter32;
                                    description "Reserved scope multicast group address.";
                                }

                                leaf mcac-policy-drops {
                                    type yang:counter32;
                                    description
                                        "Number of times a join is dropped because of applying a
                                         multicast CAC policy.";
                                }

                                leaf reached-maximum-number-groups {
                                    type yang:counter32;
                                    description
                                        "Number of times a join is dropped because we reached the maximum
                                         number of groups.";
                                }

                                leaf reached-maximum-number-group-sources {
                                    type yang:counter32;
                                    description
                                        "Number of times a join is dropped because we reached the maximum
                                         number group-source combinations.";
                                }

                                leaf reached-maximum-number-sources {
                                    type yang:counter32;
                                    description
                                        "Number of times a join is dropped because we reached the maximum
                                         number of sources per group.";
                                }

                                leaf out-of-memory-drops {
                                    type yang:counter32;
                                    description "Number of times a join is dropped because we ran out of memory.";
                                }

                                leaf mcs-failures {
                                    type yang:counter32;
                                    description "Number of times a group could not be synced through multi chassis synchronisation (MCS).";
                                }

                                leaf non-local {
                                    type yang:counter32;
                                    description "Non-local sender source IP address.";
                                }

                            } // container error

                        } // container statistics

                        list group {
                            key "group-address";
                            description
                                "Multicast group membership information that joined on
                                 the sap.";

                            leaf group-address {
                                type types-sros:ipv6-multicast-address;
                                description "Group address of multicast channel";
                            }

                            leaf group-type {
                                type types-igmp:learn-type;
                            }

                            leaf filter-mode {
                                type types-igmp:filter-mode;
                            }

                            leaf expiry-time {
                                type uint32;
                                units "seconds";
                                description "The time left before multicast group timeout.";
                            }

                            leaf up-time {
                                type uint32;
                                units "seconds";
                                description "The time elapsed since this entry was created.";
                            }

                            leaf v1-host-timer {
                                type uint32;
                                units "seconds";
                                description
                                    "The time remaining until the local router will assume that
                                     there are no longer any version 1 members.";
                            }

                            leaf mld-compatibility-mode {
                                type types-igmp:mld-version;
                                description "Compatibility with older version routers.";
                            }

                            leaf last-reporter {
                                type types-sros:ip-address;
                                description
                                    "The last host address which has sent the report to join
                                     the multicast group.";
                            }

                            list source {
                                key "source-address";
                                description
                                    "List of multicast source information of
                                     the multicast group.";

                                leaf source-address {
                                    type types-sros:ipv6-address;
                                    description "Source address of multicast channel.";
                                }

                                leaf source-type {
                                    type types-igmp:learn-type;
                                }

                                leaf forwarding-state {
                                    type types-igmp:forwarding-state;
                                    description "Traffic forwardeding state on this port.";
                                }

                                leaf expiry-time {
                                    type uint32;
                                    units "seconds";
                                    description "The time left before multicast group timeout.";
                                }

                                leaf up-time {
                                    type uint32;
                                    units "seconds";
                                    description "The time elapsed since this entry was created.";
                                }

                            } // list source

                        } // list group

                    } // list sap

                    list host {
                        key "ip-address mac-address pppoe-session-id";
                        description "List of hosts.";

                        leaf ip-address {
                            type types-sros:ipv6-address;
                            description "The IP address of this host.";
                        }

                        leaf mac-address {
                            type yang:mac-address;
                            description "The MAC address of this host.";
                        }

                        leaf pppoe-session-id {
                            type uint32;
                            description "The PPPoE session id of this host.";
                        }

                        leaf oper-state {
                            type types-sros:oper-state;
                            description "The current operating state of the MLD protocol on this interface.";
                        }

                        leaf oper-version {
                            type types-igmp:mld-version;
                            description "The operational version of the MLD which is running on this interface.";
                        }

                        leaf group-count {
                            type int32;
                            description "The number of multicast groups which have been learned on this interface.";
                        }

                        leaf next-general-query-time {
                            type uint32;
                            units "seconds";
                            description
                                "The time remaining before the general query is sent on this interface
                                 if this router is the querier.";
                        }

                        leaf maximum-groups-until-now {
                            type int32;
                            description "The highest value that 'group-count' had till now.";
                        }

                        leaf subscriber-id {
                            type types-sros:named-item;
                            description "The subscriber identification of this subscriber host.";
                        }

                        leaf bonding-context-id {
                            type types-submgt:bonding-context-id;
                            description "The bonding context identifier of the session of this host.";
                        }

                        leaf bonding-connection-index {
                            type types-submgt:bonding-connection-index;
                            description "The bonding connection index of the session of this host.";
                        }

                        leaf mld-policy {
                            type types-sros:named-item;
                            description "The mld-policy in use.";
                        }

                        container statistics {

                            container received {
                                description "Received message statistics.";

                                leaf general-queries {
                                    type yang:counter32;
                                    description "General Queries.";
                                }

                                leaf group-queries {
                                    type yang:counter32;
                                    description "Group Specific Queries.";
                                }

                                leaf group-source-queries {
                                    type yang:counter32;
                                    description "Group and Source Specific Queries.";
                                }

                                leaf v1-reports {
                                    type yang:counter32;
                                    description "V1 Reports.";
                                }

                                leaf v2-reports {
                                    type yang:counter32;
                                    description "V2 Reports.";
                                }

                                leaf leaves {
                                    type yang:counter32;
                                    description "Leaves.";
                                }

                                leaf drops {
                                    type yang:counter32;
                                    description "Total number of dropped packets.";
                                }

                            } // container received

                            container transmitted {
                                description "Transmit message statistics.";

                                leaf general-queries {
                                    type yang:counter32;
                                    description "General Queries.";
                                }

                                leaf group-queries {
                                    type yang:counter32;
                                    description "Group Specific Queries.";
                                }

                                leaf group-source-queries {
                                    type yang:counter32;
                                    description "Group and Source Specific Queries.";
                                }

                                leaf v1-reports {
                                    type yang:counter32;
                                    description "V1 Reports.";
                                }

                                leaf v2-reports {
                                    type yang:counter32;
                                    description "V2 Reports.";
                                }

                                leaf leaves {
                                    type yang:counter32;
                                    description "Leaves.";
                                }

                                leaf drops {
                                    type yang:counter32;
                                    description "Total number of dropped packets.";
                                }

                                leaf errors {
                                    type yang:counter32;
                                    description "Transmission Errors.";
                                }

                            } // container transmitted

                            container error {
                                description "Error message statistics.";

                                leaf bad-length {
                                    type yang:counter32;
                                    description "Bad length.";
                                }

                                leaf bad-ip-checksum {
                                    type yang:counter32;
                                    description "Bad Ip checksum.";
                                }

                                leaf unknown-type {
                                    type yang:counter32;
                                    description "Unknown type.";
                                }

                                leaf wrong-version {
                                    type yang:counter32;
                                    description "Wrong version.";
                                }

                                leaf import-policy-drops {
                                    type yang:counter32;
                                    description
                                        "Number of times we matched the host IP address or group or
                                         source addresses specified in the import policy.";
                                }

                                leaf missing-router-alert {
                                    type yang:counter32;
                                    description "Router alert flag is not set.";
                                }

                                leaf bad-encoding {
                                    type yang:counter32;
                                    description "Badly encoded.";
                                }

                                leaf local-scope {
                                    type yang:counter32;
                                    description "Link-local scope multicast group address.";
                                }

                                leaf reserved-scope {
                                    type yang:counter32;
                                    description "Reserved scope multicast group address.";
                                }

                                leaf mcac-policy-drops {
                                    type yang:counter32;
                                    description
                                        "Number of times a join is dropped because of applying a
                                         multicast CAC policy.";
                                }

                                leaf reached-maximum-number-groups {
                                    type yang:counter32;
                                    description
                                        "Number of times a join is dropped because we reached the maximum
                                         number of groups.";
                                }

                                leaf reached-maximum-number-group-sources {
                                    type yang:counter32;
                                    description
                                        "Number of times a join is dropped because we reached the maximum
                                         number group-source combinations.";
                                }

                                leaf reached-maximum-number-sources {
                                    type yang:counter32;
                                    description
                                        "Number of times a join is dropped because we reached the maximum
                                         number of sources per group.";
                                }

                                leaf out-of-memory-drops {
                                    type yang:counter32;
                                    description "Number of times a join is dropped because we ran out of memory.";
                                }

                                leaf mcs-failures {
                                    type yang:counter32;
                                    description "Number of times a group could not be synced through multi chassis synchronisation (MCS).";
                                }

                                leaf non-local {
                                    type yang:counter32;
                                    description "Non-local sender source IP address.";
                                }

                                leaf redirection-drops {
                                    type yang:counter32;
                                    description
                                        "Number of times a Group is dropped because of a failure
                                         while applying a redirection policy for this host.";
                                }

                            } // container error

                        } // container statistics

                        list group {
                            key "group-address";
                            description
                                "Multicast group membership information that joined on
                                 the host.";

                            leaf group-address {
                                type types-sros:ipv6-multicast-address;
                                description "Group address of multicast channel";
                            }

                            leaf group-type {
                                type types-igmp:learn-type;
                            }

                            leaf filter-mode {
                                type types-igmp:filter-mode;
                            }

                            leaf expiry-time {
                                type uint32;
                                units "seconds";
                                description "The time left before multicast group timeout.";
                            }

                            leaf up-time {
                                type uint32;
                                units "seconds";
                                description "The time elapsed since this entry was created.";
                            }

                            leaf v1-host-timer {
                                type uint32;
                                units "seconds";
                                description
                                    "The time remaining until the local router will assume that
                                     there are no longer any version 1 members.";
                            }

                            leaf mld-compatibility-mode {
                                type types-igmp:mld-version;
                                description "Compatibility with older version routers.";
                            }

                            leaf last-reporter {
                                type types-sros:ip-address;
                                description
                                    "The last host address which has sent the report to join
                                     the multicast group.";
                            }

                            list source {
                                key "source-address";
                                description
                                    "List of multicast source information of
                                     the multicast group.";

                                leaf source-address {
                                    type types-sros:ipv6-address;
                                    description "Source address of multicast channel.";
                                }

                                leaf source-type {
                                    type types-igmp:learn-type;
                                }

                                leaf forwarding-state {
                                    type types-igmp:forwarding-state;
                                    description "Traffic forwardeding state on this port.";
                                }

                                leaf expiry-time {
                                    type uint32;
                                    units "seconds";
                                    description "The time left before multicast group timeout.";
                                }

                                leaf up-time {
                                    type uint32;
                                    units "seconds";
                                    description "The time elapsed since this entry was created.";
                                }

                            } // list source

                        } // list group

                    } // list host

                } // list forwarding-group-interface

                list host {
                    key "ip-address mac-address pppoe-session-id";
                    description "List of subscriber management hosts.";

                    leaf ip-address {
                        type types-sros:ipv6-address;
                        description "The IP address of this host.";
                    }

                    leaf mac-address {
                        type yang:mac-address;
                        description "The MAC address of this host.";
                    }

                    leaf pppoe-session-id {
                        type uint32;
                        description "The PPPoE session id of this host.";
                    }

                    leaf group-interface-name {
                        type leafref {
                            path "../../group-interface/group-interface-name";
                        }
                        description "The group-interface this host belongs to.";
                    }

                    leaf forwarding-group-interface-service-name {
                        type leafref {
                            path "../../forwarding-group-interface/forwarding-service";
                        }
                        description "The service-name of the forwarding-group-interface this host belongs to.";
                    }

                    leaf forwarding-group-interface-name {
                        type leafref {
                            path "../../forwarding-group-interface/group-interface-name";
                        }
                        description "The name of the forwarding-group-interface this host belongs to.";
                    }

                } // list host

                list ipsec-static-tunnel {
                    key "tunnel-name sa-id";
                    description "MLD IPsec Static tunnel parameters.";

                    leaf tunnel-name {
                        type types-sros:named-item;
                        description "IPsec tunnel name.";
                    }

                    leaf sa-id {
                        type uint32 {
                            range "1..16";
                        }
                        description "Security Association Id";
                    }

                    leaf oper-state {
                        type types-sros:oper-state;
                        description "The current operating state of the MLD protocol on this interface.";
                    }

                    leaf oper-version {
                        type types-igmp:mld-version;
                        description "The operational version of the MLD which is running on this interface.";
                    }

                    leaf group-count {
                        type int32;
                        description "The number of multicast groups which have been learned on this interface.";
                    }

                    leaf next-general-query-time {
                        type uint32;
                        units "seconds";
                        description
                            "The time remaining before the general query is sent on this interface
                             if this router is the querier.";
                    }

                    container statistics {

                        container received {
                            description "Received message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                        } // container received

                        container transmitted {
                            description "Transmit message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                            leaf errors {
                                type yang:counter32;
                                description "Transmission Errors.";
                            }

                        } // container transmitted

                        container error {
                            description "Error message statistics.";

                            leaf bad-length {
                                type yang:counter32;
                                description "Bad length.";
                            }

                            leaf bad-ip-checksum {
                                type yang:counter32;
                                description "Bad Ip checksum.";
                            }

                            leaf unknown-type {
                                type yang:counter32;
                                description "Unknown type.";
                            }

                            leaf wrong-version {
                                type yang:counter32;
                                description "Wrong version.";
                            }

                            leaf import-policy-drops {
                                type yang:counter32;
                                description
                                    "Number of times we matched the host IP address or group or
                                     source addresses specified in the import policy.";
                            }

                            leaf missing-router-alert {
                                type yang:counter32;
                                description "Router alert flag is not set.";
                            }

                            leaf bad-encoding {
                                type yang:counter32;
                                description "Badly encoded.";
                            }

                            leaf local-scope {
                                type yang:counter32;
                                description "Link-local scope multicast group address.";
                            }

                            leaf mcac-policy-drops {
                                type yang:counter32;
                                description
                                    "Number of times a join is dropped because of applying a
                                     multicast CAC policy.";
                            }

                            leaf reached-maximum-number-groups {
                                type yang:counter32;
                                description
                                    "Number of times a join is dropped because we reached the maximum
                                     number of groups.";
                            }

                            leaf reached-maximum-number-group-sources {
                                type yang:counter32;
                                description
                                    "Number of times a join is dropped because we reached the maximum
                                     number group-source combinations.";
                            }

                            leaf reached-maximum-number-sources {
                                type yang:counter32;
                                description
                                    "Number of times a join is dropped because we reached the maximum
                                     number of sources per group.";
                            }

                            leaf out-of-memory-drops {
                                type yang:counter32;
                                description "Number of times a join is dropped because we ran out of memory.";
                            }

                            leaf mcs-failures {
                                type yang:counter32;
                                description "Number of times a group could not be synced through multi chassis synchronisation (MCS).";
                            }

                            leaf non-local {
                                type yang:counter32;
                                description "Non-local sender source IP address.";
                            }

                        } // container error

                    } // container statistics

                    list group {
                        key "group-address";
                        description "Multicast group membership information that joined on the tunnel.";

                        leaf group-address {
                            type types-sros:ipv6-multicast-address;
                            description "Group address of multicast channel";
                        }

                        leaf group-type {
                            type types-igmp:learn-type;
                        }

                        leaf filter-mode {
                            type types-igmp:filter-mode;
                        }

                        leaf expiry-time {
                            type uint32;
                            units "seconds";
                            description "The time left before multicast group timeout.";
                        }

                        leaf up-time {
                            type uint32;
                            units "seconds";
                            description "The time elapsed since this entry was created.";
                        }

                        leaf v1-host-timer {
                            type uint32;
                            units "seconds";
                            description
                                "The time remaining until the local router will assume that
                                 there are no longer any version 1 members.";
                        }

                        leaf v2-host-timer {
                            type uint32;
                            units "seconds";
                            description
                                "The time remaining until the local router will assume that
                                 there are no longer any version 2 members.";
                        }

                        leaf igmp-compatibility-mode {
                            type types-igmp:igmp-version;
                            description "Compatibility with older version routers.";
                        }

                        leaf last-reporter {
                            type types-sros:ip-address;
                            description
                                "The last host address which has sent the report to join
                                 the multicast group.";
                        }

                        list source {
                            key "source-address";
                            description "List of multicast source information of the multicast group.";

                            leaf source-address {
                                type types-sros:ipv6-address;
                                description "Source address of multicast channel.";
                            }

                            leaf source-type {
                                type types-igmp:learn-type;
                            }

                            leaf forwarding-state {
                                type types-igmp:forwarding-state;
                                description "Traffic forwardeding state on this port.";
                            }

                            leaf expiry-time {
                                type uint32;
                                units "seconds";
                                description "The time left before multicast group timeout.";
                            }

                            leaf up-time {
                                type uint32;
                                units "seconds";
                                description "The time elapsed since this entry was created.";
                            }

                        } // list source

                    } // list group

                } // list ipsec-static-tunnel

                list ipsec-ru-tunnel {
                    key "gateway-name sap-address sap-port sa-id";
                    description "MLD IPsec Remote-User tunnel parameters.";

                    leaf gateway-name {
                        type types-sros:named-item;
                        description "IPsec gateway name.";
                    }

                    leaf sap-address {
                        type types-sros:ip-address;
                        description "The address of the SAP IPsec gateway to the tunnel.";
                    }

                    leaf sap-port {
                        type types-sros:tcp-udp-port;
                        description "The UDP port of the SAP IPsec gateway to the tunnel.";
                    }

                    leaf sa-id {
                        type uint32 {
                            range "1..16";
                        }
                        description "SA Id";
                    }

                    leaf oper-state {
                        type types-sros:oper-state;
                        description "The current operating state of the MLD protocol on this interface.";
                    }

                    leaf oper-version {
                        type types-igmp:mld-version;
                        description "The operational version of the MLD which is running on this interface.";
                    }

                    leaf group-count {
                        type int32;
                        description "The number of multicast groups which have been learned on this interface.";
                    }

                    leaf next-general-query-time {
                        type uint32;
                        units "seconds";
                        description
                            "The time remaining before the general query is sent on this interface
                             if this router is the querier.";
                    }

                    container statistics {

                        container received {
                            description "Received message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                        } // container received

                        container transmitted {
                            description "Transmit message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                            leaf errors {
                                type yang:counter32;
                                description "Transmission Errors.";
                            }

                        } // container transmitted

                        container error {
                            description "Error message statistics.";

                            leaf bad-length {
                                type yang:counter32;
                                description "Bad length.";
                            }

                            leaf bad-ip-checksum {
                                type yang:counter32;
                                description "Bad Ip checksum.";
                            }

                            leaf unknown-type {
                                type yang:counter32;
                                description "Unknown type.";
                            }

                            leaf wrong-version {
                                type yang:counter32;
                                description "Wrong version.";
                            }

                            leaf import-policy-drops {
                                type yang:counter32;
                                description
                                    "Number of times we matched the host IP address or group or
                                     source addresses specified in the import policy.";
                            }

                            leaf missing-router-alert {
                                type yang:counter32;
                                description "Router alert flag is not set.";
                            }

                            leaf bad-encoding {
                                type yang:counter32;
                                description "Badly encoded.";
                            }

                            leaf local-scope {
                                type yang:counter32;
                                description "Link-local scope multicast group address.";
                            }

                            leaf mcac-policy-drops {
                                type yang:counter32;
                                description
                                    "Number of times a join is dropped because of applying a
                                     multicast CAC policy.";
                            }

                            leaf reached-maximum-number-groups {
                                type yang:counter32;
                                description
                                    "Number of times a join is dropped because we reached the maximum
                                     number of groups.";
                            }

                            leaf reached-maximum-number-group-sources {
                                type yang:counter32;
                                description
                                    "Number of times a join is dropped because we reached the maximum
                                     number group-source combinations.";
                            }

                            leaf reached-maximum-number-sources {
                                type yang:counter32;
                                description
                                    "Number of times a join is dropped because we reached the maximum
                                     number of sources per group.";
                            }

                            leaf out-of-memory-drops {
                                type yang:counter32;
                                description "Number of times a join is dropped because we ran out of memory.";
                            }

                            leaf mcs-failures {
                                type yang:counter32;
                                description "Number of times a group could not be synced through multi chassis synchronisation (MCS).";
                            }

                            leaf non-local {
                                type yang:counter32;
                                description "Non-local sender source IP address.";
                            }

                        } // container error

                    } // container statistics

                    list group {
                        key "group-address";
                        description "Multicast group membership information that joined on the tunnel.";

                        leaf group-address {
                            type types-sros:ipv6-multicast-address;
                            description "Group address of multicast channel";
                        }

                        leaf group-type {
                            type types-igmp:learn-type;
                        }

                        leaf filter-mode {
                            type types-igmp:filter-mode;
                        }

                        leaf expiry-time {
                            type uint32;
                            units "seconds";
                            description "The time left before multicast group timeout.";
                        }

                        leaf up-time {
                            type uint32;
                            units "seconds";
                            description "The time elapsed since this entry was created.";
                        }

                        leaf v1-host-timer {
                            type uint32;
                            units "seconds";
                            description
                                "The time remaining until the local router will assume that
                                 there are no longer any version 1 members.";
                        }

                        leaf v2-host-timer {
                            type uint32;
                            units "seconds";
                            description
                                "The time remaining until the local router will assume that
                                 there are no longer any version 2 members.";
                        }

                        leaf igmp-compatibility-mode {
                            type types-igmp:igmp-version;
                            description "Compatibility with older version routers.";
                        }

                        leaf last-reporter {
                            type types-sros:ip-address;
                            description
                                "The last host address which has sent the report to join
                                 the multicast group.";
                        }

                        list source {
                            key "source-address";
                            description "List of multicast source information of the multicast group.";

                            leaf source-address {
                                type types-sros:ipv6-address;
                                description "Source address of multicast channel.";
                            }

                            leaf source-type {
                                type types-igmp:learn-type;
                            }

                            leaf forwarding-state {
                                type types-igmp:forwarding-state;
                                description "Traffic forwardeding state on this port.";
                            }

                            leaf expiry-time {
                                type uint32;
                                units "seconds";
                                description "The time left before multicast group timeout.";
                            }

                            leaf up-time {
                                type uint32;
                                units "seconds";
                                description "The time elapsed since this entry was created.";
                            }

                        } // list source

                    } // list group

                } // list ipsec-ru-tunnel

            } // container mld

            container pim {
                description "Enter the pim context";

                leaf maximum-mdts {
                    type int32;
                    description
                        "Maximum number of Multicast Distribution Trees (MDTs) that can
                         be configured on the system.";
                }

                leaf multistream-spmsi {
                    type boolean;
                    description
                        "The value of this object specifies whether multistream SPMSI is
                         configured on this router.";
                }

                leaf oper-state {
                    type types-sros:oper-state;
                    description
                        "The value of this object indicates the operational
                         state of the PIM protocol.";
                }

                leaf mc-ecmp-last-rebalance-time {
                    type types-sros:date-time;
                    description
                        "The value of this object indicates the time when the last re-balancing
                         occurred if the value of mc-ecmp-rebalance-inprogress is 'false'.";
                }

                leaf mc-ecmp-next-balance-time {
                    type uint32;
                    units "seconds";
                    description
                        "The value of this object indicates how much time is remaining until
                         the next rebalance would occur.";
                }

                leaf mc-ecmp-rebalance-inprogress {
                    type boolean;
                    description "Whether or not multicast ECMP re-balancing is currently in progress.";
                }

                leaf mc-ecmp-rebalance-type {
                    type enumeration {
                        enum "triggered"                    { value 1; }
                        enum "operator-forced"              { value 2; }
                    }
                    description "The value of this object indicates the type of ECMP rebalance.";
                }

                container ipv4 {
                    description "Enter the ipv4 context";

                    list sg {
                        key "group-address source-address";
                        description
                            "Each entry represents a source address from which receivers are
                             interested or not interested in receiving multicast traffic.";

                        leaf group-address {
                            type types-sros:ipv4-multicast-address;
                            description
                                "The IP multicast group address for which this entry contains information.
                                 If the source-type is 'starStarRP', the value of this object will
                                 be zero and source-address will contain the address of the RP.";
                        }

                        leaf source-address {
                            type types-sros:ipv4-address;
                            description
                                "The source address for which this entry contains information.
                                 If source-type is 'starG', the value of this object will be zero.
                                 If source-type is 'starstarRP', the value of this object will be address of the RP.";
                        }

                        leaf source-type {
                            type enumeration {
                                enum "star-star-rp"                 { value 0; }
                                enum "star-g"                       { value 1; }
                                enum "sg"                           { value 2; }
                            }
                            description "The type of this entry.";
                        }

                        leaf sg-state {
                            type enumeration {
                                enum "none"                         { value 0; }
                                enum "active"                       { value 1; }
                                enum "standby"                      { value 2; }
                            }
                            description "The current state of the (S,G).";
                        }

                        leaf rp-address {
                            type types-sros:ip-address;
                            description "The address of the Rendezvous Point(RP).";
                        }

                        leaf advertising-router {
                            type types-sros:ip-address;
                            description "The router address that advertised the route to the source indicated by source-address.";
                        }

                        leaf downstream-rpfv-neighbor {
                            type types-sros:ip-address;
                            description "The address of the downstream RPF vector neighbor.";
                        }

                        leaf downstream-rpfv-type {
                            type types-pim:rpfv-type;
                            description "The downstream RPF vector type.";
                        }

                        leaf downstream-rpfv-rd {
                            type types-services:state-vpn-rd;
                            description "The downstream RPF vector Route Distinguisher.";
                        }

                        leaf downstream-rpfv-proxy {
                            type types-sros:ip-address;
                            description "The address of the downstream RPF vector proxy.";
                        }

                        leaf upstream-rpfv-neighbor {
                            type types-sros:ip-address;
                            description "The address of the upstream RPF vector neighbor.";
                        }

                        leaf rpfv-flags {
                            type bits {
                                bit upstream-neighbor-no-join-attribute { position 0; }
                            }
                            description
                                "The state of the rpf-vectors.

                                 When the bit 'upstream-neighbor-no-join-attribute' is set, it
                                 indicates that the upstream neighbor towards the rpf-vector
                                 proxy does not support join-attributes.";
                        }

                        leaf upstream-rpfv-type {
                            type types-pim:rpfv-type;
                            description "The upstream RPF vector type.";
                        }

                        leaf upstream-rpfv-rd {
                            type types-services:state-vpn-rd;
                            description "The upstream RPF vector Route Distinguisher.";
                        }

                        leaf upstream-rpfv-proxy {
                            type types-sros:ip-address;
                            description "The address of the upstream RPF vector proxy.";
                        }

                        leaf source-flags {
                            type bits {
                                bit spt-bit                        { position 0; }
                                bit rpt-prune-desired              { position 1; }
                            }
                            description
                                "The information about the state of the entry

                                 This object is applicable only for (S,G) entries,i.e., when
                                 source-type is 'sg'.

                                 The (S,G) 'spt-bit' is used to distinguish whether to forward on
                                 (*,*,RP) or (*,G) or on (S,G) state. It is updated when the (S,G)
                                 data comes on the RPF interface towards the source.
                                 'rpt-prune-desired' is set according to the PruneDesired(S,G,rpt)
                                 algorithm.";
                        }

                        leaf mode {
                            type enumeration {
                                enum "none"                         { value 0; }
                                enum "sparse"                       { value 1; }
                                enum "dense"                        { value 2; }
                            }
                            description "The mode of operation for the (S,G).";
                        }

                        leaf mrib-nh-address {
                            type types-sros:ip-address-with-zone;
                            description "The next hop address towards the RP.";
                        }

                        leaf standby-rpf-neighbor-address {
                            type types-sros:ip-address;
                            description
                                "The address of the secondary RPF neighbor

                                 The value of this object is applicable only when the value of the
                                 object 'configure service vprn mvpn umh-selection' is set to 'tunnel-status'
                                 indicating that the MVPN is configured with source redundancy.

                                 When MVPN is configured with source redundancy, MVPN is capable of
                                 receiving traffic from two different PE's for the same source.";
                        }

                        leaf mrib-source-flags {
                            type types-pim:mrib-source-flags;
                            description
                                "The MRIB information about the source. If the entry is of type 'starG'
                                 or 'starStarRP', it will contain information about the RP for this group.";
                        }

                        leaf standby-mrib-source-flags {
                            type types-pim:mrib-source-flags;
                            description
                                "The MRIB information about the source reachable through the standby RPF
                                 interface.

                                 This object is applicable only for (S,G) entries,i.e., when
                                 source-type is 'sg'.";
                        }

                        leaf keepalive-timer {
                            type uint32;
                            units "seconds";
                            description
                                "Is applicable only for (S,G) entries. The (S,G) Keepalive Timer is updated by
                                 data being forwarded using this (S,G) forwarding state. It is used to keep (S,G)
                                 state alive in the absence of explicit (S,G) Joins.";
                        }

                        leaf prune-limit-timer {
                            type uint32;
                            units "seconds";
                            description "The time until which no prunes will be sent upstream.";
                        }

                        leaf graft-retry-timer {
                            type uint32;
                            units "seconds";
                            description
                                "The time interval between which two grafts are sent upstream and no ack is
                                 received from the upstream router.";
                        }

                        leaf up-time {
                            type uint32;
                            units "seconds";
                            description "The time since this source group entry got created.";
                        }

                        leaf resolved-by {
                            type enumeration {
                                enum "none"                         { value 0; }
                                enum "multicast-route-table"        { value 1; }
                                enum "unicast-route-table"          { value 2; }
                            }
                            description
                                "Which unicast routing table was used to resolve this source group entry.

                                 The value of this object will be 'multicastRouteTable' if the
                                 source or Rendezvous Point (RP) is resolved by the multicast-unicast
                                 route table. The value of this object will be 'unicastRouteTable' if
                                 the source or Rendezvous Point (RP) is resolved by the unicast
                                 route table. The value will be 'none' if the source or RP is
                                 unresolved.";
                        }

                        leaf upstream-jp-state {
                            type enumeration {
                                enum "not-joined"                   { value 0; }
                                enum "joined"                       { value 1; }
                                enum "pruned"                       { value 2; }
                                enum "forwarding"                   { value 3; }
                                enum "ack-pending"                  { value 4; }
                            }
                            description
                                "The upstream Join-Prune state. This is a result of sending PIM Join-Prune
                                 messages towards the source or the RP.";
                        }

                        leaf upstream-jp-timer {
                            type uint32;
                            units "seconds";
                            description
                                "The time remaining before the router sends another Join message to it's
                                 upstream neighbor.";
                        }

                        leaf upstream-rpt-jp-state {
                            type enumeration {
                                enum "not-joined-star-g"            { value 0; }
                                enum "not-pruned"                   { value 1; }
                                enum "pruned"                       { value 2; }
                            }
                            description
                                "The upstream RPT Join-Prune state. (S,G,rpt) Joins and Prunes are (S,G) Joins or
                                 Prunes sent on the RP tree with the RPT bit set, either to modify the results of
                                 (*,G) Joins, or to override the behavior of other upstream LAN peers.";
                        }

                        leaf upstream-rpt-override-timer {
                            type uint32;
                            units "seconds";
                            description
                                "The delay to triggered Join(S,G,rpt) messages to prevent implosions of triggered
                                 messages.

                                 If non-zero, it means that the router was in 'not-pruned' state and it saw a
                                 Prune(S,G,rpt) message being sent to RPF'(S,G,rpt).

                                 If the router sees a Join(S,G,rpt) override message being sent by
                                 some other router on the LAN while the timer is still non-zero,
                                 it simply cancels the override timer. If it does not see a
                                 Join(S,G,rpt) message, then on expiry of the override timer, it
                                 sends it's own Join(S,G,rpt) message to RPF'(S,G,rpt). A similar
                                 scenario exists when RPF'(S,G,rpt) changes to become equal to
                                 RPF'(*,G).";
                        }

                        leaf standby-upstream-jp-state {
                            type enumeration {
                                enum "not-joined"                   { value 0; }
                                enum "joined"                       { value 1; }
                            }
                            description
                                "The standby RPF Join-Prune state.

                                 This object is applicable only for (S,G) entries,i.e., when
                                 source-type is 'sg'.";
                        }

                        leaf standby-upstream-jp-timer {
                            type uint32;
                            units "seconds";
                            description
                                "The time remaining before the router sends another Join message to it's
                                 upstream neighbor reachable through the standby RPF interface.

                                 This object is applicable only for (S,G) entries,i.e., when
                                 source-type is 'sg'.";
                        }

                        leaf register-state {
                            type enumeration {
                                enum "no-info"                      { value 0; }
                                enum "join"                         { value 1; }
                                enum "join-pending"                 { value 2; }
                                enum "prune"                        { value 3; }
                                enum "null-join"                    { value 4; }
                            }
                            description
                                "The register state. The register state is kept at the source DR. When the host
                                 starts sending multicast packets and if there are no entries
                                 programmed for that group, the source DR sends a Register packet
                                 to the RP(G). Register state transition happen based on the register
                                 stop timer and the response received from the RP.";
                        }

                        leaf register-stop-timer {
                            type uint32;
                            units "seconds";
                            description
                                "The time remaining before the register-state might transition
                                 to a different state. This timer has a non-zero value when the
                                 value of register-state is not 'noInfo'.";
                        }

                        leaf register-from-anycast-rp {
                            type boolean;
                            description
                                "Whether a register message for this source  group combination
                                 was received from the anycast RP and not from the designated
                                 router connected to the source. It  is not applicable when the value of
                                 source-type is starStarRP or starG.";
                        }

                        leaf rpf-neighbor-address {
                            type types-sros:ip-address;
                            description "The address of the RPF neighbor.";
                        }

                        leaf rpf-neighbor-interface-name {
                            type string;
                            description "The router's interface index on which the RPF neighbor exists.";
                        }

                        leaf standby-rpf-neighbor-interface-name {
                            type string;
                            description
                                "The router's interface index on which the secondary RPF neighbor exists.

                                 The value of this object is applicable only when the value of the
                                 object 'configure service vprn mvpn umh-selection' is set to 'tunnel-status'
                                 indicating that the MVPN is configured with source redundancy.";
                        }

                        leaf spmsi-rpf-neighbor-interface-name {
                            type string;
                            description
                                "In an MVPN scenario: The router's SPMSI interface index, if any, on which the RPF
                                 neighbor exists.";
                        }

                        leaf inherited-outgoing-interface-count {
                            type yang:gauge32;
                            description
                                "The number of interfaces in the inherited outgoing interface list. An 'inherited'
                                 list inherits state from other types.";
                        }

                        leaf s-g-rpt-prune-interface-count {
                            type yang:gauge32;
                            description "The number of interfaces on which the router received (S,G,Rpt) prunes.";
                        }

                        leaf spt-switchover-threshold {
                            type uint32;
                            units "kilobps";
                            description
                                "The configured threshold in kilobits per second(kbps) for the group to which
                                 this (S,G) belongs.  For a group G configured with a threshold,
                                 switchover to SPT for an (S,G) is attempted only if the (S,G)'s rate
                                 exceeds this configured threshold.";
                        }

                        leaf ecmp-optional-threshold {
                            type uint32 {
                                range "0..7";
                            }
                            description "The optional threshold value for ECMP balancing.";
                        }

                        leaf administrative-bandwidth {
                            type yang:gauge32 {
                                range "0..40000000";
                            }
                            units "kilobps";
                            description
                                "The administrative bandwidth in kilobits per second(kbps) for the group to which
                                 this (S,G) belongs.";
                        }

                        leaf rpt-rpf-neighbor-address {
                            type types-sros:ip-address;
                            description "The address of the RPF neighbor on the RPT.";
                        }

                        leaf immediate-outgoing-interface-count {
                            type yang:gauge32;
                            description
                                "The number of interfaces in the immediate outgoing interface list. An outgoing
                                 list can be 'immediate' if it is built directly from the state of
                                 the relevant type as indicated by source-type.";
                        }

                        leaf inherited-rpt-outgoing-interface-count {
                            type yang:gauge32;
                            description "The number of interfaces in the inherited outgoing interface list for (S,G,Rpt).";
                        }

                        leaf local-rx-include-interface-count {
                            type yang:gauge32;
                            description
                                "The number of interfaces in the local membership include interface list. Local
                                 membership is the result of the local membership mechanism (MLD)
                                 running on a interface. Include list contains interfaces which are
                                 interested in receiving multicast traffic for this source group entry.";
                        }

                        leaf local-rx-exclude-interface-count {
                            type yang:gauge32;
                            description
                                "The number of interfaces in the local membership exclude interface list. Local
                                 membership is the result of the local membership mechanism (MLD)
                                 running on the interface. Exclude list contains interfaces which are
                                 not interested in receiving multicast traffic for this source group
                                 entry.";
                        }

                        leaf join-or-prune-interface-count {
                            type yang:gauge32;
                            description
                                "The number of interfaces on which the router received a Join or Prune message for
                                 this source group combination.";
                        }

                        leaf lost-assert-interface-count {
                            type yang:gauge32;
                            description
                                "The number of interfaces on which the router lost assert for this source group
                                 combination.";
                        }

                        leaf current-forwarding-rate {
                            type yang:counter64;
                            units "bps";
                            description
                                "The current forwarding rate being used by a source group(S,G) entry or
                                 (*,G) entry, where * means any source entry, for the traffic in bits
                                 per second(bps). This forwarding rate is calculated before ingress
                                 QoS policing or shaping is applied.";
                        }

                        list group-interface {
                            key "sap forwarding-service group-interface-name";
                            description "List of the PIM enabled group-interfaces for an entry in the sg list.";

                            leaf sap {
                                type types-sros:sap;
                                description "SAP identifier.";
                            }

                            leaf forwarding-service {
                                type types-services:service-name;
                                description
                                    "Specifies the forwarding service ID for a group-interface in a retailer
                                     context.";
                            }

                            leaf group-interface-name {
                                type leafref {
                                    path "../../../../../interface/interface-name";
                                }
                                description
                                    "The unique value which identifies this group-interface of this virtual
                                     router in the system. This field provides an identifier for
                                     virtual router interfaces similar to the ifIndex values used in the
                                     mib-2 interfaces table for physical interfaces.

                                     The values can be reused for different virtual routers, but are unique within
                                     those entries with the same vrtr-id.

                                     The value for each virtual interface must remain constant at least from
                                     one re-initialization of the system management processor to the next.";
                            }

                            leaf list-flags {
                                type types-pim:sg-flags;
                                description "The different lists that this group-interface belongs to.";
                            }

                        } // list group-interface

                        list host {
                            key "host-address";
                            description "List of PIM enabled hosts and their states for each entry in the sg list.";

                            leaf host-address {
                                type types-sros:ipv4-unicast-address;
                                description
                                    "The IP multicast host address for which this entry contains information.
                                     If the ../type is 'star-star-rp', the value of this object will
                                     be zero and host-address will contain the address of the RP.";
                            }

                            leaf host-flags {
                                type types-pim:sg-flags;
                                description "The different lists that this host belongs to.";
                            }

                        } // list host

                        list interface {
                            key "interface-name";
                            description "List of the PIM enabled interfaces for an entry in sg list.";

                            leaf interface-name {
                                type types-sros:interface-name;
                                description "Router interface name.";
                            }

                            leaf interface-flags {
                                type types-pim:sg-flags;
                                description "Set of lists to which this interface belongs";
                            }

                            leaf spmsi-interface-name {
                                type string;
                                description
                                    "In an MVPN scenario: The router's SPMSI interface index, if any, corresponding to
                                     the outgoing IPMSI interface.";
                            }

                        } // list interface

                        container statistics {
                            description "Statistics for the entries in the sg list collected by the forwarding engine.";

                            leaf forwarded-packets {
                                type yang:counter64;
                                description
                                    "The number of multicast packets that were forwarded to the interfaces in the
                                     outgoing interface list. 'display router/(service vprn) pim ipv4/6 sg interface' lists all the
                                     interfaces in the outgoing interface list.";
                            }

                            leaf discarded-packets {
                                type yang:counter64;
                                description
                                    "The number of multicast packets that matched this source group entry but were
                                     discarded. For (S,G) entries, if the traffic is getting forwarded on
                                     the SPT, the packets arriving from the RPT will be discarded.";
                            }

                            leaf rpf-mismatches {
                                type yang:counter64;
                                description
                                    "The number of multicast packets that matched this source group entry
                                     but they did not arrive on the interface indicated by
                                     'display router/(service vprn) pim ipv4/6 sg rpf-neighbor-interface-name'.";
                            }

                            leaf forwarded-octets {
                                type yang:counter64;
                                description
                                    "The number of multicast octets that were forwarded to the interfaces in the
                                     outgoing interface list. 'display router/(service vprn) pim ipv4/6 sg interface' lists all the
                                     interfaces in the outgoing interface list.";
                            }

                        } // container statistics

                        list multicast-management-operational-data {
                            key "chassis-number slot-number fp-number";
                            description "operational data.";

                            leaf chassis-number {
                                type uint32;
                                description "The unique index identifying this physical chassis.";
                            }

                            leaf slot-number {
                                type uint32;
                                description
                                    "The unique value which identifies the IOM slot within a
                                     chassis in the system.";
                            }

                            leaf fp-number {
                                type uint32;
                                description "Forwarding plane within a specific IOM card";
                            }

                            leaf bandwith {
                                type yang:gauge32;
                                units "kilobps";
                                description "Current bandwidth";
                            }

                            leaf current-path {
                                type enumeration {
                                    enum "none"                         { value 0; }
                                    enum "primary"                      { value 1; }
                                    enum "secondary"                    { value 2; }
                                    enum "ancillary"                    { value 3; }
                                    enum "blackhole"                    { value 4; }
                                }
                                description "Explicit sf path.";
                            }

                            leaf explicit-path {
                                type boolean;
                                description "???";
                            }

                            leaf admin-bw {
                                type yang:gauge32;
                                description "Admin bandwidth.";
                            }

                            leaf preference {
                                type yang:gauge32;
                                description "Preference level.";
                            }

                            leaf blackholed {
                                type boolean;
                                description "In black-hole state";
                            }

                            leaf blackhole-rate {
                                type yang:gauge32;
                                description "The current rate at which this channel will be placed in black-hole state";
                            }

                            leaf highest-bw {
                                type yang:gauge32;
                                description "The highest multicast bandwidth that has been accounted.";
                            }

                            leaf second-highest-bw {
                                type yang:gauge32;
                                description "The second highest multicast bandwidth that has been accounted.";
                            }

                            leaf expiry-time {
                                type uint32;
                                units "seconds";
                                description "Remaining time before the bandwidth update timer on the FP expires";
                            }

                            leaf plane {
                                type uint32;
                                description "Forwarding plane";
                            }

                        } // list multicast-management-operational-data

                    } // list sg

                    container statistics {
                        description "PIM statistics for a particular PIM instance.";

                        leaf tx-registers {
                            type yang:counter32;
                            description "The number of PIM Register messages transmitted by this instance.";
                        }

                        leaf tx-register-errors {
                            type yang:counter32;
                            description
                                "The number of the times there was an error while transmitting PIM
                                 Register messages by this instance.";
                        }

                        leaf tx-null-registers {
                            type yang:counter32;
                            description "The number of PIM Null Register messages transmitted by this instance.";
                        }

                        leaf rx-candidate-rp-advertisements {
                            type yang:counter32;
                            description "The number of PIM Candidate-RP Advertisements (C-RP-Adv) received by this instance.";
                        }

                        leaf tx-candidate-rp-advertisements {
                            type yang:counter32;
                            description
                                "The number of PIM Candidate-RP Advertisements (C-RP-Adv) transmitted by this router
                                 instance.";
                        }

                        leaf rx-candidate-rp-advertisement-drops {
                            type yang:counter32;
                            description
                                "The number of PIM Candidate-RP Advertisements (C-RP-Adv) received by this instance,
                                 but were dropped.";
                        }

                        leaf tx-candidate-rp-advertisement-errors {
                            type yang:counter32;
                            description "The number of errors while transmitting PIM Candidate-RP Advertisements (C-RP-Adv).";
                        }

                        leaf forwarded-candidate-rp-advertisements {
                            type yang:counter32;
                            description
                                "The number of Candidate-RP Advertisements(C-RP-Adv) that were forwarded by the
                                 router. C-RP-Adv's are forwarded when the received advertisement
                                 has a router alert set and the destination address is not the
                                 router's local address.";
                        }

                        leaf forwarded-candidate-rp-advertisement-drops {
                            type yang:counter32;
                            description
                                "The number of times the Candidate-RP Advertisements(C-RP-Adv) could not be forwarded
                                 by the router.";
                        }

                        leaf tx-mdt-join-tlvs {
                            type yang:counter32;
                            description "The number of times MDT Join TLV were transmitted.";
                        }

                        leaf rx-mdt-join-tlvs {
                            type yang:counter32;
                            description "The number of times MDT Join TLV were received.";
                        }

                        leaf tx-mdt-join-tlv-errors {
                            type yang:counter32;
                            description "The number of times MDT Join TLV could not be transmitted.";
                        }

                        leaf rx-mdt-join-tlv-errors {
                            type yang:counter32;
                            description
                                "The number of times MDT Join TLVs were dropped due to errors in the
                                 received TLV.";
                        }

                        leaf tx-spmsi-limit-hits {
                            type yang:counter32;
                            description
                                "The number of times the switch from ipmsi to S-PMSI is failed because of reaching the
                                 maximum S-PMSI limit configured in
                                 TIMETRA-VRTR-MIB::vRtrMvpnSpmsiMaxLimit.";
                        }

                        leaf p2mp-pmsi-create-fails {
                            type yang:counter32;
                            description "The number of times a P2MP PMSI tunnel creation has failed.";
                        }

                        leaf p2mp-pmsi-request-fails {
                            type yang:counter32;
                            description "The number of times a P2MP PMSI tunnel request has failed.";
                        }

                        leaf rx-control-pdu-interface-drops {
                            type yang:counter32;
                            description
                                "The number of control PDU drops on an interface which is operationally down or on an
                                 interface on which PIM is not enabled.";
                        }

                        leaf active-tx-s-pmsis {
                            type yang:gauge32;
                            description
                                "The number of active MDTs on which the PE is forwarding packets. This object is
                                 applicable to VPRNs only.";
                        }

                        leaf active-tx-receiver-threshold-s-pmsis {
                            type yang:counter32;
                            description
                                "The number of active MDTs on which the PE is forwarding packets. This S-PMSI is
                                 threshold controlled.";
                        }

                        leaf active-rx-s-pmsis {
                            type yang:gauge32;
                            description
                                "The number of active Mdts on which the PE is receiving packets.  This object is applicable
                                 to VPRNs only.";
                        }

                        leaf active-rx-pseudo-s-pmsis {
                            type yang:counter32;
                            description
                                "The number of active Mdts on which the pseudo PE is receiving packets. This object
                                 is applicable to VPRNs only.";
                        }

                        leaf total-tx-s-pmsis {
                            type yang:counter32;
                            description
                                "The number of MDTs created by the PE for forwarding packets. This object is applicable to
                                 VPRNs only.";
                        }

                        leaf total-rx-s-pmsis {
                            type yang:counter32;
                            description
                                "The number of MDTs created by the PE for receiving packets. This object is applicable to
                                 VPRNs only.";
                        }

                        leaf sg-count {
                            type yang:gauge32;
                            description
                                "The number of entries in 'display router/(service vprn) pim ipv4/6 sg'
                                 for which 'type' is 'sg'.";
                        }

                        leaf star-g-count {
                            type yang:gauge32;
                            description
                                "The number of entries in 'display router/(service vprn) pim ipv4/6 sg'
                                 for which 'type' is 'starG'.";
                        }

                        leaf star-star-rp-count {
                            type yang:gauge32;
                            description
                                "The number of entries in 'display router/(service vprn) pim ipv4/6 sg'
                                 for which 'type' is 'starStarRP'.";
                        }

                        leaf tx-register-ttl-drops {
                            type yang:counter32;
                            description
                                "The number of multicast data packets which could not be encapsulated in Register
                                 messages because the Time To Live (TTL) was zero.";
                        }

                        leaf rx-intra-as-ad {
                            type yang:counter32;
                            description "The number of Intra AS AD routes received on this interface.";
                        }

                        leaf tx-intra-as-ad {
                            type yang:counter32;
                            description "The number of Intra AS AD routes transmitted on this interface.";
                        }

                        leaf rx-intra-as-ad-errors {
                            type yang:counter32;
                            description
                                "The number of errors while processing Intra AS AD routes received on this
                                 interface.";
                        }

                        leaf tx-inter-as-ad {
                            type yang:counter32;
                            description
                                "The number
                                 of Inter AS AD routes transmitted on this interface.";
                        }

                        leaf rx-inter-as-ad {
                            type yang:counter32;
                            description
                                "The number
                                 of Inter AS AD routes received on this interface.";
                        }

                        leaf rx-inter-as-ad-errors {
                            type yang:counter32;
                            description
                                "The number of errors while processing Inter AS AD routes received on this
                                 interface.";
                        }

                        leaf rx-mdt-safi {
                            type yang:counter32;
                            description
                                "The number
                                 of MDT-SAFI AD routes received on this interface.";
                        }

                        leaf tx-mdt-safi {
                            type yang:counter32;
                            description
                                "The number
                                 of MDT-SAFI AD routes transmitted on this interface.";
                        }

                        leaf rx-mdt-safi-errors {
                            type yang:counter32;
                            description
                                "The number of errors while processing MDT-SAFI AD routes received on this
                                 interface.";
                        }

                        leaf rx-spmsi-ad {
                            type yang:counter32;
                            description "The number of S-PMSI AD routes received on this interface.";
                        }

                        leaf tx-spmsi-ad {
                            type yang:counter32;
                            description "The number of S-PMSI AD routes transmitted on this interface.";
                        }

                        leaf rx-spmsi-ad-errors {
                            type yang:counter32;
                            description
                                "The number of errors while processing S-PMSI AD routes received on
                                 this interface.";
                        }

                        leaf rx-leaf-ad {
                            type yang:counter32;
                            description "The number of Leaf AD routes received on this interface.";
                        }

                        leaf tx-leaf-ad {
                            type yang:counter32;
                            description "The number of Leaf AD routes transmitted on this interface.";
                        }

                        leaf rx-leaf-ad-errors {
                            type yang:counter32;
                            description
                                "The number of errors while processing Leaf AD routes received on
                                 this interface.";
                        }

                        leaf rx-source-active-ad {
                            type yang:counter32;
                            description "The number of Source Active AD routes received on this interface.";
                        }

                        leaf tx-source-active-ad {
                            type yang:counter32;
                            description "The number of Source Active AD routes transmitted on this interface.";
                        }

                        leaf tx-source-active-ad-errors {
                            type yang:counter32;
                            description
                                "The number of errors while processing Source Active AD routes received
                                 on this interface.";
                        }

                        leaf rx-shared-tree-join {
                            type yang:counter32;
                            description "The number of Shared Tree Joins received on this interface.";
                        }

                        leaf tx-shared-tree-join {
                            type yang:counter32;
                            description "The number of Shared Tree Joins transmitted on this interface.";
                        }

                        leaf rx-shared-tree-join-errors {
                            type yang:counter32;
                            description
                                "The number of errors while processing Shared Tree Joins received
                                 on this interface.";
                        }

                        leaf rx-source-tree-join {
                            type yang:counter32;
                            description "The number of Source Tree Joins received on this interface.";
                        }

                        leaf tx-source-tree-join {
                            type yang:counter32;
                            description "The number of Source Tree Joins transmitted on this interface.";
                        }

                        leaf rx-source-tree-join-errors {
                            type yang:counter32;
                            description
                                "The number of errors while processing Source Tree Joins received on
                                 this interface.";
                        }

                        leaf rx-bgp-packets {
                            type yang:counter32;
                            description
                                "The number
                                 of BGP Packets received on this interface.";
                        }

                        leaf tx-bgp-packets {
                            type yang:counter32;
                            description
                                "The number
                                 of BGP Packets transmitted on this interface.";
                        }

                    } // container statistics

                    container s-pmsi {
                        description "IPv4 selective provider-network multicast service interface (S-PMSI) configuration";

                        list ldp {
                            key "root-address lsp-id";
                            description
                                "The list of the LDP Provider-Network Multicast Service (PMSI) interfaces.

                                 A PMSI can be thought of as a connector between a set of PE routers
                                 forming a multicast domain. From the perspective of a VPN-specific
                                 PIM instance, a PMSI is a single multi-access interface.

                                 A PMSI interface is created whenever the threshold of a (C-S,C-G)
                                 exceeds the configured threshold value specified by Multicast Data Tunnel thresholds.
                                 If the data-threshold goes below the value specified by
                                 Multicast Data Tunnel thresholds, the PMSI interface is automatically deleted.";

                            leaf root-address {
                                type types-sros:ipv4-unicast-address;
                                description "The extended tunnel address for a PMSI.";
                            }

                            leaf lsp-id {
                                type uint32;
                                description "The LSP Identifier for a PMSI.";
                            }

                            leaf interface-name {
                                type string;
                                description
                                    "The interface name of the PMSI.

                                     This value is specific to the router.";
                            }

                            leaf interface-type {
                                type types-pim:pmsi-interface-type;
                                description "Whether this PMSI interface is of type transmitter or receiver.";
                            }

                            leaf vpn-cscg-count {
                                type uint32;
                                description "The number of (C-S,C-G)'s mapped to this PMSI.";
                            }

                            leaf up-time {
                                type uint32;
                                units "seconds";
                                description "The time since this PMSI entry was created.";
                            }

                            leaf multistream-id {
                                type uint32;
                                description "The stream Id of this multi stream SPMSI.";
                            }

                            leaf multistream-oper-state {
                                type types-sros:up-down-status;
                                description "The current operational state of this multi stream SPMSI.";
                            }

                            list cscg {
                                key "vpn-group-address vpn-source-address";
                                description
                                    "The list of the (C-S,C-G) mapped to the Data Multicast Tunnel(MT).

                                     An entry in this table is created whenever a (C-S,C-G) is mapped to a MT interface.
                                     An entry will be deleted automatically when the mapping between (C-S,C-G) and
                                     Data MT is removed.";

                                leaf vpn-group-address {
                                    type types-sros:ip-multicast-address;
                                    description "The IP address of the multicast traffic destination address in the VPN (C-group address).";
                                }

                                leaf vpn-source-address {
                                    type types-sros:ip-unicast-address;
                                    description "The IP address of the traffic source in the VPN (C-source address).";
                                }

                                leaf current-forwarding-rate {
                                    type yang:counter64;
                                    units "bps";
                                    description
                                        "The current forwarding rate being used by a source group(S,G) entry or
                                         (*,G) entry, where * means any source entry, for the traffic in bits
                                         per second(bps). This forwarding rate is calculated before ingress
                                         QoS policing or shaping is applied.";
                                }

                                leaf cscg-state {
                                    type types-pim:cscg-state;
                                    description
                                        "The state of this PMSI (S,G).

                                         If the S-PMSI is bound to a (C-S,C-G) on the ingress PE and if the PE
                                         is allocating a PMSI, the state will be 'tx-join-pending'. The
                                         state will change to 'tx-joined' when the (C-S,C-G) traffic is switched
                                         over to the new S-PMSI.

                                         If the S-PMSI is not bound to a (C-S,C-G) on the egress PE, the state
                                         will be 'rx-not-joined'. The state will be 'rx-joined' if the (C-S,C-G)
                                         has bound to the S-PMSI.

                                         Egress PE state will be 'rx-joined-tracking' if it receives SPMSI-AD
                                         with no tunnel information.";
                                }

                                leaf mdt-threshold {
                                    type uint32;
                                    units "kilobps";
                                    description
                                        "The threshold in kilobits per second (kbps) for the group to which
                                         this (C-S,C-G) belongs.

                                         For a group C-G configured with a threshold, a (C-S,C-G) is mapped to
                                         a PMSI only if the (C-S,C-G)'s rate exceeds this configured threshold.";
                                }

                                leaf join-timer {
                                    type uint32;
                                    units "seconds";
                                    description
                                        "The time interval before the Provider Edge (PE) router connected to the
                                         source switches to the S-PMSI group.

                                         After providing sufficient time for all PE's to join the S-PMSI, the
                                         transmitting PE switches the given multicast stream to the S-PMSI.
                                         The PE router connected to the source then starts encapsulating
                                         traffic using the S-PMSI group.";
                                }

                                leaf holddown-timer {
                                    type uint32;
                                    units "seconds";
                                    description
                                        "The time interval before which the PE router will switch back to the
                                         Default S-PMSI after it started encapsulating packets using the S-PMSI
                                         group.

                                         This is used to avoid oscillation when traffic is bursty.";
                                }

                                leaf expiry-timer {
                                    type uint32;
                                    units "seconds";
                                    description
                                        "The time interval after which the Provider Edge (PE) router connected to
                                         the receivers time out S-PMSI Join Tag Length Value (TLV) received and
                                         leave the S-PMSI group.

                                         This value must be consistent among PE routers.";
                                }

                                leaf receiver-threshold {
                                    type boolean;
                                    description "Whether receiver threshold is enabled for this S-PMSI.";
                                }

                                leaf receiver-count {
                                    type uint32;
                                    description
                                        "The current receiver count for this S-PMSI.

                                         The value of this object is applicable only when the value of
                                         'receiver-threshold' is 'true'.";
                                }

                                leaf interface-name {
                                    type types-sros:interface-name;
                                    description
                                        "The interface name of this S-PMSI.

                                         This value will be non-zero integer value specific to the router.";
                                }

                                leaf up-time {
                                    type uint32;
                                    units "seconds";
                                    description "The time since this entry was created.";
                                }

                            } // list cscg

                        } // list ldp

                        list pim {
                            key "md-source-address md-group-address";
                            description
                                "The list of Data Multicast Tunnel (MT) interfaces.

                                 An MT can be thought of as a connector between a set of PE routers
                                 forming a Multicast Domain.  From the perspective of a VPN-specific
                                 PIM instance, an MT is a single multi-access interface.

                                 An MT interface is created whenever the threshold of a (C-S,C-G)
                                 exceeds the configured threshold value specified by Multicast Data Tunnel thresholds.
                                 If the data-threshold goes below the value specified by Multicast Data Tunnel thresholds,
                                 the MT interface is automatically deleted.";

                            leaf md-source-address {
                                type types-sros:ipv4-unicast-address;
                                description "Indicates the source address for a Multicast Tunnel.";
                            }

                            leaf md-group-address {
                                type types-sros:ipv4-multicast-address;
                                description "Indicates the group address for a Multicast Tunnel.";
                            }

                            leaf interface-name {
                                type string;
                                description
                                    "The interface name of the PMSI.

                                     This value is specific to the router.";
                            }

                            leaf vpn-cscg-count {
                                type uint32;
                                description "The number of (C-S,C-G)'s mapped to this PMSI.";
                            }

                            leaf up-time {
                                type uint32;
                                units "seconds";
                                description "The time since this PMSI entry was created.";
                            }

                            leaf multistream-id {
                                type uint32;
                                description "The stream Id of this multi stream SPMSI.";
                            }

                            list cscg {
                                key "vpn-group-address vpn-source-address";
                                description
                                    "The list of the (C-S,C-G) mapped to the Data Multicast Tunnel (MT).

                                     An entry in this table is created whenever a (C-S,C-G) is mapped to a MT interface.
                                     An entry will be deleted automatically when the mapping between (C-S,C-G) and
                                     Data MT is removed.";

                                leaf vpn-group-address {
                                    type types-sros:ip-multicast-address;
                                    description "The IP address of the multicast traffic destination address in the VPN (C-group address).";
                                }

                                leaf vpn-source-address {
                                    type types-sros:ip-unicast-address;
                                    description "The IP address of the traffic source in the VPN (C-source address).";
                                }

                                leaf current-forwarding-rate {
                                    type yang:counter64;
                                    units "bps";
                                    description
                                        "The current forwarding rate being used by a source group(S,G) entry or
                                         (*,G) entry, where * means any source entry, for the traffic in bits
                                         per second(bps). This forwarding rate is calculated before ingress
                                         QoS policing or shaping is applied.";
                                }

                                leaf cscg-state {
                                    type types-pim:cscg-state;
                                    description
                                        "The state of this PMSI (S,G).

                                         If the S-PMSI is bound to a (C-S,C-G) on the ingress PE and if the PE
                                         is allocating a PMSI, the state will be 'tx-join-pending'. The
                                         state will change to 'tx-joined' when the (C-S,C-G) traffic is switched
                                         over to the new S-PMSI.

                                         If the S-PMSI is not bound to a (C-S,C-G) on the egress PE, the state
                                         will be 'rx-not-joined'. The state will be 'rx-joined' if the (C-S,C-G)
                                         has bound to the S-PMSI.

                                         Egress PE state will be 'rx-joined-tracking' if it receives SPMSI-AD
                                         with no tunnel information.";
                                }

                                leaf mdt-threshold {
                                    type uint32;
                                    units "kilobps";
                                    description
                                        "The threshold in kilobits per second (kbps) for the group to which
                                         this (C-S,C-G) belongs.

                                         For a group C-G configured with a threshold, a (C-S,C-G) is mapped to
                                         a PMSI only if the (C-S,C-G)'s rate exceeds this configured threshold.";
                                }

                                leaf join-timer {
                                    type uint32;
                                    units "seconds";
                                    description
                                        "The time interval before the Provider Edge (PE) router connected to the
                                         source switches to the S-PMSI group.

                                         After providing sufficient time for all PE's to join the S-PMSI, the
                                         transmitting PE switches the given multicast stream to the S-PMSI.
                                         The PE router connected to the source then starts encapsulating
                                         traffic using the S-PMSI group.";
                                }

                                leaf holddown-timer {
                                    type uint32;
                                    units "seconds";
                                    description
                                        "The time interval before which the PE router will switch back to the
                                         Default S-PMSI after it started encapsulating packets using the S-PMSI
                                         group.

                                         This is used to avoid oscillation when traffic is bursty.";
                                }

                                leaf expiry-timer {
                                    type uint32;
                                    units "seconds";
                                    description
                                        "The time interval after which the Provider Edge (PE) router connected to
                                         the receivers time out S-PMSI Join Tag Length Value (TLV) received and
                                         leave the S-PMSI group.

                                         This value must be consistent among PE routers.";
                                }

                                leaf interface-name {
                                    type types-sros:interface-name;
                                    description
                                        "The interface name of this S-PMSI.

                                         This value will be non-zero integer value specific to the router.";
                                }

                                leaf up-time {
                                    type uint32;
                                    units "seconds";
                                    description "The time since this entry was created.";
                                }

                            } // list cscg

                        } // list pim

                        list rsvp {
                            key "extended-tunnel-address tunnel-id p2mp-id";
                            description
                                "The list of the RSVP Provider-Network Multicast Service (PMSI) interfaces.

                                 A PMSI can be thought of as a connector between a set of PE routers
                                 forming a Multicast Domain. From the perspective of a VPN-specific
                                 PIM instance, a PMSI is a single multi-access interface.

                                 A PMSI interface is created whenever the threshold of a (C-S,C-G)
                                 exceeds the configured threshold value specified by Multicast Data Tunnel thresholds.
                                 If the data-threshold goes below the value specified by
                                 Multicast Data Tunnel thresholds, the PMSI interface is automatically deleted.";

                            leaf extended-tunnel-address {
                                type types-sros:ipv4-unicast-address;
                                description "The extended Tunnel address for a PMSI.";
                            }

                            leaf tunnel-id {
                                type uint32;
                                description "The Source RSVP Tunnel Identifier for a PMSI.";
                            }

                            leaf p2mp-id {
                                type uint32;
                                description "The P2MP Identifier for a PMSI.";
                            }

                            leaf interface-name {
                                type string;
                                description
                                    "The interface name of the PMSI.

                                     This value is specific to the router.";
                            }

                            leaf interface-type {
                                type types-pim:pmsi-interface-type;
                                description "Whether this PMSI interface is of type transmitter or receiver.";
                            }

                            leaf vpn-cscg-count {
                                type uint32;
                                description "The number of (C-S,C-G)'s mapped to this PMSI.";
                            }

                            leaf up-time {
                                type uint32;
                                units "seconds";
                                description "The time since this PMSI entry was created.";
                            }

                            leaf multistream-id {
                                type uint32;
                                description "The stream Id of this multi stream SPMSI.";
                            }

                            leaf multistream-oper-state {
                                type types-sros:up-down-status;
                                description "The current operational state of this multi stream SPMSI.";
                            }

                            list cscg {
                                key "vpn-group-address vpn-source-address";
                                description
                                    "The list of the (C-S,C-G) mapped to the Data Multicast Tunnel(MT).

                                     An entry in this table is created whenever a (C-S,C-G) is mapped to a MT interface.
                                     An entry will be deleted automatically when the mapping between (C-S,C-G) and
                                     Data MT is removed.";

                                leaf vpn-group-address {
                                    type types-sros:ip-multicast-address;
                                    description "The IP address of the multicast traffic destination address in the VPN (C-group address).";
                                }

                                leaf vpn-source-address {
                                    type types-sros:ip-unicast-address;
                                    description "The IP address of the traffic source in the VPN (C-source address).";
                                }

                                leaf current-forwarding-rate {
                                    type yang:counter64;
                                    units "bps";
                                    description
                                        "The current forwarding rate being used by a source group(S,G) entry or
                                         (*,G) entry, where * means any source entry, for the traffic in bits
                                         per second(bps). This forwarding rate is calculated before ingress
                                         QoS policing or shaping is applied.";
                                }

                                leaf cscg-state {
                                    type types-pim:cscg-state;
                                    description
                                        "The state of this PMSI (S,G).

                                         If the S-PMSI is bound to a (C-S,C-G) on the ingress PE and if the PE
                                         is allocating a PMSI, the state will be 'tx-join-pending'. The
                                         state will change to 'tx-joined' when the (C-S,C-G) traffic is switched
                                         over to the new S-PMSI.

                                         If the S-PMSI is not bound to a (C-S,C-G) on the egress PE, the state
                                         will be 'rx-not-joined'. The state will be 'rx-joined' if the (C-S,C-G)
                                         has bound to the S-PMSI.

                                         Egress PE state will be 'rx-joined-tracking' if it receives SPMSI-AD
                                         with no tunnel information.";
                                }

                                leaf mdt-threshold {
                                    type uint32;
                                    units "kilobps";
                                    description
                                        "The threshold in kilobits per second (kbps) for the group to which
                                         this (C-S,C-G) belongs.

                                         For a group C-G configured with a threshold, a (C-S,C-G) is mapped to
                                         a PMSI only if the (C-S,C-G)'s rate exceeds this configured threshold.";
                                }

                                leaf join-timer {
                                    type uint32;
                                    units "seconds";
                                    description
                                        "The time interval before the Provider Edge (PE) router connected to the
                                         source switches to the S-PMSI group.

                                         After providing sufficient time for all PE's to join the S-PMSI, the
                                         transmitting PE switches the given multicast stream to the S-PMSI.
                                         The PE router connected to the source then starts encapsulating
                                         traffic using the S-PMSI group.";
                                }

                                leaf holddown-timer {
                                    type uint32;
                                    units "seconds";
                                    description
                                        "The time interval before which the PE router will switch back to the
                                         Default S-PMSI after it started encapsulating packets using the S-PMSI
                                         group.

                                         This is used to avoid oscillation when traffic is bursty.";
                                }

                                leaf expiry-timer {
                                    type uint32;
                                    units "seconds";
                                    description
                                        "The time interval after which the Provider Edge (PE) router connected to
                                         the receivers time out S-PMSI Join Tag Length Value (TLV) received and
                                         leave the S-PMSI group.

                                         This value must be consistent among PE routers.";
                                }

                                leaf receiver-threshold {
                                    type boolean;
                                    description "Whether receiver threshold is enabled for this S-PMSI.";
                                }

                                leaf receiver-count {
                                    type uint32;
                                    description
                                        "The current receiver count for this S-PMSI.

                                         The value of this object is applicable only when the value of
                                         'receiver-threshold' is 'true'.";
                                }

                                leaf interface-name {
                                    type types-sros:interface-name;
                                    description
                                        "The interface name of this S-PMSI.

                                         This value will be non-zero integer value specific to the router.";
                                }

                                leaf up-time {
                                    type uint32;
                                    units "seconds";
                                    description "The time since this entry was created.";
                                }

                            } // list cscg

                        } // list rsvp

                        list bier {
                            key "root-address subdomain-id bfr-id mpls-label";
                            description
                                "The list of Bier Provider-Network Multicast Service (PMSI) interfaces.

                                 A PMSI can be thought of as a connector between a set of PE routers 
                                 forming a multicast domain. From the perspective of a VPN-specific 
                                 PIM instance, a PMSI is a single multi-access interface.

                                 PMSI's are used for transmitting the MVPN's multicast data from one
                                 PE to others.";

                            leaf root-address {
                                type types-sros:ip-address;
                                description "The tunnel root address of the PMSI.";
                            }

                            leaf subdomain-id {
                                type uint32;
                                description "The BIER sub-domain ID.";
                            }

                            leaf bfr-id {
                                type uint32;
                                description "The BFR ID.";
                            }

                            leaf mpls-label {
                                type uint32;
                                description "The MPLS service label for the PMSI.";
                            }

                            leaf interface-name {
                                type string;
                                description
                                    "The interface name of the PMSI.

                                     This value is specific to the router.";
                            }

                            leaf vpn-cscg-count {
                                type uint32;
                                description "The number of (C-S,C-G)'s mapped to this PMSI.";
                            }

                            leaf up-time {
                                type uint32;
                                units "seconds";
                                description "The time since this PMSI entry was created.";
                            }

                            leaf multistream-id {
                                type uint32;
                                description "The stream Id of this multi stream SPMSI.";
                            }

                            leaf multistream-oper-state {
                                type types-sros:up-down-status;
                                description "The current operational state of this multi stream SPMSI.";
                            }

                            list cscg {
                                key "vpn-group-address vpn-source-address";
                                description
                                    "The lists of the the C-(S,G) mapped to the BIER Provider-Network
                                     Multicast Service Interface (PMSI).

                                     An entry in this table is created whenever a C-(S,G)
                                     is mapped to a PMSI interface. An entry will be deleted automatically
                                     when the mapping between C-(S,G) and Bier PMSI is removed.";

                                leaf vpn-group-address {
                                    type types-sros:ip-multicast-address;
                                    description "The IP address of the multicast traffic destination address in the VPN (C-group address).";
                                }

                                leaf vpn-source-address {
                                    type types-sros:ip-unicast-address;
                                    description "The IP address of the traffic source in the VPN (C-source address).";
                                }

                                leaf cscg-state {
                                    type types-pim:cscg-state;
                                    description
                                        "The state of this PMSI (S,G).

                                         If the S-PMSI is bound to a (C-S,C-G) on the ingress PE and if the PE
                                         is allocating a PMSI, the state will be 'tx-join-pending'. The
                                         state will change to 'tx-joined' when the (C-S,C-G) traffic is switched
                                         over to the new S-PMSI.

                                         If the S-PMSI is not bound to a (C-S,C-G) on the egress PE, the state
                                         will be 'rx-not-joined'. The state will be 'rx-joined' if the (C-S,C-G)
                                         has bound to the S-PMSI.

                                         Egress PE state will be 'rx-joined-tracking' if it receives SPMSI-AD
                                         with no tunnel information.";
                                }

                                leaf mdt-threshold {
                                    type uint32;
                                    units "kilobps";
                                    description
                                        "The threshold in kilobits per second (kbps) for the group to which
                                         this (C-S,C-G) belongs.

                                         For a group C-G configured with a threshold, a (C-S,C-G) is mapped to
                                         a PMSI only if the (C-S,C-G)'s rate exceeds this configured threshold.";
                                }

                                leaf join-timer {
                                    type uint32;
                                    units "seconds";
                                    description
                                        "The time interval before the Provider Edge (PE) router connected to the
                                         source switches to the S-PMSI group.

                                         After providing sufficient time for all PE's to join the S-PMSI, the
                                         transmitting PE switches the given multicast stream to the S-PMSI.
                                         The PE router connected to the source then starts encapsulating
                                         traffic using the S-PMSI group.";
                                }

                                leaf holddown-timer {
                                    type uint32;
                                    units "seconds";
                                    description
                                        "The time interval before which the PE router will switch back to the
                                         Default S-PMSI after it started encapsulating packets using the S-PMSI
                                         group.

                                         This is used to avoid oscillation when traffic is bursty.";
                                }

                                leaf expiry-timer {
                                    type uint32;
                                    units "seconds";
                                    description
                                        "The time interval after which the Provider Edge (PE) router connected to
                                         the receivers time out S-PMSI Join Tag Length Value (TLV) received and
                                         leave the S-PMSI group.

                                         This value must be consistent among PE routers.";
                                }

                                leaf receiver-threshold {
                                    type boolean;
                                    description "Whether receiver threshold is enabled for this S-PMSI.";
                                }

                                leaf receiver-count {
                                    type uint32;
                                    description
                                        "The current receiver count for this S-PMSI.

                                         The value of this object is applicable only when the value of
                                         'receiver-threshold' is 'true'.";
                                }

                                leaf interface-name {
                                    type types-sros:interface-name;
                                    description
                                        "The interface name of this S-PMSI.

                                         This value will be non-zero integer value specific to the router.";
                                }

                                leaf up-time {
                                    type uint32;
                                    units "seconds";
                                    description "The time since this entry was created.";
                                }

                            } // list cscg

                        } // list bier

                    } // container s-pmsi

                } // container ipv4

                container ipv6 {
                    description "Enter the ipv6 context";

                    list sg {
                        key "group-address source-address";
                        description
                            "Each entry represents a source address from which receivers are
                             interested or not interested in receiving multicast traffic.";

                        leaf group-address {
                            type types-sros:ipv6-multicast-address;
                            description
                                "The IP multicast group address for which this entry contains information.
                                 If the source-type is 'starStarRP', the value of this object will
                                 be zero and source-address will contain the address of the RP.";
                        }

                        leaf source-address {
                            type types-sros:ipv6-address;
                            description
                                "The source address for which this entry contains information.
                                 If source-type is 'starG', the value of this object will be zero.
                                 If source-type is 'starstarRP', the value of this object will be address of the RP.";
                        }

                        leaf source-type {
                            type enumeration {
                                enum "star-star-rp"                 { value 0; }
                                enum "star-g"                       { value 1; }
                                enum "sg"                           { value 2; }
                            }
                            description "The type of this entry.";
                        }

                        leaf sg-state {
                            type enumeration {
                                enum "none"                         { value 0; }
                                enum "active"                       { value 1; }
                                enum "standby"                      { value 2; }
                            }
                            description "The current state of the (S,G).";
                        }

                        leaf rp-address {
                            type types-sros:ip-address;
                            description "The address of the Rendezvous Point(RP).";
                        }

                        leaf advertising-router {
                            type types-sros:ip-address;
                            description "The router address that advertised the route to the source indicated by source-address.";
                        }

                        leaf downstream-rpfv-neighbor {
                            type types-sros:ip-address;
                            description "The address of the downstream RPF vector neighbor.";
                        }

                        leaf downstream-rpfv-type {
                            type types-pim:rpfv-type;
                            description "The downstream RPF vector type.";
                        }

                        leaf downstream-rpfv-rd {
                            type types-services:state-vpn-rd;
                            description "The downstream RPF vector Route Distinguisher.";
                        }

                        leaf downstream-rpfv-proxy {
                            type types-sros:ip-address;
                            description "The address of the downstream RPF vector proxy.";
                        }

                        leaf upstream-rpfv-neighbor {
                            type types-sros:ip-address;
                            description "The address of the upstream RPF vector neighbor.";
                        }

                        leaf rpfv-flags {
                            type bits {
                                bit upstream-neighbor-no-join-attribute { position 0; }
                            }
                            description
                                "The state of the rpf-vectors.

                                 When the bit 'upstream-neighbor-no-join-attribute' is set, it
                                 indicates that the upstream neighbor towards the rpf-vector
                                 proxy does not support join-attributes.";
                        }

                        leaf upstream-rpfv-type {
                            type types-pim:rpfv-type;
                            description "The upstream RPF vector type.";
                        }

                        leaf upstream-rpfv-rd {
                            type types-services:state-vpn-rd;
                            description "The upstream RPF vector Route Distinguisher.";
                        }

                        leaf upstream-rpfv-proxy {
                            type types-sros:ip-address;
                            description "The address of the upstream RPF vector proxy.";
                        }

                        leaf source-flags {
                            type bits {
                                bit spt-bit                        { position 0; }
                                bit rpt-prune-desired              { position 1; }
                            }
                            description
                                "The information about the state of the entry

                                 This object is applicable only for (S,G) entries,i.e., when
                                 source-type is 'sg'.

                                 The (S,G) 'spt-bit' is used to distinguish whether to forward on
                                 (*,*,RP) or (*,G) or on (S,G) state. It is updated when the (S,G)
                                 data comes on the RPF interface towards the source.
                                 'rpt-prune-desired' is set according to the PruneDesired(S,G,rpt)
                                 algorithm.";
                        }

                        leaf mode {
                            type enumeration {
                                enum "none"                         { value 0; }
                                enum "sparse"                       { value 1; }
                                enum "dense"                        { value 2; }
                            }
                            description "The mode of operation for the (S,G).";
                        }

                        leaf mrib-nh-address {
                            type types-sros:ip-address-with-zone;
                            description "The next hop address towards the RP.";
                        }

                        leaf standby-rpf-neighbor-address {
                            type types-sros:ip-address;
                            description
                                "The address of the secondary RPF neighbor

                                 The value of this object is applicable only when the value of the
                                 object 'configure service vprn mvpn umh-selection' is set to 'tunnel-status'
                                 indicating that the MVPN is configured with source redundancy.

                                 When MVPN is configured with source redundancy, MVPN is capable of
                                 receiving traffic from two different PE's for the same source.";
                        }

                        leaf mrib-source-flags {
                            type types-pim:mrib-source-flags;
                            description
                                "The MRIB information about the source. If the entry is of type 'starG'
                                 or 'starStarRP', it will contain information about the RP for this group.";
                        }

                        leaf standby-mrib-source-flags {
                            type types-pim:mrib-source-flags;
                            description
                                "The MRIB information about the source reachable through the standby RPF
                                 interface.

                                 This object is applicable only for (S,G) entries,i.e., when
                                 source-type is 'sg'.";
                        }

                        leaf keepalive-timer {
                            type uint32;
                            units "seconds";
                            description
                                "Is applicable only for (S,G) entries. The (S,G) Keepalive Timer is updated by
                                 data being forwarded using this (S,G) forwarding state. It is used to keep (S,G)
                                 state alive in the absence of explicit (S,G) Joins.";
                        }

                        leaf prune-limit-timer {
                            type uint32;
                            units "seconds";
                            description "The time until which no prunes will be sent upstream.";
                        }

                        leaf graft-retry-timer {
                            type uint32;
                            units "seconds";
                            description
                                "The time interval between which two grafts are sent upstream and no ack is
                                 received from the upstream router.";
                        }

                        leaf up-time {
                            type uint32;
                            units "seconds";
                            description "The time since this source group entry got created.";
                        }

                        leaf resolved-by {
                            type enumeration {
                                enum "none"                         { value 0; }
                                enum "multicast-route-table"        { value 1; }
                                enum "unicast-route-table"          { value 2; }
                            }
                            description
                                "Which unicast routing table was used to resolve this source group entry.

                                 The value of this object will be 'multicastRouteTable' if the
                                 source or Rendezvous Point (RP) is resolved by the multicast-unicast
                                 route table. The value of this object will be 'unicastRouteTable' if
                                 the source or Rendezvous Point (RP) is resolved by the unicast
                                 route table. The value will be 'none' if the source or RP is
                                 unresolved.";
                        }

                        leaf upstream-jp-state {
                            type enumeration {
                                enum "not-joined"                   { value 0; }
                                enum "joined"                       { value 1; }
                                enum "pruned"                       { value 2; }
                                enum "forwarding"                   { value 3; }
                                enum "ack-pending"                  { value 4; }
                            }
                            description
                                "The upstream Join-Prune state. This is a result of sending PIM Join-Prune
                                 messages towards the source or the RP.";
                        }

                        leaf upstream-jp-timer {
                            type uint32;
                            units "seconds";
                            description
                                "The time remaining before the router sends another Join message to it's
                                 upstream neighbor.";
                        }

                        leaf upstream-rpt-jp-state {
                            type enumeration {
                                enum "not-joined-star-g"            { value 0; }
                                enum "not-pruned"                   { value 1; }
                                enum "pruned"                       { value 2; }
                            }
                            description
                                "The upstream RPT Join-Prune state. (S,G,rpt) Joins and Prunes are (S,G) Joins or
                                 Prunes sent on the RP tree with the RPT bit set, either to modify the results of
                                 (*,G) Joins, or to override the behavior of other upstream LAN peers.";
                        }

                        leaf upstream-rpt-override-timer {
                            type uint32;
                            units "seconds";
                            description
                                "The delay to triggered Join(S,G,rpt) messages to prevent implosions of triggered
                                 messages.

                                 If non-zero, it means that the router was in 'not-pruned' state and it saw a
                                 Prune(S,G,rpt) message being sent to RPF'(S,G,rpt).

                                 If the router sees a Join(S,G,rpt) override message being sent by
                                 some other router on the LAN while the timer is still non-zero,
                                 it simply cancels the override timer. If it does not see a
                                 Join(S,G,rpt) message, then on expiry of the override timer, it
                                 sends it's own Join(S,G,rpt) message to RPF'(S,G,rpt). A similar
                                 scenario exists when RPF'(S,G,rpt) changes to become equal to
                                 RPF'(*,G).";
                        }

                        leaf standby-upstream-jp-state {
                            type enumeration {
                                enum "not-joined"                   { value 0; }
                                enum "joined"                       { value 1; }
                            }
                            description
                                "The standby RPF Join-Prune state.

                                 This object is applicable only for (S,G) entries,i.e., when
                                 source-type is 'sg'.";
                        }

                        leaf standby-upstream-jp-timer {
                            type uint32;
                            units "seconds";
                            description
                                "The time remaining before the router sends another Join message to it's
                                 upstream neighbor reachable through the standby RPF interface.

                                 This object is applicable only for (S,G) entries,i.e., when
                                 source-type is 'sg'.";
                        }

                        leaf register-state {
                            type enumeration {
                                enum "no-info"                      { value 0; }
                                enum "join"                         { value 1; }
                                enum "join-pending"                 { value 2; }
                                enum "prune"                        { value 3; }
                                enum "null-join"                    { value 4; }
                            }
                            description
                                "The register state. The register state is kept at the source DR. When the host
                                 starts sending multicast packets and if there are no entries
                                 programmed for that group, the source DR sends a Register packet
                                 to the RP(G). Register state transition happen based on the register
                                 stop timer and the response received from the RP.";
                        }

                        leaf register-stop-timer {
                            type uint32;
                            units "seconds";
                            description
                                "The time remaining before the register-state might transition
                                 to a different state. This timer has a non-zero value when the
                                 value of register-state is not 'noInfo'.";
                        }

                        leaf register-from-anycast-rp {
                            type boolean;
                            description
                                "Whether a register message for this source  group combination
                                 was received from the anycast RP and not from the designated
                                 router connected to the source. It  is not applicable when the value of
                                 source-type is starStarRP or starG.";
                        }

                        leaf rpf-neighbor-address {
                            type types-sros:ip-address;
                            description "The address of the RPF neighbor.";
                        }

                        leaf rpf-neighbor-interface-name {
                            type string;
                            description "The router's interface index on which the RPF neighbor exists.";
                        }

                        leaf standby-rpf-neighbor-interface-name {
                            type string;
                            description
                                "The router's interface index on which the secondary RPF neighbor exists.

                                 The value of this object is applicable only when the value of the
                                 object 'configure service vprn mvpn umh-selection' is set to 'tunnel-status'
                                 indicating that the MVPN is configured with source redundancy.";
                        }

                        leaf spmsi-rpf-neighbor-interface-name {
                            type string;
                            description
                                "In an MVPN scenario: The router's SPMSI interface index, if any, on which the RPF
                                 neighbor exists.";
                        }

                        leaf inherited-outgoing-interface-count {
                            type yang:gauge32;
                            description
                                "The number of interfaces in the inherited outgoing interface list. An 'inherited'
                                 list inherits state from other types.";
                        }

                        leaf s-g-rpt-prune-interface-count {
                            type yang:gauge32;
                            description "The number of interfaces on which the router received (S,G,Rpt) prunes.";
                        }

                        leaf spt-switchover-threshold {
                            type uint32;
                            units "kilobps";
                            description
                                "The configured threshold in kilobits per second(kbps) for the group to which
                                 this (S,G) belongs.  For a group G configured with a threshold,
                                 switchover to SPT for an (S,G) is attempted only if the (S,G)'s rate
                                 exceeds this configured threshold.";
                        }

                        leaf ecmp-optional-threshold {
                            type uint32 {
                                range "0..7";
                            }
                            description "The optional threshold value for ECMP balancing.";
                        }

                        leaf administrative-bandwidth {
                            type yang:gauge32 {
                                range "0..40000000";
                            }
                            units "kilobps";
                            description
                                "The administrative bandwidth in kilobits per second(kbps) for the group to which
                                 this (S,G) belongs.";
                        }

                        leaf rpt-rpf-neighbor-address {
                            type types-sros:ip-address;
                            description "The address of the RPF neighbor on the RPT.";
                        }

                        leaf immediate-outgoing-interface-count {
                            type yang:gauge32;
                            description
                                "The number of interfaces in the immediate outgoing interface list. An outgoing
                                 list can be 'immediate' if it is built directly from the state of
                                 the relevant type as indicated by source-type.";
                        }

                        leaf inherited-rpt-outgoing-interface-count {
                            type yang:gauge32;
                            description "The number of interfaces in the inherited outgoing interface list for (S,G,Rpt).";
                        }

                        leaf local-rx-include-interface-count {
                            type yang:gauge32;
                            description
                                "The number of interfaces in the local membership include interface list. Local
                                 membership is the result of the local membership mechanism (MLD)
                                 running on a interface. Include list contains interfaces which are
                                 interested in receiving multicast traffic for this source group entry.";
                        }

                        leaf local-rx-exclude-interface-count {
                            type yang:gauge32;
                            description
                                "The number of interfaces in the local membership exclude interface list. Local
                                 membership is the result of the local membership mechanism (MLD)
                                 running on the interface. Exclude list contains interfaces which are
                                 not interested in receiving multicast traffic for this source group
                                 entry.";
                        }

                        leaf join-or-prune-interface-count {
                            type yang:gauge32;
                            description
                                "The number of interfaces on which the router received a Join or Prune message for
                                 this source group combination.";
                        }

                        leaf lost-assert-interface-count {
                            type yang:gauge32;
                            description
                                "The number of interfaces on which the router lost assert for this source group
                                 combination.";
                        }

                        leaf current-forwarding-rate {
                            type yang:counter64;
                            units "bps";
                            description
                                "The current forwarding rate being used by a source group(S,G) entry or
                                 (*,G) entry, where * means any source entry, for the traffic in bits
                                 per second(bps). This forwarding rate is calculated before ingress
                                 QoS policing or shaping is applied.";
                        }

                        list group-interface {
                            key "sap forwarding-service group-interface-name";
                            description "List of the PIM enabled group-interfaces for an entry in the sg list.";

                            leaf sap {
                                type types-sros:sap;
                                description "SAP identifier.";
                            }

                            leaf forwarding-service {
                                type types-services:service-name;
                                description
                                    "Specifies the forwarding service ID for a group-interface in a retailer
                                     context.";
                            }

                            leaf group-interface-name {
                                type leafref {
                                    path "../../../../../interface/interface-name";
                                }
                                description
                                    "The unique value which identifies this group-interface of this virtual
                                     router in the system. This field provides an identifier for
                                     virtual router interfaces similar to the ifIndex values used in the
                                     mib-2 interfaces table for physical interfaces.

                                     The values can be reused for different virtual routers, but are unique within
                                     those entries with the same vrtr-id.

                                     The value for each virtual interface must remain constant at least from
                                     one re-initialization of the system management processor to the next.";
                            }

                            leaf list-flags {
                                type types-pim:sg-flags;
                                description "The different lists that this group-interface belongs to.";
                            }

                        } // list group-interface

                        list host {
                            key "host-address";
                            description "List of PIM enabled hosts and their states for each entry in the sg list.";

                            leaf host-address {
                                type types-sros:ipv6-unicast-address;
                                description
                                    "The IP multicast host address for which this entry contains information.
                                     If the ../type is 'star-star-rp', the value of this object will
                                     be zero and host-address will contain the address of the RP.";
                            }

                            leaf host-flags {
                                type types-pim:sg-flags;
                                description "The different lists that this host belongs to.";
                            }

                        } // list host

                        list interface {
                            key "interface-name";
                            description "List of the PIM enabled interfaces for an entry in sg list.";

                            leaf interface-name {
                                type types-sros:interface-name;
                                description "Router interface name.";
                            }

                            leaf interface-flags {
                                type types-pim:sg-flags;
                                description "Set of lists to which this interface belongs";
                            }

                            leaf spmsi-interface-name {
                                type string;
                                description
                                    "In an MVPN scenario: The router's SPMSI interface index, if any, corresponding to
                                     the outgoing IPMSI interface.";
                            }

                        } // list interface

                        container statistics {
                            description
                                "Statistics for the entries in the sg list. These statistics are
                                 collected by the forwarding engine.";

                            leaf forwarded-packets {
                                type yang:counter64;
                                description
                                    "The number of multicast packets that were forwarded to the interfaces in the
                                     outgoing interface list. 'display router/(service vprn) pim ipv4/6 sg interface' lists all the
                                     interfaces in the outgoing interface list.";
                            }

                            leaf discarded-packets {
                                type yang:counter64;
                                description
                                    "The number of multicast packets that matched this source group entry but were
                                     discarded. For (S,G) entries, if the traffic is getting forwarded on
                                     the SPT, the packets arriving from the RPT will be discarded.";
                            }

                            leaf rpf-mismatches {
                                type yang:counter64;
                                description
                                    "The number of multicast packets that matched this source group entry
                                     but they did not arrive on the interface indicated by
                                     'display router/(service vprn) pim ipv4/6 sg rpf-neighbor-interface-name'.";
                            }

                            leaf forwarded-octets {
                                type yang:counter64;
                                description
                                    "The number of multicast octets that were forwarded to the interfaces in the
                                     outgoing interface list. 'display router/(service vprn) pim ipv4/6 sg interface' lists all the
                                     interfaces in the outgoing interface list.";
                            }

                        } // container statistics

                        list multicast-management-operational-data {
                            key "chassis-number slot-number fp-number";
                            description "operational data.";

                            leaf chassis-number {
                                type uint32;
                                description "The unique index identifying this physical chassis.";
                            }

                            leaf slot-number {
                                type uint32;
                                description
                                    "The unique value which identifies the IOM slot within a
                                     chassis in the system.";
                            }

                            leaf fp-number {
                                type uint32;
                                description "Forwarding plane within a specific IOM card";
                            }

                            leaf bandwith {
                                type yang:gauge32;
                                units "kilobps";
                                description "Current bandwidth";
                            }

                            leaf current-path {
                                type enumeration {
                                    enum "none"                         { value 0; }
                                    enum "primary"                      { value 1; }
                                    enum "secondary"                    { value 2; }
                                    enum "ancillary"                    { value 3; }
                                    enum "blackhole"                    { value 4; }
                                }
                                description "Explicit sf path.";
                            }

                            leaf explicit-path {
                                type boolean;
                                description "???";
                            }

                            leaf admin-bw {
                                type yang:gauge32;
                                description "Admin bandwidth.";
                            }

                            leaf preference {
                                type yang:gauge32;
                                description "Preference level.";
                            }

                            leaf blackholed {
                                type boolean;
                                description "In black-hole state";
                            }

                            leaf blackhole-rate {
                                type yang:gauge32;
                                description "The current rate at which this channel will be placed in black-hole state";
                            }

                            leaf highest-bw {
                                type yang:gauge32;
                                description "The highest multicast bandwidth that has been accounted.";
                            }

                            leaf second-highest-bw {
                                type yang:gauge32;
                                description "The second highest multicast bandwidth that has been accounted.";
                            }

                            leaf expiry-time {
                                type uint32;
                                units "seconds";
                                description "Remaining time before the bandwidth update timer on the FP expires";
                            }

                            leaf plane {
                                type uint32;
                                description "Forwarding plane";
                            }

                        } // list multicast-management-operational-data

                    } // list sg

                    container statistics {
                        description "PIM statistics for a particular PIM instance.";

                        leaf tx-registers {
                            type yang:counter32;
                            description "The number of PIM Register messages transmitted by this instance.";
                        }

                        leaf tx-register-errors {
                            type yang:counter32;
                            description
                                "The number of the times there was an error while transmitting PIM
                                 Register messages by this instance.";
                        }

                        leaf tx-null-registers {
                            type yang:counter32;
                            description "The number of PIM Null Register messages transmitted by this instance.";
                        }

                        leaf rx-candidate-rp-advertisements {
                            type yang:counter32;
                            description "The number of PIM Candidate-RP Advertisements (C-RP-Adv) received by this instance.";
                        }

                        leaf tx-candidate-rp-advertisements {
                            type yang:counter32;
                            description
                                "The number of PIM Candidate-RP Advertisements (C-RP-Adv) transmitted by this router
                                 instance.";
                        }

                        leaf rx-candidate-rp-advertisement-drops {
                            type yang:counter32;
                            description
                                "The number of PIM Candidate-RP Advertisements (C-RP-Adv) received by this instance,
                                 but were dropped.";
                        }

                        leaf tx-candidate-rp-advertisement-errors {
                            type yang:counter32;
                            description "The number of errors while transmitting PIM Candidate-RP Advertisements (C-RP-Adv).";
                        }

                        leaf forwarded-candidate-rp-advertisements {
                            type yang:counter32;
                            description
                                "The number of Candidate-RP Advertisements(C-RP-Adv) that were forwarded by the
                                 router. C-RP-Adv's are forwarded when the received advertisement
                                 has a router alert set and the destination address is not the
                                 router's local address.";
                        }

                        leaf forwarded-candidate-rp-advertisement-drops {
                            type yang:counter32;
                            description
                                "The number of times the Candidate-RP Advertisements(C-RP-Adv) could not be forwarded
                                 by the router.";
                        }

                        leaf tx-mdt-join-tlvs {
                            type yang:counter32;
                            description "The number of times MDT Join TLV were transmitted.";
                        }

                        leaf rx-mdt-join-tlvs {
                            type yang:counter32;
                            description "The number of times MDT Join TLV were received.";
                        }

                        leaf tx-mdt-join-tlv-errors {
                            type yang:counter32;
                            description "The number of times MDT Join TLV could not be transmitted.";
                        }

                        leaf rx-mdt-join-tlv-errors {
                            type yang:counter32;
                            description
                                "The number of times MDT Join TLVs were dropped due to errors in the
                                 received TLV.";
                        }

                        leaf tx-spmsi-limit-hits {
                            type yang:counter32;
                            description
                                "The number of times the switch from ipmsi to S-PMSI is failed because of reaching the
                                 maximum S-PMSI limit configured in
                                 TIMETRA-VRTR-MIB::vRtrMvpnSpmsiMaxLimit.";
                        }

                        leaf p2mp-pmsi-create-fails {
                            type yang:counter32;
                            description "The number of times a P2MP PMSI tunnel creation has failed.";
                        }

                        leaf p2mp-pmsi-request-fails {
                            type yang:counter32;
                            description "The number of times a P2MP PMSI tunnel request has failed.";
                        }

                        leaf rx-control-pdu-interface-drops {
                            type yang:counter32;
                            description
                                "The number of control PDU drops on an interface which is operationally down or on an
                                 interface on which PIM is not enabled.";
                        }

                        leaf active-tx-s-pmsis {
                            type yang:gauge32;
                            description
                                "The number of active MDTs on which the PE is forwarding packets. This object is
                                 applicable to VPRNs only.";
                        }

                        leaf active-tx-receiver-threshold-s-pmsis {
                            type yang:counter32;
                            description
                                "The number of active MDTs on which the PE is forwarding packets. This S-PMSI is
                                 threshold controlled.";
                        }

                        leaf active-rx-s-pmsis {
                            type yang:gauge32;
                            description
                                "The number of active Mdts on which the PE is receiving packets.  This object is applicable
                                 to VPRNs only.";
                        }

                        leaf active-rx-pseudo-s-pmsis {
                            type yang:counter32;
                            description
                                "The number of active Mdts on which the pseudo PE is receiving packets. This object
                                 is applicable to VPRNs only.";
                        }

                        leaf total-tx-s-pmsis {
                            type yang:counter32;
                            description
                                "The number of MDTs created by the PE for forwarding packets. This object is applicable to
                                 VPRNs only.";
                        }

                        leaf total-rx-s-pmsis {
                            type yang:counter32;
                            description
                                "The number of MDTs created by the PE for receiving packets. This object is applicable to
                                 VPRNs only.";
                        }

                        leaf sg-count {
                            type yang:gauge32;
                            description
                                "The number of entries in 'display router/(service vprn) pim ipv4/6 sg'
                                 for which 'type' is 'sg'.";
                        }

                        leaf star-g-count {
                            type yang:gauge32;
                            description
                                "The number of entries in 'display router/(service vprn) pim ipv4/6 sg'
                                 for which 'type' is 'starG'.";
                        }

                        leaf star-star-rp-count {
                            type yang:gauge32;
                            description
                                "The number of entries in 'display router/(service vprn) pim ipv4/6 sg'
                                 for which 'type' is 'starStarRP'.";
                        }

                        leaf tx-register-ttl-drops {
                            type yang:counter32;
                            description
                                "The number of multicast data packets which could not be encapsulated in Register
                                 messages because the Time To Live (TTL) was zero.";
                        }

                        leaf rx-intra-as-ad {
                            type yang:counter32;
                            description "The number of Intra AS AD routes received on this interface.";
                        }

                        leaf tx-intra-as-ad {
                            type yang:counter32;
                            description "The number of Intra AS AD routes transmitted on this interface.";
                        }

                        leaf rx-intra-as-ad-errors {
                            type yang:counter32;
                            description
                                "The number of errors while processing Intra AS AD routes received on this
                                 interface.";
                        }

                        leaf tx-inter-as-ad {
                            type yang:counter32;
                            description
                                "The number
                                 of Inter AS AD routes transmitted on this interface.";
                        }

                        leaf rx-inter-as-ad {
                            type yang:counter32;
                            description
                                "The number
                                 of Inter AS AD routes received on this interface.";
                        }

                        leaf rx-inter-as-ad-errors {
                            type yang:counter32;
                            description
                                "The number of errors while processing Inter AS AD routes received on this
                                 interface.";
                        }

                        leaf rx-mdt-safi {
                            type yang:counter32;
                            description
                                "The number
                                 of MDT-SAFI AD routes received on this interface.";
                        }

                        leaf tx-mdt-safi {
                            type yang:counter32;
                            description
                                "The number
                                 of MDT-SAFI AD routes transmitted on this interface.";
                        }

                        leaf rx-mdt-safi-errors {
                            type yang:counter32;
                            description
                                "The number of errors while processing MDT-SAFI AD routes received on this
                                 interface.";
                        }

                        leaf rx-spmsi-ad {
                            type yang:counter32;
                            description "The number of S-PMSI AD routes received on this interface.";
                        }

                        leaf tx-spmsi-ad {
                            type yang:counter32;
                            description "The number of S-PMSI AD routes transmitted on this interface.";
                        }

                        leaf rx-spmsi-ad-errors {
                            type yang:counter32;
                            description
                                "The number of errors while processing S-PMSI AD routes received on
                                 this interface.";
                        }

                        leaf rx-leaf-ad {
                            type yang:counter32;
                            description "The number of Leaf AD routes received on this interface.";
                        }

                        leaf tx-leaf-ad {
                            type yang:counter32;
                            description "The number of Leaf AD routes transmitted on this interface.";
                        }

                        leaf rx-leaf-ad-errors {
                            type yang:counter32;
                            description
                                "The number of errors while processing Leaf AD routes received on
                                 this interface.";
                        }

                        leaf rx-source-active-ad {
                            type yang:counter32;
                            description "The number of Source Active AD routes received on this interface.";
                        }

                        leaf tx-source-active-ad {
                            type yang:counter32;
                            description "The number of Source Active AD routes transmitted on this interface.";
                        }

                        leaf tx-source-active-ad-errors {
                            type yang:counter32;
                            description
                                "The number of errors while processing Source Active AD routes received
                                 on this interface.";
                        }

                        leaf rx-shared-tree-join {
                            type yang:counter32;
                            description "The number of Shared Tree Joins received on this interface.";
                        }

                        leaf tx-shared-tree-join {
                            type yang:counter32;
                            description "The number of Shared Tree Joins transmitted on this interface.";
                        }

                        leaf rx-shared-tree-join-errors {
                            type yang:counter32;
                            description
                                "The number of errors while processing Shared Tree Joins received
                                 on this interface.";
                        }

                        leaf rx-source-tree-join {
                            type yang:counter32;
                            description "The number of Source Tree Joins received on this interface.";
                        }

                        leaf tx-source-tree-join {
                            type yang:counter32;
                            description "The number of Source Tree Joins transmitted on this interface.";
                        }

                        leaf rx-source-tree-join-errors {
                            type yang:counter32;
                            description
                                "The number of errors while processing Source Tree Joins received on
                                 this interface.";
                        }

                        leaf rx-bgp-packets {
                            type yang:counter32;
                            description
                                "The number
                                 of BGP Packets received on this interface.";
                        }

                        leaf tx-bgp-packets {
                            type yang:counter32;
                            description
                                "The number
                                 of BGP Packets transmitted on this interface.";
                        }

                    } // container statistics

                } // container ipv6

                list interface {
                    key "interface-name";
                    description "Enter the interface list instance";

                    leaf interface-name {
                        type types-sros:interface-name;
                        description "Service VPRN interface name.";
                    }

                    leaf auto-created-interface {
                        type boolean;
                        description
                            "The value of this object indicates if this interface was
                             auto created.";
                    }

                    leaf extranet-type {
                        type enumeration {
                            enum "rx"                           { value 0; }
                            enum "tx"                           { value 1; }
                            enum "none"                         { value 3; }
                        }
                        description
                            "The value of this object indicates whether the extranet interface
                             is of type transmitter or receiver.";
                    }

                    leaf extranet-mvpn-id {
                        type uint32 {
                            range "0..10240";
                        }
                        description
                            "The value of this object indicates the id associated with the
                             extranet interface. If the interface is not an extranet
                             interface then the value of this object will be '0'.";
                    }

                    leaf oper-state {
                        type types-sros:oper-state;
                        description
                            "The value of the this object indicates the operational
                             state of the destination.";
                    }

                    leaf pmsi-type {
                        type enumeration {
                            enum "none"                         { value 0; }
                            enum "ipmsi-tx"                     { value 1; }
                            enum "ipmsi-rx"                     { value 2; }
                            enum "spmsi-tx"                     { value 3; }
                            enum "spmsi-rx"                     { value 4; }
                        }
                        description
                            "The value of this object indicates the type of the tunnel
                             interface.";
                    }

                    container i-pmsi {
                        description "Inclusive provider-network multicast service interface (I-PMSI)";

                        container ldp {
                            description
                                "The list of Ldp Inclusive Provider-Network Multicast Service
                                 (IPMSI) interfaces.

                                 A PMSI can be thought of as a connector between a set of PE routers 
                                 forming a multicast domain. From the perspective of a VPN-specific 
                                 PIM instance, a PMSI is a single multi-access interface.

                                 IPMSI's are used for transmitting the MVPN's multicast data from one
                                 PE to others.";

                            leaf root-address {
                                type types-sros:ip-address;
                                description "The root address for the PMSI.";
                            }

                            leaf lsp-id {
                                type uint32;
                                description "The lsp identifier associated with the PMSI.";
                            }

                            leaf lsp-name {
                                type types-sros:named-item;
                                description "The lsp name associated with the PMSI.";
                            }

                        } // container ldp

                        container rsvp {
                            description
                                "The list of RSVP Inclusive Provider-Network Multicast Service
                                 (IPMSI) interfaces.

                                 A PMSI can be thought of as a connector between a set of PE routers 
                                 forming a multicast domain. From the perspective of a VPN-specific 
                                 PIM instance, a PMSI is a single multi-access interface.

                                 IPMSI's are used for transmitting the MVPN's multicast data from one
                                 PE to others.";

                            leaf extended-tunnel-address {
                                type types-sros:ip-address;
                                description "The extended tunnel address for the PMSI.";
                            }

                            leaf lsp-name {
                                type types-sros:named-item;
                                description
                                    "The indicates the the RSVP point to multipoint (P2MP)
                                     lsp name associated with this IPMSI.

                                     In case of terminating IPMSIs the indicates the name of the
                                     tunnel interface.";
                            }

                            leaf p2mp-id {
                                type uint32;
                                description "The P2MP Identifier associated with this PMSI.";
                            }

                            leaf tunnel-id {
                                type uint32;
                                description "The tunnel identifier associated with this PMSI.";
                            }

                        } // container rsvp

                        container bier {
                            description
                                "The list of Bier Inclusive Provider-Network Multicast Service
                                 (IPMSI) interfaces.

                                 A PMSI can be thought of as a connector between a set of PE routers 
                                 forming a multicast domain. From the perspective of a VPN-specific 
                                 PIM instance, a PMSI is a single multi-access interface.

                                 IPMSI's are used for transmitting the MVPN's multicast data from one
                                 PE to others.";

                            leaf root-address {
                                type types-sros:ip-address;
                                description "The tunnel root address of the PMSI.";
                            }

                            leaf subdomain-id {
                                type uint32;
                                description "The BIER sub-domain ID.";
                            }

                            leaf bfr-id {
                                type uint32;
                                description "The BFR ID.";
                            }

                            leaf mpls-label {
                                type uint32;
                                description "The MPLS service label for the PMSI.";
                            }

                        } // container bier

                    } // container i-pmsi

                    container s-pmsi {
                        description "Selective provider-network multicast service interface (S-PMSI) configuration";

                        container ldp {
                            description
                                "The list of the LDP Provider-Network Multicast Service (PMSI) interfaces.

                                 A PMSI can be thought of as a connector between a set of PE routers
                                 forming a multicast domain. From the perspective of a VPN-specific
                                 PIM instance, a PMSI is a single multi-access interface.

                                 A PMSI interface is created whenever the threshold of a (C-S,C-G)
                                 exceeds the configured threshold value specified by Multicast Data Tunnel thresholds.
                                 If the data-threshold goes below the value specified by
                                 Multicast Data Tunnel thresholds, the PMSI interface is automatically deleted.";

                            leaf root-address {
                                type types-sros:ip-address;
                                description "The root address for the PMSI.";
                            }

                            leaf lsp-id {
                                type uint32;
                                description "The lsp identifier associated with the PMSI.";
                            }

                            leaf lsp-name {
                                type types-sros:named-item;
                                description "The lsp name associated with the PMSI.";
                            }

                        } // container ldp

                        container rsvp {
                            description
                                "The list of the RSVP Provider-Network Multicast Service (PMSI) interfaces.

                                 A PMSI can be thought of as a connector between a set of PE routers
                                 forming a Multicast Domain. From the perspective of a VPN-specific
                                 PIM instance, a PMSI is a single multi-access interface.

                                 A PMSI interface is created whenever the threshold of a (C-S,C-G)
                                 exceeds the configured threshold value specified by Multicast Data Tunnel thresholds.
                                 If the data-threshold goes below the value specified by
                                 Multicast Data Tunnel thresholds, the PMSI interface is automatically deleted.";

                            leaf extended-tunnel-address {
                                type types-sros:ip-address;
                                description "The extended tunnel address for the PMSI.";
                            }

                            leaf lsp-name {
                                type types-sros:named-item;
                                description
                                    "The indicates the the RSVP point to multipoint (P2MP)
                                     lsp name associated with this IPMSI.

                                     In case of terminating IPMSIs the indicates the name of the
                                     tunnel interface.";
                            }

                            leaf p2mp-id {
                                type uint32;
                                description "The P2MP Identifier associated with this PMSI.";
                            }

                            leaf tunnel-id {
                                type uint32;
                                description "The tunnel identifier associated with this PMSI.";
                            }

                        } // container rsvp

                        container bier {
                            description
                                "The list of Bier Provider-Network Multicast Service (PMSI) interfaces.

                                 A PMSI can be thought of as a connector between a set of PE routers 
                                 forming a multicast domain. From the perspective of a VPN-specific 
                                 PIM instance, a PMSI is a single multi-access interface.

                                 PMSI's are used for transmitting the MVPN's multicast data from one
                                 PE to others.";

                            leaf root-address {
                                type types-sros:ip-address;
                                description "The tunnel root address of the PMSI.";
                            }

                            leaf subdomain-id {
                                type uint32;
                                description "The BIER sub-domain ID.";
                            }

                            leaf bfr-id {
                                type uint32;
                                description "The BFR ID.";
                            }

                            leaf mpls-label {
                                type uint32;
                                description "The MPLS service label for the PMSI.";
                            }

                            leaf lsp-name {
                                type types-sros:named-item;
                                description "The lsp name associated with the PMSI.";
                            }

                        } // container bier

                    } // container s-pmsi

                    container ipv4 {
                        description "Enter the ipv4 context";

                        leaf max-groups-till-now {
                            type yang:counter32;
                            description "The highest value that Current Groups had till now.";
                        }

                        leaf oper-state {
                            type types-sros:oper-state;
                            description
                                "The current operational state associated with this address family
                                 for PIM protocol on this interface.";
                        }

                        leaf designated-router {
                            type types-sros:ip-address;
                            description "Designated router IP address.";
                        }

                        leaf oper-dr-priority {
                            type uint32;
                            description "Operational DR priority.";
                        }

                        leaf time-to-next-hello {
                            type uint32;
                            description "Time for next hello.";
                        }

                        leaf tracking-support-oper-state {
                            type types-sros:up-down-status;
                            description "J/P Tracking support operational state.";
                        }

                        container statistics {
                            description "The PIM statistics for a particular interface.";

                            leaf rx-hellos {
                                type yang:counter32;
                                description "The number of PIM hello messages received on this interface.";
                            }

                            leaf tx-hellos {
                                type yang:counter32;
                                description "The number of PIM Hello messages transmitted on this interface.";
                            }

                            leaf rx-hellos-dropped {
                                type yang:counter32;
                                description
                                    "The number of PIM Hello messages which were received on this interface but were
                                     dropped.";
                            }

                            leaf rx-join-prunes {
                                type yang:counter32;
                                description
                                    "The number of PIM
                                     Join Prune messages received on this interface.";
                            }

                            leaf tx-join-prunes {
                                type yang:counter32;
                                description
                                    "The number of PIM
                                     Join Prune messages transmitted on this interface.";
                            }

                            leaf rx-join-prune-errors {
                                type yang:counter32;
                                description
                                    "The number of errors while processing Join-Prune messages received on this
                                     interface.";
                            }

                            leaf rx-mvpn-rpfv-jp {
                                type yang:counter32;
                                description
                                    "The number of PIM
                                     Join Prune messages received on this interface which were propagated
                                     using RPF vectors for the MVPN.";
                            }

                            leaf tx-mvpn-rpfv-jp {
                                type yang:counter32;
                                description
                                    "The number of PIM
                                     Join Prune messages transmitted on this interface which were propagated
                                     using RPF vectors for the MVPN.";
                            }

                            leaf rx-invalid-mvpn-rpfv-jp {
                                type yang:counter32;
                                description
                                    "The number of invalid PIM Join Prune messages received on this interface which were
                                     propagated using RPF vectors for the MVPN.";
                            }

                            leaf rx-asserts {
                                type yang:counter32;
                                description "The number of PIM Assert messages received on this interface.";
                            }

                            leaf tx-asserts {
                                type yang:counter32;
                                description "The number of PIM Assert messages transmitted on this interface.";
                            }

                            leaf rx-assert-errors {
                                type yang:counter32;
                                description "The number of errors while processing Assert messages received on this interface.";
                            }

                            leaf rx-registers {
                                type yang:counter32;
                                description "The number of PIM Register messages received on this interface.";
                            }

                            leaf rx-register-errors {
                                type yang:counter32;
                                description "The number of errors while processing Register messages received on this interface.";
                            }

                            leaf rx-null-registers {
                                type yang:counter32;
                                description "The number of PIM Null Register messages received on this interface.";
                            }

                            leaf rx-register-stops {
                                type yang:counter32;
                                description "The number of PIM Register Stop messages received on this interface.";
                            }

                            leaf tx-register-stops {
                                type yang:counter32;
                                description "The number of PIM Register Stop messages transmitted on this interface.";
                            }

                            leaf rx-register-stop-errors {
                                type yang:counter32;
                                description
                                    "The number of errors while processing Register Stop messages received on this
                                     interface.";
                            }

                            leaf tx-register-stop-errors {
                                type yang:counter32;
                                description
                                    "The number of PIM errors while trasmitting PIM Register Stop messages
                                     on this interface.";
                            }

                            leaf rx-bsm-pdus {
                                type yang:counter32;
                                description "The number of PIM Bootstrap Messages (BSM) received on this interface.";
                            }

                            leaf tx-bsm-pdus {
                                type yang:counter32;
                                description "The number of PIM Bootstrap Messages (BSM) transmitted on this interface.";
                            }

                            leaf rx-bsm-pdu-drops {
                                type yang:counter32;
                                description "The number of PIM Bootstrap Messages (BSM) received on this interface but were dropped.";
                            }

                            leaf tx-bsm-errors {
                                type yang:counter32;
                                description "The number of errors while transmitting PIM Bootstrap Messages (BSM) on this interface.";
                            }

                            leaf rx-auto-rp-announce {
                                type yang:counter32;
                                description "The number Auto-RP announcements received on this interface.";
                            }

                            leaf tx-auto-rp-announce {
                                type yang:counter32;
                                description "The number of Auto-RP announcements transmitted on this interface.";
                            }

                            leaf rx-auto-rp-announce-errors {
                                type yang:counter32;
                                description
                                    "The number of errors while processing Auto-RP announcements received on
                                     this interface.";
                            }

                            leaf tx-auto-rp-announce-errors {
                                type yang:counter32;
                                description
                                    "The number of errors while transmitting Auto-RP announcements on this
                                     interface.";
                            }

                            leaf rx-auto-rp-mapping {
                                type yang:counter32;
                                description "The number of Auto-RP mappings received on this interface.";
                            }

                            leaf tx-auto-rp-mapping {
                                type yang:counter32;
                                description "The number of Auto-RP mappings transmitted on this interface.";
                            }

                            leaf rx-auto-rp-mapping-errors {
                                type yang:counter32;
                                description
                                    "The number of errors while processing Auto-RP mappings received on this
                                     interface.";
                            }

                            leaf tx-auto-rp-mapping-errors {
                                type yang:counter32;
                                description
                                    "The number of errors while transmitting Auto-RP mappings on this
                                     interface.";
                            }

                            leaf rx-grafts {
                                type yang:counter32;
                                description "The number of graft messages which were received on this interface.";
                            }

                            leaf tx-grafts {
                                type yang:counter32;
                                description "The number of graft messages which were transmitted from this interface.";
                            }

                            leaf rx-graft-errors {
                                type yang:counter32;
                                description "The number of invalid graft messages which were received on this interface.";
                            }

                            leaf rx-graft-acks {
                                type yang:counter32;
                                description "The number of graft acknowledgement messages which were received on this interface.";
                            }

                            leaf tx-graft-acks {
                                type yang:counter32;
                                description
                                    "The number of graft acknowledgement messages which were transmitted from this
                                     interface.";
                            }

                            leaf rx-graft-ack-errors {
                                type yang:counter32;
                                description
                                    "The number of invalid graft acknowledgement messages which were received on this
                                     interface.";
                            }

                            leaf rx-packets {
                                type yang:counter32;
                                description "The number of multicast data packets received on this interface.";
                            }

                            leaf tx-packets {
                                type yang:counter32;
                                description "The number of multicast data packets transmitted on this interface.";
                            }

                            leaf rx-invalid-registers {
                                type yang:counter32;
                                description
                                    "The number of invalid PIM Register messages received on this interface

                                     A Register message is invalid when the RP address in the message
                                     is not the RP for the group specified in the message. If such a message
                                     arrives, a Invalid Register notification is sent.";
                            }

                            leaf rx-neighbor-unknown {
                                type yang:counter32;
                                description
                                    "The number of PIM messages (other than Hello messages) which were received on this
                                     interface and were rejected because the adjacency with the neighbor
                                     router was not already established.";
                            }

                            leaf rx-bad-checksum-discard {
                                type yang:counter32;
                                description
                                    "The number of PIM messages received on this interface which were discarded because
                                     of bad checksum.";
                            }

                            leaf rx-bad-encodings {
                                type yang:counter32;
                                description "The number of PIM messages with bad encodings received on this interface.";
                            }

                            leaf rx-bad-version-discard {
                                type yang:counter32;
                                description "The number of PIM messages with bad versions received on this interface.";
                            }

                            leaf rx-candidate-rp-adv-no-router-alert {
                                type yang:counter32;
                                description
                                    "The number of Candidate-RP Advertisements(C-RP-Adv) received on this interface
                                     which had no router alert option set.";
                            }

                            leaf rx-bsm-no-router-alert-drops {
                                type yang:counter32;
                                description
                                    "The number
                                     of BSM messages that were dropped because router alert option was not
                                     present.";
                            }

                            leaf rx-bsm-wrong-interface-drops {
                                type yang:counter32;
                                description
                                    "The number of BSM messages that were dropped either because they were not sent by
                                     the correct RPF neighbor or because they arrived on the
                                     wrong interface.";
                            }

                            leaf rx-invalid-join-prunes {
                                type yang:counter32;
                                description
                                    "The number of invalid PIM Join Prune messages received on this interface

                                     A Join Prune message is invalid when the RP address in the message
                                     is not the RP for the group specified in the message. If such a message
                                     arrives, a Invalid Join Prune notification is sent.";
                            }

                            leaf rx-invalid-auto-rp-pdu {
                                type yang:counter32;
                                description
                                    "The number of errors while processing Auto-RP messages received on this
                                     interface.";
                            }

                            leaf rx-auto-rp-mapping-rpf-mismatch {
                                type yang:counter32;
                                description
                                    "The number of times an Auto-RP mapping message was received on this interface
                                     other than the RPF interface.";
                            }

                            leaf rx-auto-rp-announcement-rpf-mismatch {
                                type yang:counter32;
                                description
                                    "The number of times an Auto-RP announcement message was received on this interface
                                     other than the RPF interface.";
                            }

                            leaf rx-unknown-pdu-type {
                                type yang:counter32;
                                description "The number of packets received with an unsupported PIM type.";
                            }

                            leaf join-policy-drops {
                                type yang:counter32;
                                description
                                    "The number of times the join policy match resulted in dropping PIM Join-Prune
                                     Message or one of the source group contained in the message.";
                            }

                            leaf register-policy-drops {
                                type yang:counter32;
                                description
                                    "The number of times the register policy match resulted in dropping PIM Register
                                     Message.";
                            }

                            leaf bootstrap-import-policy-drops {
                                type yang:counter32;
                                description
                                    "The number of Bootstrap Messages received on this interface but were dropped
                                     because of Bootstrap import policy.";
                            }

                            leaf bootstrap-export-policy-drops {
                                type yang:counter32;
                                description
                                    "The number of Bootstrap Messages that were not transmitted on this interface
                                     because of Bootstrap export policy.";
                            }

                            leaf mcac-policy-drops {
                                type yang:counter32;
                                description
                                    "The number times a PIM Group is dropped because of applying a
                                     multicast CAC policy on this interface.";
                            }

                            leaf sg-count {
                                type yang:gauge32;
                                description
                                    "The number of entries in 'display router/(service vprn) pim interface ipv4/6 sg'
                                     for which type is 'sg'.";
                            }

                            leaf star-g-count {
                                type yang:gauge32;
                                description
                                    "The number of entries in 'display router/(service vprn) pim interface ipv4/6 sg'
                                     for which type is 'starG'.";
                            }

                            leaf star-star-rp-count {
                                type yang:gauge32;
                                description
                                    "The number of entries in 'display router/(service vprn) pim interface ipv4/6 sg'
                                     for which type is 'starStarRP'.";
                            }

                        } // container statistics

                        list neighbor {
                            key "neighbor-address";
                            description "List of the router's PIM neighbors on an interface.";

                            leaf neighbor-address {
                                type types-sros:ipv4-address;
                                description "This value indicates the IPv4 address of the PIM neighbor.";
                            }

                            leaf dr-priority {
                                type uint32;
                                description
                                    "This value indicates neighbor's DR priority which is received
                                     in the hello message. If the Hello Message did not contain
                                     the DR priority field, the value of priority will be '1'.";
                            }

                            leaf dr-priority-present {
                                type boolean;
                                description
                                    "This value of indicates whether the DR priority field was present
                                     in the Hello message received from the PIM neighbor.";
                            }

                            leaf tracking-support {
                                type boolean;
                                description
                                    "This value indicates whether the T bit in the LAN Prune Delay
                                     option was present in the Hello message. This indicates the
                                     neighbor's capability to disable Join message suppression.";
                            }

                            leaf lan-delay {
                                type uint32;
                                units "milliseconds";
                                description
                                    "This value indicates the value of lan delay field present in
                                     the Hello message received from the neighbor. ";
                            }

                            leaf lan-delay-present {
                                type boolean;
                                description
                                    "This value indicates whether the Hello message received from
                                     the neighbor contained the Lan Delay field.";
                            }

                            leaf generated-id {
                                type uint32;
                                description
                                    "This value indicates a randomly generated 32-bit value that is
                                     regenerated each time PIM forwarding is started or restarted on
                                     the interface, including when the router itself restarts.";
                            }

                            leaf override-interval {
                                type uint32;
                                units "milliseconds";
                                description
                                    "This value indicates the value of the override interval present
                                     in the Hello message.";
                            }

                            leaf up-time {
                                type uint32;
                                units "seconds";
                                description
                                    "This value indicates the time since this PIM neighbor (last)
                                     became a neighbor of the local router.";
                            }

                            leaf expiry-time {
                                type uint32;
                                units "seconds";
                                description
                                    "This value indicates the minimum time remaining before this
                                     PIM neighbor will be aged out.";
                            }

                            leaf hold-time {
                                type uint32;
                                units "seconds";
                                description
                                    "This value indicates the value of the hold time present in the
                                     Hello message.";
                            }

                            leaf join-attribute-support {
                                type boolean;
                                description
                                    "This value indicates whether the Hello Message received from
                                     the neighbor contained the Join Attribute field.";
                            }

                            list secondary-neighbor {
                                key "secondary-neighbor-address";
                                description "Each entry represents the secondary addresses advertised by PIM neighbor.";

                                leaf secondary-neighbor-address {
                                    type types-sros:ipv4-address;
                                    description
                                        "This value indicates the IPv4 address of the secondary PIM
                                         neighbor.";
                                }

                            } // list secondary-neighbor

                        } // list neighbor

                        list sg {
                            key "type group-address source-address";
                            description
                                "List of the (*,*,RP), (*,G) and (S,G) and (S,G,rpt)
                                 entries for which this particular interface has state.";

                            leaf type {
                                type enumeration {
                                    enum "star-star-rp"                 { value 0; }
                                    enum "star-g"                       { value 1; }
                                    enum "sg"                           { value 2; }
                                }
                                description "The type of this entry.";
                            }

                            leaf group-address {
                                type types-sros:ipv4-multicast-address;
                                description
                                    "The multicast group address of the entry. It will be zero if the
                                     'type' is 'star-star-rp'.";
                            }

                            leaf source-address {
                                type types-sros:ipv4-address;
                                description
                                    "The source address of the multicast sender. It will be zero if the
                                     leaf 'type' value is 'star-g' and it will be the address of
                                     the Rendezvous Point(RP) if the leaf 'type' value is 'star-star-rp'.";
                            }

                            leaf up-time {
                                type uint32;
                                units "seconds";
                                description "The time since this source group entry got created.";
                            }

                            leaf join-prune-state {
                                type types-pim:join-prune-state;
                                description
                                    "The Join Prune state for this entry on the interface.

                                     PIM Join or Prune messages are sent by the downstream routers
                                     towards the RPF' neighbor.";
                            }

                            leaf join-prune-timer {
                                type uint32;
                                units "seconds";
                                description
                                    "The time remaining before the router transitions the value of
                                     join-prune-state to 'no-info'.

                                     The timer is started or restarted when a valid Join message is
                                     received. If the value of this object is zero and
                                     join-prune-state is 'join' state, it means that the
                                     downstream router sent a holdtime of '0xffff'. In this case,
                                     join-prune-state will not transition until an appropriate
                                     cancelling of Join or Prune message is received.";
                            }

                            leaf prune-pending-timer {
                                type uint32;
                                units "seconds";
                                description
                                    "The time remaining before the router transitions the value of
                                     join-prune-state to 'no-info'.

                                     The timer is set when the PIM Prune message is received.";
                            }

                            leaf join-prune-rpt-state {
                                type types-pim:join-prune-state;
                                description
                                    "The Join Prune Rpt state for this entry on the interface.

                                     PIM Join or Prune messages are sent by the downstream routers towards the
                                     RPF' neighbor. (S,G,rpt) state is a result of receiving (S,G, rpt) JP message
                                     from the downstream router on the RP tree.";
                            }

                            leaf join-prune-rpt-timer {
                                type uint32;
                                units "seconds";
                                description
                                    "The time remaining before the router transitions the value of
                                     join-prune-rpt-state to 'no-info'.

                                     The timer is started or restarted when a valid Join message is
                                     received. If the value of this object is zero and
                                     join-prune-rpt-state is in 'join' state, it means that the
                                     downstream router sent a holdtime of '0xffff'. In this case,
                                     join-prune-rpt-state will not transition until an appropriate
                                     cancelling of Join or Prune message is received from the
                                     downstream router.";
                            }

                            leaf join-prune-rpt-pending-timer {
                                type uint32;
                                units "seconds";
                                description
                                    "The time remaining before the router transitions the value of
                                     join-prune-rpt-state to 'no-info'.

                                     The timer is set when the (S,G,rpt) PIM Prune message is received.";
                            }

                            leaf rp-address {
                                type types-sros:ip-address;
                                description "The address of the Rendezvous Point(RP).";
                            }

                            leaf assert-state {
                                type enumeration {
                                    enum "no-info"                      { value 0; }
                                    enum "lost-assert"                  { value 1; }
                                    enum "won-assert"                   { value 2; }
                                }
                                description
                                    "The ASSERT state for this entry.

                                     Where multiple PIM routers peer over a shared LAN it  possible
                                     for more than one upstream router to have valid forwarding state
                                     for a packet, which can lead to packet duplication. PIM does not
                                     attempt to prevent this from occurring. Instead it detects when this
                                     has happened and elects a single forwarder amongst the upstream
                                     routers to prevent further duplication. This election is performed
                                     using PIM Assert messages.  Assert messages are also received by
                                     downstream routers on the LAN, and these cause subsequent Join or
                                     Prune messages to be sent to the upstream router that won the Assert.";
                            }

                            leaf assert-timer {
                                type uint32;
                                units "seconds";
                                description
                                    "If the value of assert-state is 'lost-assert': the time remaining before
                                     the router transitions the assert-state to 'no-info'.
                                     If the value of assert-state is 'won-assert':  the time remaining before
                                     the ASSERT message is resent.";
                            }

                            leaf assert-metric {
                                type uint32;
                                description "The metric associated by the MRIB for the route towards the source or the RP.";
                            }

                            leaf assert-metric-preference {
                                type uint32;
                                description "The preference associated by the MRIB for the route towards the source or the RP.";
                            }

                            leaf assert-rpt-bit {
                                type boolean;
                                description "The value  is 'true' if the RPT bit is set and 'false' when the RPT bit is not set.";
                            }

                            leaf assert-winner-address {
                                type types-sros:ip-address;
                                description "The ASSERT winner's interface IP address.";
                            }

                            leaf assert-winner-metric {
                                type uint32;
                                description
                                    "The ASSERT winner's metric associated by it's MRIB for the route
                                     towards the source or the RP.";
                            }

                            leaf assert-winner-metric-preference {
                                type uint32;
                                description
                                    "The ASSERT winner's preference associated by it's MRIB for the
                                     route towards the source or the RP.";
                            }

                            leaf assert-winner-rpt-bit {
                                type boolean;
                                description "The value is 'true' if the RPT bit is set and 'false' when the RPT bit is not set.";
                            }

                            leaf data-mt-interface-name {
                                type types-sros:interface-name;
                                description
                                    "The interface name of the Multicast Tunnel(MT) interface.

                                     If the value is not set, it indicates that there is no data MT
                                     associated with this group-source interface to forward
                                     multicast traffic into the service provider network.
                                     If the value is set, it indicates the data MT tunnel
                                     that is used to forward multicast traffic into the
                                     service provider network.";
                            }

                        } // list sg

                    } // container ipv4

                    container ipv6 {
                        description "Enter the ipv6 context";

                        leaf max-groups-till-now {
                            type yang:counter32;
                            description "The highest value that Current Groups had till now.";
                        }

                        leaf oper-state {
                            type types-sros:oper-state;
                            description
                                "The current operational state associated with this address family
                                 for PIM protocol on this interface.";
                        }

                        leaf designated-router {
                            type types-sros:ip-address;
                            description "Designated router IP address.";
                        }

                        leaf oper-dr-priority {
                            type uint32;
                            description "Operational DR priority.";
                        }

                        leaf time-to-next-hello {
                            type uint32;
                            description "Time for next hello.";
                        }

                        leaf tracking-support-oper-state {
                            type types-sros:up-down-status;
                            description "J/P Tracking support operational state.";
                        }

                        container statistics {
                            description "The PIM statistics for a particular interface.";

                            leaf rx-hellos {
                                type yang:counter32;
                                description "The number of PIM hello messages received on this interface.";
                            }

                            leaf tx-hellos {
                                type yang:counter32;
                                description "The number of PIM Hello messages transmitted on this interface.";
                            }

                            leaf rx-hellos-dropped {
                                type yang:counter32;
                                description
                                    "The number of PIM Hello messages which were received on this interface but were
                                     dropped.";
                            }

                            leaf rx-join-prunes {
                                type yang:counter32;
                                description
                                    "The number of PIM
                                     Join Prune messages received on this interface.";
                            }

                            leaf tx-join-prunes {
                                type yang:counter32;
                                description
                                    "The number of PIM
                                     Join Prune messages transmitted on this interface.";
                            }

                            leaf rx-join-prune-errors {
                                type yang:counter32;
                                description
                                    "The number of errors while processing Join-Prune messages received on this
                                     interface.";
                            }

                            leaf rx-mvpn-rpfv-jp {
                                type yang:counter32;
                                description
                                    "The number of PIM
                                     Join Prune messages received on this interface which were propagated
                                     using RPF vectors for the MVPN.";
                            }

                            leaf tx-mvpn-rpfv-jp {
                                type yang:counter32;
                                description
                                    "The number of PIM
                                     Join Prune messages transmitted on this interface which were propagated
                                     using RPF vectors for the MVPN.";
                            }

                            leaf rx-invalid-mvpn-rpfv-jp {
                                type yang:counter32;
                                description
                                    "The number of invalid PIM Join Prune messages received on this interface which were
                                     propagated using RPF vectors for the MVPN.";
                            }

                            leaf rx-asserts {
                                type yang:counter32;
                                description "The number of PIM Assert messages received on this interface.";
                            }

                            leaf tx-asserts {
                                type yang:counter32;
                                description "The number of PIM Assert messages transmitted on this interface.";
                            }

                            leaf rx-assert-errors {
                                type yang:counter32;
                                description "The number of errors while processing Assert messages received on this interface.";
                            }

                            leaf rx-registers {
                                type yang:counter32;
                                description "The number of PIM Register messages received on this interface.";
                            }

                            leaf rx-register-errors {
                                type yang:counter32;
                                description "The number of errors while processing Register messages received on this interface.";
                            }

                            leaf rx-null-registers {
                                type yang:counter32;
                                description "The number of PIM Null Register messages received on this interface.";
                            }

                            leaf rx-register-stops {
                                type yang:counter32;
                                description "The number of PIM Register Stop messages received on this interface.";
                            }

                            leaf tx-register-stops {
                                type yang:counter32;
                                description "The number of PIM Register Stop messages transmitted on this interface.";
                            }

                            leaf rx-register-stop-errors {
                                type yang:counter32;
                                description
                                    "The number of errors while processing Register Stop messages received on this
                                     interface.";
                            }

                            leaf tx-register-stop-errors {
                                type yang:counter32;
                                description
                                    "The number of PIM errors while trasmitting PIM Register Stop messages
                                     on this interface.";
                            }

                            leaf rx-bsm-pdus {
                                type yang:counter32;
                                description "The number of PIM Bootstrap Messages (BSM) received on this interface.";
                            }

                            leaf tx-bsm-pdus {
                                type yang:counter32;
                                description "The number of PIM Bootstrap Messages (BSM) transmitted on this interface.";
                            }

                            leaf rx-bsm-pdu-drops {
                                type yang:counter32;
                                description "The number of PIM Bootstrap Messages (BSM) received on this interface but were dropped.";
                            }

                            leaf tx-bsm-errors {
                                type yang:counter32;
                                description "The number of errors while transmitting PIM Bootstrap Messages (BSM) on this interface.";
                            }

                            leaf rx-auto-rp-announce {
                                type yang:counter32;
                                description "The number Auto-RP announcements received on this interface.";
                            }

                            leaf tx-auto-rp-announce {
                                type yang:counter32;
                                description "The number of Auto-RP announcements transmitted on this interface.";
                            }

                            leaf rx-auto-rp-announce-errors {
                                type yang:counter32;
                                description
                                    "The number of errors while processing Auto-RP announcements received on
                                     this interface.";
                            }

                            leaf tx-auto-rp-announce-errors {
                                type yang:counter32;
                                description
                                    "The number of errors while transmitting Auto-RP announcements on this
                                     interface.";
                            }

                            leaf rx-auto-rp-mapping {
                                type yang:counter32;
                                description "The number of Auto-RP mappings received on this interface.";
                            }

                            leaf tx-auto-rp-mapping {
                                type yang:counter32;
                                description "The number of Auto-RP mappings transmitted on this interface.";
                            }

                            leaf rx-auto-rp-mapping-errors {
                                type yang:counter32;
                                description
                                    "The number of errors while processing Auto-RP mappings received on this
                                     interface.";
                            }

                            leaf tx-auto-rp-mapping-errors {
                                type yang:counter32;
                                description
                                    "The number of errors while transmitting Auto-RP mappings on this
                                     interface.";
                            }

                            leaf rx-grafts {
                                type yang:counter32;
                                description "The number of graft messages which were received on this interface.";
                            }

                            leaf tx-grafts {
                                type yang:counter32;
                                description "The number of graft messages which were transmitted from this interface.";
                            }

                            leaf rx-graft-errors {
                                type yang:counter32;
                                description "The number of invalid graft messages which were received on this interface.";
                            }

                            leaf rx-graft-acks {
                                type yang:counter32;
                                description "The number of graft acknowledgement messages which were received on this interface.";
                            }

                            leaf tx-graft-acks {
                                type yang:counter32;
                                description
                                    "The number of graft acknowledgement messages which were transmitted from this
                                     interface.";
                            }

                            leaf rx-graft-ack-errors {
                                type yang:counter32;
                                description
                                    "The number of invalid graft acknowledgement messages which were received on this
                                     interface.";
                            }

                            leaf rx-packets {
                                type yang:counter32;
                                description "The number of multicast data packets received on this interface.";
                            }

                            leaf tx-packets {
                                type yang:counter32;
                                description "The number of multicast data packets transmitted on this interface.";
                            }

                            leaf rx-invalid-registers {
                                type yang:counter32;
                                description
                                    "The number of invalid PIM Register messages received on this interface

                                     A Register message is invalid when the RP address in the message
                                     is not the RP for the group specified in the message. If such a message
                                     arrives, a Invalid Register notification is sent.";
                            }

                            leaf rx-neighbor-unknown {
                                type yang:counter32;
                                description
                                    "The number of PIM messages (other than Hello messages) which were received on this
                                     interface and were rejected because the adjacency with the neighbor
                                     router was not already established.";
                            }

                            leaf rx-bad-checksum-discard {
                                type yang:counter32;
                                description
                                    "The number of PIM messages received on this interface which were discarded because
                                     of bad checksum.";
                            }

                            leaf rx-bad-encodings {
                                type yang:counter32;
                                description "The number of PIM messages with bad encodings received on this interface.";
                            }

                            leaf rx-bad-version-discard {
                                type yang:counter32;
                                description "The number of PIM messages with bad versions received on this interface.";
                            }

                            leaf rx-candidate-rp-adv-no-router-alert {
                                type yang:counter32;
                                description
                                    "The number of Candidate-RP Advertisements(C-RP-Adv) received on this interface
                                     which had no router alert option set.";
                            }

                            leaf rx-bsm-no-router-alert-drops {
                                type yang:counter32;
                                description
                                    "The number
                                     of BSM messages that were dropped because router alert option was not
                                     present.";
                            }

                            leaf rx-bsm-wrong-interface-drops {
                                type yang:counter32;
                                description
                                    "The number of BSM messages that were dropped either because they were not sent by
                                     the correct RPF neighbor or because they arrived on the
                                     wrong interface.";
                            }

                            leaf rx-invalid-join-prunes {
                                type yang:counter32;
                                description
                                    "The number of invalid PIM Join Prune messages received on this interface

                                     A Join Prune message is invalid when the RP address in the message
                                     is not the RP for the group specified in the message. If such a message
                                     arrives, a Invalid Join Prune notification is sent.";
                            }

                            leaf rx-invalid-auto-rp-pdu {
                                type yang:counter32;
                                description
                                    "The number of errors while processing Auto-RP messages received on this
                                     interface.";
                            }

                            leaf rx-auto-rp-mapping-rpf-mismatch {
                                type yang:counter32;
                                description
                                    "The number of times an Auto-RP mapping message was received on this interface
                                     other than the RPF interface.";
                            }

                            leaf rx-auto-rp-announcement-rpf-mismatch {
                                type yang:counter32;
                                description
                                    "The number of times an Auto-RP announcement message was received on this interface
                                     other than the RPF interface.";
                            }

                            leaf rx-unknown-pdu-type {
                                type yang:counter32;
                                description "The number of packets received with an unsupported PIM type.";
                            }

                            leaf join-policy-drops {
                                type yang:counter32;
                                description
                                    "The number of times the join policy match resulted in dropping PIM Join-Prune
                                     Message or one of the source group contained in the message.";
                            }

                            leaf register-policy-drops {
                                type yang:counter32;
                                description
                                    "The number of times the register policy match resulted in dropping PIM Register
                                     Message.";
                            }

                            leaf bootstrap-import-policy-drops {
                                type yang:counter32;
                                description
                                    "The number of Bootstrap Messages received on this interface but were dropped
                                     because of Bootstrap import policy.";
                            }

                            leaf bootstrap-export-policy-drops {
                                type yang:counter32;
                                description
                                    "The number of Bootstrap Messages that were not transmitted on this interface
                                     because of Bootstrap export policy.";
                            }

                            leaf mcac-policy-drops {
                                type yang:counter32;
                                description
                                    "The number times a PIM Group is dropped because of applying a
                                     multicast CAC policy on this interface.";
                            }

                            leaf sg-count {
                                type yang:gauge32;
                                description
                                    "The number of entries in 'display router/(service vprn) pim interface ipv4/6 sg'
                                     for which type is 'sg'.";
                            }

                            leaf star-g-count {
                                type yang:gauge32;
                                description
                                    "The number of entries in 'display router/(service vprn) pim interface ipv4/6 sg'
                                     for which type is 'starG'.";
                            }

                            leaf star-star-rp-count {
                                type yang:gauge32;
                                description
                                    "The number of entries in 'display router/(service vprn) pim interface ipv4/6 sg'
                                     for which type is 'starStarRP'.";
                            }

                        } // container statistics

                        list neighbor {
                            key "neighbor-address";
                            description "List of the router's PIM neighbors on an interface.";

                            leaf neighbor-address {
                                type types-sros:ipv6-address;
                                description "This value indicates the IPv6 address of the PIM neighbor.";
                            }

                            leaf dr-priority {
                                type uint32;
                                description
                                    "This value indicates neighbor's DR priority which is received
                                     in the hello message. If the Hello Message did not contain
                                     the DR priority field, the value of priority will be '1'.";
                            }

                            leaf dr-priority-present {
                                type boolean;
                                description
                                    "This value of indicates whether the DR priority field was present
                                     in the Hello message received from the PIM neighbor.";
                            }

                            leaf tracking-support {
                                type boolean;
                                description
                                    "This value indicates whether the T bit in the LAN Prune Delay
                                     option was present in the Hello message. This indicates the
                                     neighbor's capability to disable Join message suppression.";
                            }

                            leaf lan-delay {
                                type uint32;
                                units "milliseconds";
                                description
                                    "This value indicates the value of lan delay field present in
                                     the Hello message received from the neighbor. ";
                            }

                            leaf lan-delay-present {
                                type boolean;
                                description
                                    "This value indicates whether the Hello message received from
                                     the neighbor contained the Lan Delay field.";
                            }

                            leaf generated-id {
                                type uint32;
                                description
                                    "This value indicates a randomly generated 32-bit value that is
                                     regenerated each time PIM forwarding is started or restarted on
                                     the interface, including when the router itself restarts.";
                            }

                            leaf override-interval {
                                type uint32;
                                units "milliseconds";
                                description
                                    "This value indicates the value of the override interval present
                                     in the Hello message.";
                            }

                            leaf up-time {
                                type uint32;
                                units "seconds";
                                description
                                    "This value indicates the time since this PIM neighbor (last)
                                     became a neighbor of the local router.";
                            }

                            leaf expiry-time {
                                type uint32;
                                units "seconds";
                                description
                                    "This value indicates the minimum time remaining before this
                                     PIM neighbor will be aged out.";
                            }

                            leaf hold-time {
                                type uint32;
                                units "seconds";
                                description
                                    "This value indicates the value of the hold time present in the
                                     Hello message.";
                            }

                            leaf join-attribute-support {
                                type boolean;
                                description
                                    "This value indicates whether the Hello Message received from
                                     the neighbor contained the Join Attribute field.";
                            }

                            list secondary-neighbor {
                                key "secondary-neighbor-address";
                                description "Each entry represents the secondary addresses advertised by PIM neighbor.";

                                leaf secondary-neighbor-address {
                                    type types-sros:ipv6-address;
                                    description
                                        "This value indicates the IPv6 address of the secondary PIM
                                         neighbor.";
                                }

                            } // list secondary-neighbor

                        } // list neighbor

                        list sg {
                            key "type group-address source-address";
                            description
                                "List of the (*,*,RP), (*,G) and (S,G) and (S,G,rpt)
                                 entries for which this particular interface has state.";

                            leaf type {
                                type types-pim:sg-type;
                                description "The type of the SG entry.";
                            }

                            leaf group-address {
                                type types-sros:ipv6-multicast-address;
                                description
                                    "The multicast group address of the entry. It will be zero if the
                                     'type' is 'star-star-rp'.";
                            }

                            leaf source-address {
                                type types-sros:ipv6-address;
                                description
                                    "The source address of the multicast sender. It will be zero if the
                                     leaf 'type' value is 'star-g' and it will be the address of
                                     the Rendezvous Point(RP) if the leaf 'type' value is 'star-star-rp'.";
                            }

                            leaf up-time {
                                type uint32;
                                units "seconds";
                                description "The time since this source group entry got created.";
                            }

                            leaf join-prune-state {
                                type types-pim:join-prune-state;
                                description
                                    "The Join Prune state for this entry on the interface.

                                     PIM Join or Prune messages are sent by the downstream routers
                                     towards the RPF' neighbor.";
                            }

                            leaf join-prune-timer {
                                type uint32;
                                units "seconds";
                                description
                                    "The time remaining before the router transitions the value of
                                     join-prune-state to 'no-info'.

                                     The timer is started or restarted when a valid Join message is
                                     received. If the value of this object is zero and
                                     join-prune-state is 'join' state, it means that the
                                     downstream router sent a holdtime of '0xffff'. In this case,
                                     join-prune-state will not transition until an appropriate
                                     cancelling of Join or Prune message is received.";
                            }

                            leaf prune-pending-timer {
                                type uint32;
                                units "seconds";
                                description
                                    "The time remaining before the router transitions the value of
                                     join-prune-state to 'no-info'.

                                     The timer is set when the PIM Prune message is received.";
                            }

                            leaf join-prune-rpt-state {
                                type types-pim:join-prune-state;
                                description
                                    "The Join Prune Rpt state for this entry on the interface.

                                     PIM Join or Prune messages are sent by the downstream routers towards the
                                     RPF' neighbor. (S,G,rpt) state is a result of receiving (S,G, rpt) JP message
                                     from the downstream router on the RP tree.";
                            }

                            leaf join-prune-rpt-timer {
                                type uint32;
                                units "seconds";
                                description
                                    "The time remaining before the router transitions the value of
                                     join-prune-rpt-state to 'no-info'.

                                     The timer is started or restarted when a valid Join message is
                                     received. If the value of this object is zero and
                                     join-prune-rpt-state is in 'join' state, it means that the
                                     downstream router sent a holdtime of '0xffff'. In this case,
                                     join-prune-rpt-state will not transition until an appropriate
                                     cancelling of Join or Prune message is received from the
                                     downstream router.";
                            }

                            leaf join-prune-rpt-pending-timer {
                                type uint32;
                                units "seconds";
                                description
                                    "The time remaining before the router transitions the value of
                                     join-prune-rpt-state to 'no-info'.

                                     The timer is set when the (S,G,rpt) PIM Prune message is received.";
                            }

                            leaf rp-address {
                                type types-sros:ip-address;
                                description "The address of the Rendezvous Point(RP).";
                            }

                            leaf assert-state {
                                type enumeration {
                                    enum "no-info"                      { value 0; }
                                    enum "lost-assert"                  { value 1; }
                                    enum "won-assert"                   { value 2; }
                                }
                                description
                                    "The ASSERT state for this entry.

                                     Where multiple PIM routers peer over a shared LAN it  possible
                                     for more than one upstream router to have valid forwarding state
                                     for a packet, which can lead to packet duplication. PIM does not
                                     attempt to prevent this from occurring. Instead it detects when this
                                     has happened and elects a single forwarder amongst the upstream
                                     routers to prevent further duplication. This election is performed
                                     using PIM Assert messages.  Assert messages are also received by
                                     downstream routers on the LAN, and these cause subsequent Join or
                                     Prune messages to be sent to the upstream router that won the Assert.";
                            }

                            leaf assert-timer {
                                type uint32;
                                units "seconds";
                                description
                                    "If the value of assert-state is 'lost-assert': the time remaining before
                                     the router transitions the assert-state to 'no-info'.
                                     If the value of assert-state is 'won-assert':  the time remaining before
                                     the ASSERT message is resent.";
                            }

                            leaf assert-metric {
                                type uint32;
                                description "The metric associated by the MRIB for the route towards the source or the RP.";
                            }

                            leaf assert-metric-preference {
                                type uint32;
                                description "The preference associated by the MRIB for the route towards the source or the RP.";
                            }

                            leaf assert-rpt-bit {
                                type boolean;
                                description "The value  is 'true' if the RPT bit is set and 'false' when the RPT bit is not set.";
                            }

                            leaf assert-winner-address {
                                type types-sros:ip-address;
                                description "The ASSERT winner's interface IP address.";
                            }

                            leaf assert-winner-metric {
                                type uint32;
                                description
                                    "The ASSERT winner's metric associated by it's MRIB for the route
                                     towards the source or the RP.";
                            }

                            leaf assert-winner-metric-preference {
                                type uint32;
                                description
                                    "The ASSERT winner's preference associated by it's MRIB for the
                                     route towards the source or the RP.";
                            }

                            leaf assert-winner-rpt-bit {
                                type boolean;
                                description "The value is 'true' if the RPT bit is set and 'false' when the RPT bit is not set.";
                            }

                            leaf data-mt-interface-name {
                                type types-sros:interface-name;
                                description
                                    "The interface name of the Multicast Tunnel(MT) interface.

                                     If the value is not set, it indicates that there is no data MT
                                     associated with this group-source interface to forward
                                     multicast traffic into the service provider network.
                                     If the value is set, it indicates the data MT tunnel
                                     that is used to forward multicast traffic into the
                                     service provider network.";
                            }

                        } // list sg

                    } // container ipv6

                    container mcac {
                        description "Enter the mcac context";

                        leaf in-use-mandatory-bandwidth {
                            type uint32;
                            units "kilobps";
                            description
                                "The in-use bandwidth for the mandatory channels for this
                                 protocol interface instance.";
                        }

                        leaf in-use-optional-bandwidth {
                            type uint32;
                            units "kilobps";
                            description
                                "The in-use bandwidth for the optional channels for this
                                 protocol interface instance.";
                        }

                        leaf available-mandatory-bandwidth {
                            type uint32;
                            units "kilobps";
                            description
                                "The pre-reserved bandwidth for the mandatory channels for
                                 this interface instance.";
                        }

                        leaf available-optional-bandwidth {
                            type uint32;
                            units "kilobps";
                            description "The available bandwidth for this interface instance.";
                        }

                        leaf values-in-transit {
                            type boolean;
                            description
                                "The operational (available and in-use mandatory/optional) value for the
                                 following objects is in transition due to configuration change:
                                 - available-mandatory-bandwidth
                                 - available-bandwidth
                                 - in-use-mandatory-bandwidth
                                 - in-use-optional-bandwidth.";
                        }

                    } // container mcac

                } // list interface

                container rp {
                    description "Enter the rp context";

                    container ipv4 {
                        description "Enter the ipv4 context";

                        container bsr-candidate {
                            description "Enter the bsr-candidate context";

                            leaf bsr-address {
                                type types-sros:ip-address;
                                description "The value of this object indicates the bootstrap address of the router.";
                            }

                            leaf bsr-state {
                                type enumeration {
                                    enum "none"                         { value 0; }
                                    enum "candidate-bsr"                { value 1; }
                                    enum "pending-bsr"                  { value 2; }
                                    enum "elected-bsr"                  { value 3; }
                                    enum "accept-any"                   { value 4; }
                                    enum "accept-preferred"             { value 5; }
                                }
                                description
                                    "The value of this object indicates the state of the router
                                     with respect to the bootstrap mechanism.";
                            }

                            leaf up-time {
                                type uint32;
                                units "seconds";
                                description
                                    "The value of this object indicates the time since
                                     the current E-BSR became the elected BSR.";
                            }

                            leaf expiry-time {
                                type uint32;
                                units "seconds";
                                description
                                    "The value of this object indicates the minimum time remaining
                                     before the elected bootstrap router will be declared down if the
                                     value of bsr-state is not 'elected-bsr'.";
                            }

                            leaf bsr-hash-mask-length {
                                type int32;
                                description "The value of this object indicates the bootstrap hash mask length.";
                            }

                            leaf bsr-rpf-interface {
                                type string {
                                    length "0..32";
                                }
                                description "The RPF interface towards the elected BSR.";
                            }

                            leaf bsr-priority {
                                type uint32 {
                                    range "0..255";
                                }
                                description "The value of this object indicates the bootstrap priority of the router.";
                            }

                            leaf oper-state {
                                type types-sros:oper-state;
                                description
                                    "The value of the this object indicates the operational
                                     state of the destination.";
                            }

                        } // container bsr-candidate

                        container rp-candidate {
                            description "Enter the rp-candidate context";

                            leaf oper-state {
                                type types-sros:oper-state;
                                description
                                    "The value of the this object indicates the operational
                                     state of the destination.";
                            }

                            list advertised {
                                key "group-ip-prefix candidate-ip-address";
                                description
                                    "List of the C-RP's and the group prefixes sent in the C-RP advertisement.

                                     It will be empty on all routers except the elected BSR router.";

                                leaf group-ip-prefix {
                                    type types-sros:ipv4-multicast-prefix;
                                    description
                                        "The range of multicast group addresses for which 'candidate-ip-address' is the
                                         candidate RP.";
                                }

                                leaf candidate-ip-address {
                                    type types-sros:ipv4-address;
                                    description "Candidate RP address.";
                                }

                                leaf priority {
                                    type int32;
                                    description
                                        "The Candidate RP's priority for becoming a Rendezvous Point (RP).

                                         This value is used to elect RP for a group range. A value of 0 is considered as the
                                         highest priority.";
                                }

                                leaf hold-time {
                                    type int32;
                                    units "seconds";
                                    description
                                        "The hold time of the candidate RP.

                                         It is used by the bootstrap router to timeout the RP entries if it does not
                                         listen to another C-RP advertisement within the holdtime period.";
                                }

                                leaf expiry-time {
                                    type uint32;
                                    units "seconds";
                                    description
                                        "The minimum time remaining before the Candidate-RP will be declared down.

                                         If the local router is not the BSR, this value is 0.";
                                }

                            } // list advertised

                        } // container rp-candidate

                        list set {
                            key "type group-ip-prefix candidate-ip-address";
                            description
                                "An entry of this list is created by:
                                 - the elected BSR when it receives the Candidate-RP-Adv messages
                                 - other routers on receiving Bootstrap Message(BSM) sent by the
                                   elected BSR router;
                                 - a router when it receives a Mapping message from the Auto-RP Mapping Agent.";

                            leaf type {
                                type enumeration {
                                    enum "dynamic"                      { value 1; }
                                    enum "static"                       { value 2; }
                                    enum "auto-rp"                      { value 3; }
                                }
                                description
                                    "Whether the entry was learned through the bootstrap mechanism, the
                                     Auto-RP mechanism or if it was statically configured using the
                                     (router|service/vprn)/pim/rp/(ipv4|ipv6)/static/address.";
                            }

                            leaf group-ip-prefix {
                                type types-sros:ipv4-multicast-prefix;
                                description
                                    "The range of multicast group addresses for which 'candidate-ip-address' is the
                                     candidate RP.";
                            }

                            leaf candidate-ip-address {
                                type types-sros:ipv4-address;
                                description "Candidate RP address.";
                            }

                            leaf priority {
                                type int32;
                                description
                                    "The Candidate RP's priority for becoming a Rendezvous Point (RP).

                                     This value is used to elect RP for a group range. A value of 0 is considered as the
                                     highest priority. For static entries, the priority is always 1.";
                            }

                            leaf hold-time {
                                type int32;
                                units "seconds";
                                description
                                    "The hold time of the candidate RP.

                                     It is used by the bootstrap router to timeout the RP entries if it does not
                                     listen to another C-RP advertisement within the holdtime period.
                                     It will be zero for static entries.";
                            }

                            leaf expiry-time {
                                type uint32;
                                units "seconds";
                                description "The minimum time remaining before the RP Set group prefix will be declared down.";
                            }

                        } // list set

                    } // container ipv4

                    container ipv6 {
                        description "Enter the ipv6 context";

                        container bsr-candidate {
                            description "Enter the bsr-candidate context";

                            leaf bsr-address {
                                type types-sros:ip-address;
                                description "The value of this object indicates the bootstrap address of the router.";
                            }

                            leaf bsr-state {
                                type enumeration {
                                    enum "none"                         { value 0; }
                                    enum "candidate-bsr"                { value 1; }
                                    enum "pending-bsr"                  { value 2; }
                                    enum "elected-bsr"                  { value 3; }
                                    enum "accept-any"                   { value 4; }
                                    enum "accept-preferred"             { value 5; }
                                }
                                description
                                    "The value of this object indicates the state of the router
                                     with respect to the bootstrap mechanism.";
                            }

                            leaf up-time {
                                type uint32;
                                units "seconds";
                                description
                                    "The value of this object indicates the time since
                                     the current E-BSR became the elected BSR.";
                            }

                            leaf expiry-time {
                                type uint32;
                                units "seconds";
                                description
                                    "The value of this object indicates the minimum time remaining
                                     before the elected bootstrap router will be declared down if the
                                     value of bsr-state is not 'elected-bsr'.";
                            }

                            leaf bsr-hash-mask-length {
                                type int32;
                                description "The value of this object indicates the bootstrap hash mask length.";
                            }

                            leaf bsr-rpf-interface {
                                type string {
                                    length "0..32";
                                }
                                description "The RPF interface towards the elected BSR.";
                            }

                            leaf bsr-priority {
                                type uint32 {
                                    range "0..255";
                                }
                                description "The value of this object indicates the bootstrap priority of the router.";
                            }

                            leaf oper-state {
                                type types-sros:oper-state;
                                description
                                    "The value of the this object indicates the operational
                                     state of the destination.";
                            }

                        } // container bsr-candidate

                        container rp-candidate {
                            description "Enter the rp-candidate context";

                            leaf oper-state {
                                type types-sros:oper-state;
                                description
                                    "The value of the this object indicates the operational
                                     state of the destination.";
                            }

                            list advertised {
                                key "group-ip-prefix candidate-ip-address";
                                description
                                    "List of the C-RP's and the group prefixes sent in the C-RP advertisement.

                                     It will be empty on all routers except the elected BSR router.";

                                leaf group-ip-prefix {
                                    type types-sros:ipv6-multicast-prefix;
                                    description
                                        "The range of multicast group addresses for which 'candidate-ip-address' is the
                                         candidate RP.";
                                }

                                leaf candidate-ip-address {
                                    type types-sros:ipv6-address;
                                    description "Candidate RP address.";
                                }

                                leaf priority {
                                    type int32;
                                    description
                                        "The Candidate RP's priority for becoming a Rendezvous Point (RP).

                                         This value is used to elect RP for a group range. A value of 0 is considered as the
                                         highest priority.";
                                }

                                leaf hold-time {
                                    type int32;
                                    units "seconds";
                                    description
                                        "The hold time of the candidate RP.

                                         It is used by the bootstrap router to timeout the RP entries if it does not
                                         listen to another C-RP advertisement within the holdtime period.";
                                }

                                leaf expiry-time {
                                    type uint32;
                                    units "seconds";
                                    description
                                        "The minimum time remaining before the Candidate-RP will be declared down.

                                         If the local router is not the BSR, this value is 0.";
                                }

                            } // list advertised

                        } // container rp-candidate

                        list set {
                            key "type group-ip-prefix candidate-ip-address";
                            description
                                "An entry of this list is created by:
                                 - the elected BSR when it receives the Candidate-RP-Adv messages
                                 - other routers on receiving Bootstrap Message(BSM) sent by the
                                   elected BSR router;
                                 - a router when it receives a Mapping message from the Auto-RP Mapping Agent.";

                            leaf type {
                                type enumeration {
                                    enum "dynamic"                      { value 1; }
                                    enum "static"                       { value 2; }
                                    enum "auto-rp"                      { value 3; }
                                }
                                description
                                    "Whether the entry was learned through the bootstrap mechanism, the
                                     Auto-RP mechanism or if it was statically configured using the
                                     (router|service/vprn)/pim/rp/(ipv4|ipv6)/static/address.";
                            }

                            leaf group-ip-prefix {
                                type types-sros:ipv6-multicast-prefix;
                                description
                                    "The range of multicast group addresses for which 'candidate-ip-address' is the
                                     candidate RP.";
                            }

                            leaf candidate-ip-address {
                                type types-sros:ipv6-address;
                                description "Candidate RP address.";
                            }

                            leaf priority {
                                type int32;
                                description
                                    "The Candidate RP's priority for becoming a Rendezvous Point (RP).

                                     This value is used to elect RP for a group range. A value of 0 is considered as the
                                     highest priority. For static entries, the priority is always 1.";
                            }

                            leaf hold-time {
                                type int32;
                                units "seconds";
                                description
                                    "The hold time of the candidate RP.

                                     It is used by the bootstrap router to timeout the RP entries if it does not
                                     listen to another C-RP advertisement within the holdtime period.
                                     It will be zero for static entries.";
                            }

                            leaf expiry-time {
                                type uint32;
                                units "seconds";
                                description "The minimum time remaining before the RP Set group prefix will be declared down.";
                            }

                        } // list set

                    } // container ipv6

                } // container rp

            } // container pim

            container wpp {
                description "Enter the wpp context";

                list portal {
                    key "name";
                    description "Enter the portal list instance";

                    leaf name {
                        type types-sros:named-item;
                        description "WPP portal name";
                    }

                    leaf controlled-router {
                        type types-sros:router-instance;
                        description "The router controlled by this portal.";
                    }

                    leaf enabled-interfaces {
                        type uint32;
                        description
                            "The number of interfaces that are associated with this portal
                             and adminstrative enabled.";
                    }

                    leaf triggered-hosts {
                        type boolean;
                        description "Indicates if triggered hosts are enabled or disabled on this portal.";
                    }

                    list statistics {
                        key "type id";
                        description "The protocol statistics of the portal";

                        leaf type {
                            type enumeration {
                                enum "event"                        { value 1; }
                                enum "dropped"                      { value 2; }
                                enum "accepted"                     { value 3; }
                                enum "original-transmitted"         { value 4; }
                                enum "retransmitted"                { value 5; }
                                enum "forwarded-to-peer"            { value 6; }
                                enum "received-from-peer"           { value 7; }
                            }
                            description "Indicates the statistics type.";
                        }

                        leaf id {
                            type uint32 {
                                range "0..40";
                            }
                            description "The counter id.";
                        }

                        leaf description {
                            type types-sros:display-string {
                                length "1..64";
                            }
                            description "Describes the statistic.";
                        }

                        leaf value {
                            type yang:counter32;
                            description "The value of the counter.";
                        }

                    } // list statistics

                    list host {
                        key "address";
                        description "A host controlled by the portal";

                        leaf address {
                            type types-sros:ipv4-unicast-address;
                            description "The address of the WPP host.";
                        }

                        leaf state {
                            type enumeration {
                                enum "idle"                         { value 1; }
                                enum "challenged"                   { value 2; }
                                enum "authenticating"               { value 3; }
                                enum "authenticated"                { value 4; }
                                enum "established"                  { value 5; }
                                enum "logging-out"                  { value 6; }
                            }
                            description "The state of the WPP host.";
                        }

                        leaf serial-number {
                            type uint32 {
                                range "1..4294967295";
                            }
                            description "The serial number of the WPP host.";
                        }

                        leaf request-id {
                            type uint32 {
                                range "1..4294967295";
                            }
                            description "The request-id of the WPP host.";
                        }

                        leaf remote-port {
                            type inet:port-number;
                            description "The UDP source port used by the portal while sending a message for this host.";
                        }

                        leaf local-address {
                            type types-sros:ipv4-unicast-address;
                            description "The destination address used by the portal while sending a message for this host.";
                        }

                        leaf user-name {
                            type types-sros:display-string;
                            description "The WPP user name of this WPP host.";
                        }

                        leaf service {
                            type types-services:service-name;
                            description "The service to which the WPP host belongs.";
                        }

                        leaf mac-address {
                            type yang:mac-address;
                            description "The mac-address of the WPP host.";
                        }

                        leaf is-triggered {
                            type boolean;
                            description "True if the creation of the host was triggered by the portal, false otherwise.";
                        }

                        leaf track-srrp-instance {
                            type uint32;
                            description
                                "The SRRP instance whose state is tracked by this WPP host to determine if
                                 it is on the MCS master or backup node.";
                        }

                        leaf is-mcs-backup {
                            type boolean;
                            description "True if the WPP host is on the MCS backup node, false otherwise.";
                        }

                    } // list host

                } // list portal

                list statistics {
                    key "type id";
                    description "The Web Portal Protocol statistics.";

                    leaf type {
                        type enumeration {
                            enum "event"                        { value 1; }
                            enum "dropped"                      { value 2; }
                            enum "accepted"                     { value 3; }
                            enum "original-transmitted"         { value 4; }
                            enum "retransmitted"                { value 5; }
                            enum "forwarded-to-peer"            { value 6; }
                            enum "received-from-peer"           { value 7; }
                        }
                        description "Indicates the statistics type.";
                    }

                    leaf id {
                        type uint32 {
                            range "0..40";
                        }
                        description "The counter id.";
                    }

                    leaf description {
                        type types-sros:display-string {
                            length "1..64";
                        }
                        description "Describes the statistic.";
                    }

                    leaf value {
                        type yang:counter32;
                        description "The value of the counter.";
                    }

                } // list statistics

            } // container wpp

            container mvpn {
                description "Enter the mvpn context";

                leaf c-mcast-import-route-target {
                    type types-sros:named-item-or-empty;
                    description "Customer multicast Import Route that uniquely identifies a VRF.";
                }

            } // container mvpn

            container aaa {
                description "Enter the aaa context";

                container remote-servers {
                    description "Enter the remote-servers context";

                    container tacplus {
                        description "Enter the tacplus context";

                        leaf oper-state {
                            type types-sros:up-down-status;
                            description "Current status of aaa server. Is it up if one server is up.";
                        }

                        list server {
                            key "index";
                            description "Enter the server list instance";

                            leaf index {
                                type uint32 {
                                    range "1..5";
                                }
                                description "Identifies a specific TACACS+ server.";
                            }

                            leaf oper-state {
                                type types-sros:up-down-status;
                                description "Operational status of TACACS+ server.";
                            }

                        } // list server

                    } // container tacplus

                    container radius {
                        description "Enter the radius context";

                        leaf oper-state {
                            type types-sros:up-down-status;
                            description "Current status of aaa server. Is it up if one server is up.";
                        }

                        list server {
                            key "index";
                            description "Enter the server list instance";

                            leaf index {
                                type uint32 {
                                    range "1..5";
                                }
                                description "Unique number which identifies a specific RADIUS server.";
                            }

                            leaf oper-state {
                                type types-sros:up-down-status;
                                description "Current status of RADIUS server.";
                            }

                        } // list server

                    } // container radius

                } // container remote-servers

            } // container aaa

            container aggregates {
                description "Enter the aggregates context";

                list aggregate {
                    key "ip-prefix";
                    description "Enter the aggregate list instance";

                    leaf ip-prefix {
                        type types-sros:ip-unicast-prefix;
                        description "Destination IP address prefix of the aggregate route";
                    }

                    leaf oper-state {
                        type types-sros:oper-state;
                        description "Operational state.";
                    }

                } // list aggregate

            } // container aggregates

            list wlan-gw-tunnel {
                key "remote-address local-address";
                description "Tunnels that connect with access points";

                leaf remote-address {
                    type types-sros:ip-address;
                    description "IP address of the remote endpoint (Access Point) of this tunnel";
                }

                leaf local-address {
                    type types-sros:ip-address;
                    description "IP address of the local endpoint of this tunnel";
                }

                leaf established-time {
                    type yang:date-and-time;
                    description "Time when this tunnel was established";
                }

                leaf wlan-gw-group {
                    type types-isa:wlan-gw-group-id;
                    description "WLAN-GW ISA group associated with this tunnel";
                }

                leaf group-member {
                    type types-nat:bb-group-member;
                    description "The member of the WLAN-GW ISA group associated with this tunnel";
                }

                leaf number-of-ues {
                    type uint32;
                    description
                        "Number of User Equipment's connected to this system through
                         this tunnel";
                }

                leaf service {
                    type types-services:service-name;
                    description
                        "Identifier of the service of the WLAN-GW group-interface
                         associated with this tunnel";
                }

                leaf group-interface {
                    type types-sros:interface-name;
                    description "The group-interface associated with this tunnel";
                }

                container access-point {

                    leaf mac-address {
                        type types-sros:mac-address;
                        description "MAC address of the Access Point, as learned by this system";
                    }

                    leaf mac-learn-failed {
                        type boolean;
                        description
                            "Learning of the MAC address of the Access Point via ARPoGRE
                             or NDoGRE failed";
                    }

                } // container access-point

                container l2 {

                    leaf sap {
                        type types-sros:sap;
                        description "The SAP of the L2 Access Point, as learned by this system";
                    }

                    leaf inner-vlan {
                        type types-sros:qtag-full-range;
                        description "Inner tag in case of qinq encapsulation";
                    }

                    leaf outer-vlan {
                        type types-sros:qtag-full-range;
                        description
                            "VLAN tag in case of IEEE 802.1Q encapsulation, or the outer
                             tag in case of qinq encapsulation";
                    }

                } // container l2

                container qos {
                    description "Per tunnel QoS aggregation";

                    leaf oper-state {
                        type types-wlangw:qos-oper-state;
                        description "Operational state of per tunnel QoS enforcement";
                    }

                    leaf remaining-hold-time {
                        type types-sros:time-duration;
                        description
                            "Remaining time before the tunnel QoS is removed when no UEs are
                             active";
                    }

                    container egress-encapsulation-group {
                        description
                            "Egress-encapsulation-group internally used to represent tunnel
                             QoS aggregation";

                        leaf service {
                            type types-services:service-name;
                            description
                                "Name of the internal service where the encap group is
                                 applied";
                        }

                        leaf sap {
                            type types-sros:sap;
                            description "Internal SAP to which the encap-group is applied";
                        }

                        leaf name {
                            type string;
                            description "Name of the encapsulation group";
                        }

                        leaf member {
                            type types-services:isid;
                            description "Encapsulation group member (ISID) used";
                        }

                    } // container egress-encapsulation-group

                    container overrides {
                        description "Dynamic overrides to the QoS parameters";

                        leaf aggregate-rate-limit {
                            type types-qos:queue-pir-rate-override;
                            units "kilobps";
                            description "Overridden aggregate rate limit";
                        }

                        list scheduler {
                            key "name";

                            leaf name {
                                type string;
                                description "Identifier of the overwritten QoS object";
                            }

                            leaf pir {
                                type types-qos:queue-pir-rate-override;
                                units "kilobps";
                                description "Overridden PIR";
                            }

                            leaf cir {
                                type types-qos:queue-cir-rate-override;
                                units "kilobps";
                                description "Overridden CIR";
                            }

                        } // list scheduler

                    } // container overrides

                } // container qos

                list ue {
                    key "bridge-domain mac-address";
                    description "User Equipment information";

                    leaf bridge-domain {
                        type uint32;
                        description
                            "The vRGW Bridge Domain of this UE, 0 denotes no associated
                             bridge or plain WLAN-GW functionality";
                    }

                    leaf mac-address {
                        type types-sros:mac-unicast-address;
                        description "The MAC address of this UE";
                    }

                    leaf vlan {
                        type types-sros:qtag-full-range;
                        description "The VLAN tag present in the traffic received from this UE";
                    }

                    leaf mpls-label {
                        type types-sros:mpls-label-full-range;
                        description "The MPLS label present in the traffic received from this UE";
                    }

                    leaf ssid {
                        type types-wlan:ssid;
                        description "Service Set ID (SSID) of this UE";
                    }

                    leaf previous-access-point-address {
                        type types-sros:ip-address;
                        description "IP address of the previous Access Point of this UE";
                    }

                    leaf last-move-time {
                        type yang:date-and-time;
                        description "Most recent Access Point move of this UE";
                    }

                    leaf service {
                        type types-services:service-name;
                        description
                            "Service identifier of the (internal) SAP associated with
                             this UE";
                    }

                    leaf encapsulation {
                        type types-wlangw:encapsulation;
                        description "Tunnel encapsulation type for this UE";
                    }

                    container session {
                        description "Session identification";

                        leaf subscriber {
                            type types-submgt:subscriber-id;
                            description "Subscriber Identification string";
                        }

                        leaf sla-profile-instance {
                            type types-submgt:sla-profile-instance-id;
                            description "Sla profile instance identifier";
                        }

                        leaf ipoe-session-id {
                            type types-submgt:session-id;
                            description "Session identifier";
                        }

                    } // container session

                } // list ue

                list per-retailer-qos {
                    key "retail-service";
                    description "Per tunnel and service QoS aggregation";

                    leaf retail-service {
                        type types-services:service-name;
                        description "Identifier of the retail service";
                    }

                    leaf oper-state {
                        type types-wlangw:qos-oper-state;
                        description "Operational state of per tunnel QoS enforcement";
                    }

                    leaf number-of-ues {
                        type uint32;
                        description "Number of User Equipment's using this aggregate QoS";
                    }

                    leaf remaining-hold-time {
                        type types-sros:time-duration;
                        description
                            "Remaining time before the tunnel QoS is removed when no UEs are
                             active";
                    }

                    container egress-encapsulation-group {
                        description
                            "Egress-encapsulation-group internally used to represent tunnel
                             QoS aggregation";

                        leaf service {
                            type types-services:service-name;
                            description
                                "Name of the internal service where the encap group is
                                 applied";
                        }

                        leaf sap {
                            type types-sros:sap;
                            description "Internal SAP to which the encap-group is applied";
                        }

                        leaf name {
                            type string;
                            description "Name of the encapsulation group";
                        }

                        leaf member {
                            type types-services:isid;
                            description "Encapsulation group member (ISID) used";
                        }

                    } // container egress-encapsulation-group

                    container overrides {
                        description "Dynamic overrides to the QoS parameters";

                        leaf aggregate-rate-limit {
                            type types-qos:queue-pir-rate-override;
                            units "kilobps";
                            description "Overridden aggregate rate limit";
                        }

                        list scheduler {
                            key "name";

                            leaf name {
                                type string;
                                description "Identifier of the overwritten QoS object";
                            }

                            leaf pir {
                                type types-qos:queue-pir-rate-override;
                                units "kilobps";
                                description "Overridden PIR";
                            }

                            leaf cir {
                                type types-qos:queue-cir-rate-override;
                                units "kilobps";
                                description "Overridden CIR";
                            }

                        } // list scheduler

                    } // container overrides

                } // list per-retailer-qos

            } // list wlan-gw-tunnel

            container bgp {
                description "Enter the bgp context";

                container convergence {
                    description "Enter the convergence context";

                    list family {
                        key "family-type";
                        description "Enter the family list instance";

                        leaf family-type {
                            type enumeration {
                                enum "ipv4"                         { value 1; }
                                enum "ipv6"                         { value 3; }
                            }
                            description "Address family for which convergence selection applies";
                        }

                        leaf up-peers-when-min-expired {
                            type uint16;
                            description
                                "The number of BGP sessions (configured and dynamic) that support the address family and that were in established state
                                 when the win-wait-to-advertise timer expired";
                        }

                        leaf up-peers {
                            type uint32;
                            description
                                "The number of BGP sessions (configured and dynamic) that support the address family and that are currently in the
                                 established state";
                        }

                        leaf converged-peers {
                            type uint32;
                            description "The number of peers that have sent an EOR marker for the address family since the last BGP restart";
                        }

                        leaf first-up-peer-time {
                            type yang:timeticks;
                            description
                                "The time when the first session supporting the address family came up, measured from the time that the BGP
                                 instance restarted";
                        }

                        leaf last-up-peer-time {
                            type yang:timeticks;
                            description
                                "The time when the last session supporting the address family came up, measured from the time that the BGP
                                 instance restarted";
                        }

                        leaf convergence-state {
                            type enumeration {
                                enum "waiting"                      { value 1; description "BGP has recently restarted and no sessions have re-established yet"; }
                                enum "started"                      { value 2; description "BGP has recently restarted and at least one session has re-established with support of the address family"; }
                                enum "partial"                      { value 3; description "BGP has recently restarted and at least one session has advertised an End-of-RIB marker for the address 
                                family."; }
                                enum "timeout"                      { value 4; description "BGP has recently restarted and not all non-slow peers advertised an End-of-RIB marker for the address family 
                                before the max-wait-to-advertise timer expired"; }
                                enum "converged"                    { value 5; description "All non-slow peers that support the address family have have advertised the End-of-RIB marker for the address 
                                family"; }
                            }
                        }

                        leaf convergence-time {
                            type yang:timeticks;
                            description "The elapsed time in seconds, starting from the last BGP restart, to reach the converged state for the address family.";
                        }

                    } // list family

                } // container convergence

                container statistics {

                    leaf operational-state {
                        type string;
                    }

                    leaf peer-groups {
                        type uint32;
                    }

                    leaf peers {
                        type uint32;
                    }

                    leaf vpn-peer-groups {
                        type uint32;
                    }

                    leaf vpn-peers {
                        type uint32;
                    }

                    leaf bgp-paths {
                        type uint32;
                    }

                    leaf path-memory {
                        type uint32;
                    }

                    container routes-per-family {
                        description "Family specific routes counters.";

                        container ipv4 {
                            description "ipv4 counter values.";

                            leaf remote-routes {
                                type uint32;
                            }

                            leaf remote-active-routes {
                                type uint32;
                            }

                            leaf backup-routes {
                                type uint32;
                            }

                        } // container ipv4

                        container ipv6 {
                            description "ipv6 counter values.";

                            leaf remote-routes {
                                type uint32;
                            }

                            leaf remote-active-routes {
                                type uint32;
                            }

                            leaf backup-routes {
                                type uint32;
                            }

                        } // container ipv6

                        container route-flap-dampening {

                            container ipv4-ipv6 {
                                description "flap dampening statistics for ipv4 and ipv6 unicast prefixes.";

                                leaf suppressed-routes {
                                    type uint32;
                                }

                                leaf history-routes {
                                    type uint32;
                                }

                                leaf decay-routes {
                                    type uint32;
                                }

                            } // container ipv4-ipv6

                        } // container route-flap-dampening

                        container mcast-ipv4 {
                            description "mcast-ipv4 counter values.";

                            leaf remote-routes {
                                type uint32;
                            }

                            leaf remote-active-routes {
                                type uint32;
                            }

                            leaf backup-routes {
                                type uint32;
                            }

                        } // container mcast-ipv4

                        container mcast-ipv6 {
                            description "mcast-ipv6 counter values.";

                            leaf remote-routes {
                                type uint32;
                            }

                            leaf remote-active-routes {
                                type uint32;
                            }

                            leaf backup-routes {
                                type uint32;
                            }

                        } // container mcast-ipv6

                        container flow-ipv4 {
                            description "flow-ipv4 counter values.";

                            leaf remote-routes {
                                type uint32;
                            }

                            leaf remote-active-routes {
                                type uint32;
                            }

                            leaf backup-routes {
                                type uint32;
                            }

                        } // container flow-ipv4

                        container flow-ipv6 {
                            description "flow-ipv6 counter values.";

                            leaf remote-routes {
                                type uint32;
                            }

                            leaf remote-active-routes {
                                type uint32;
                            }

                            leaf backup-routes {
                                type uint32;
                            }

                        } // container flow-ipv6

                        container label-ipv4 {
                            description "label-ipv4 counter values.";

                            leaf remote-routes {
                                type uint32;
                            }

                            leaf remote-active-routes {
                                type uint32;
                            }

                            leaf backup-routes {
                                type uint32;
                            }

                        } // container label-ipv4

                    } // container routes-per-family

                } // container statistics

                list neighbor {
                    key "ip-address";
                    description "Enter the neighbor list instance";

                    leaf ip-address {
                        type types-sros:ip-address-with-zone;
                        description "IP address that the neighbor uses to communicate with BGP peers";
                    }

                    container statistics {

                        leaf peer-as {
                            type uint32;
                            description "specifies the AS number for dynamic peers.";
                        }

                        leaf peer-port {
                            type int32;
                            description "specifies the peer's port.";
                        }

                        leaf local-port {
                            type int32;
                            description "specifies the local port on this peer.";
                        }

                        leaf session-state {
                            type string {
                                length "0..32";
                            }
                            description "specifies the current BGP state of this peer.";
                        }

                        leaf last-state {
                            type string {
                                length "0..32";
                            }
                            description "specifies the last BGP state of this peer.";
                        }

                        leaf last-event {
                            type string {
                                length "0..32";
                            }
                            description "specifies the last BGP event of this peer.";
                        }

                        leaf last-error {
                            type string {
                                length "0..80";
                            }
                            description "specifies the last error of this peer.";
                        }

                        leaf-list negotiated-family {
                            type string {
                                length "0..16";
                            }
                            description "specifies the family successfully negotiated with the peer.";
                        }

                        leaf operational-local-address {
                            type types-sros:ip-unicast-address;
                            description "Local IP address used by the neighbor when communicating with BGP peers";
                        }

                        leaf peer-identifier {
                            type string {
                                length "0..16";
                            }
                            description "specifies the peers ip address.";
                        }

                        leaf established-transitions {
                            type uint32;
                            description "specifies the number of state transitions made by the peer.";
                        }

                        leaf last-established-time {
                            type yang:date-and-time;
                            description "specifies the time when the peer established the BGP session.";
                        }

                        leaf in-update-elapsed-time {
                            type yang:timeticks;
                            description "specifies the time elapsed since the last update was received.";
                        }

                        leaf hold-time-interval {
                            type int32;
                            description "specifies the hold time value negotiated with the peer.";
                        }

                        leaf remaining-idle-hold-time {
                            type uint32;
                            description
                                "specifies how much time is remaining until the Idle hold time
                                 period runs out and session establishment can begin again for this peer.";
                        }

                        leaf keep-alive-interval {
                            type int32;
                            description "specifies the keep alive time value negotiated with the peer.";
                        }

                        leaf number-of-update-flaps {
                            type uint32;
                            description "specifies the number of flaps of updates from this peer.";
                        }

                        leaf update-errors {
                            type uint32;
                            description "specifies the number of update errors received from this peer.";
                        }

                        leaf-list negotiated-capability {
                            type string {
                                length "0..16";
                            }
                            description "specifies the capabilities successfully negotiated with the peer.";
                        }

                        leaf received-paths {
                            type uint32;
                            description "specifies the number of paths received from this peer.";
                        }

                        leaf dynamically-configured {
                            type boolean;
                            description "specifies dynamic peer.";
                        }

                        leaf-list convergence-recv-eor {
                            type string {
                                length "0..16";
                            }
                            description "specifies the convergence types that the peer received end of rib marker for.";
                        }

                        leaf-list convergence-sent-eor {
                            type string {
                                length "0..16";
                            }
                            description "specifies the convergence types that the peer sent end of rib marker for.";
                        }

                        leaf convergence-exceeded-min-wait {
                            type enumeration {
                                enum "no"                           { value 1; }
                                enum "yes"                          { value 2; }
                                enum "unknown"                      { value 3; }
                            }
                            description "specifies if the convergence min-wait is exceeded.";
                        }

                        container remote-family {
                            description
                                "specifies the types of routing information to be distributed
                                 by the remote end of this Peer of the BGP protocol.";

                            leaf-list family {
                                type string {
                                    length "0..16";
                                }
                            }

                        } // container remote-family

                        container local-capability {
                            description "specifies the capabilities supported on the local end of the BGP Peer.";

                            leaf-list capability {
                                type string {
                                    length "0..16";
                                }
                                description "specifies the capability name.";
                            }

                        } // container local-capability

                        container remote-capability {
                            description "specifies the capabilities advertised by the remote end of the BGP Peer.";

                            leaf-list capability {
                                type string {
                                    length "0..16";
                                }
                                description "specifies the capability name.";
                            }

                        } // container remote-capability

                        container family-prefix {
                            description "prefix counter values.";

                            container ipv4 {
                                description "ipv4 counter values.";

                                leaf backup {
                                    type uint32;
                                    description "specifies the number routes selected as backup from this peer.";
                                }

                                leaf received {
                                    type uint32;
                                    description "specifies the number of prefixes received from this peer.";
                                }

                                leaf active {
                                    type uint32;
                                    description "specifies the number of active prefixes from this peer.";
                                }

                                leaf suppressed {
                                    type uint32;
                                    description "specifies the number prefixes from this peer, which have been suppressed by damping.";
                                }

                                leaf rejected {
                                    type uint32;
                                    description "specifies the number of prefixes rejected from this peer.";
                                }

                                leaf sent {
                                    type uint32;
                                    description "specifies the number of prefixes transmitted to this peer.";
                                }

                            } // container ipv4

                            container ipv6 {
                                description "ipv6 counter values.";

                                leaf backup {
                                    type uint32;
                                    description "specifies the number routes selected as backup from this peer.";
                                }

                                leaf received {
                                    type uint32;
                                    description "specifies the number of prefixes received from this peer.";
                                }

                                leaf active {
                                    type uint32;
                                    description "specifies the number of active prefixes from this peer.";
                                }

                                leaf suppressed {
                                    type uint32;
                                    description "specifies the number prefixes from this peer, which have been suppressed by damping.";
                                }

                                leaf rejected {
                                    type uint32;
                                    description "specifies the number of prefixes rejected from this peer.";
                                }

                                leaf sent {
                                    type uint32;
                                    description "specifies the number of prefixes transmitted to this peer.";
                                }

                            } // container ipv6

                            container mcast-ipv4 {
                                description "mcast-ipv4 counter values.";

                                leaf backup {
                                    type uint32;
                                    description "specifies the number routes selected as backup from this peer.";
                                }

                                leaf received {
                                    type uint32;
                                    description "specifies the number of prefixes received from this peer.";
                                }

                                leaf active {
                                    type uint32;
                                    description "specifies the number of active prefixes from this peer.";
                                }

                                leaf suppressed {
                                    type uint32;
                                    description "specifies the number prefixes from this peer, which have been suppressed by damping.";
                                }

                                leaf rejected {
                                    type uint32;
                                    description "specifies the number of prefixes rejected from this peer.";
                                }

                                leaf sent {
                                    type uint32;
                                    description "specifies the number of prefixes transmitted to this peer.";
                                }

                            } // container mcast-ipv4

                            container mcast-ipv6 {
                                description "mcast-ipv6 counter values.";

                                leaf backup {
                                    type uint32;
                                    description "specifies the number routes selected as backup from this peer.";
                                }

                                leaf received {
                                    type uint32;
                                    description "specifies the number of prefixes received from this peer.";
                                }

                                leaf active {
                                    type uint32;
                                    description "specifies the number of active prefixes from this peer.";
                                }

                                leaf suppressed {
                                    type uint32;
                                    description "specifies the number prefixes from this peer, which have been suppressed by damping.";
                                }

                                leaf rejected {
                                    type uint32;
                                    description "specifies the number of prefixes rejected from this peer.";
                                }

                                leaf sent {
                                    type uint32;
                                    description "specifies the number of prefixes transmitted to this peer.";
                                }

                            } // container mcast-ipv6

                            container flow-ipv4 {
                                description "flow-ipv4 counter values.";

                                leaf backup {
                                    type uint32;
                                    description "specifies the number routes selected as backup from this peer.";
                                }

                                leaf received {
                                    type uint32;
                                    description "specifies the number of prefixes received from this peer.";
                                }

                                leaf active {
                                    type uint32;
                                    description "specifies the number of active prefixes from this peer.";
                                }

                                leaf suppressed {
                                    type uint32;
                                    description "specifies the number prefixes from this peer, which have been suppressed by damping.";
                                }

                                leaf rejected {
                                    type uint32;
                                    description "specifies the number of prefixes rejected from this peer.";
                                }

                                leaf sent {
                                    type uint32;
                                    description "specifies the number of prefixes transmitted to this peer.";
                                }

                            } // container flow-ipv4

                            container flow-ipv6 {
                                description "flow-ipv6 counter values.";

                                leaf backup {
                                    type uint32;
                                    description "specifies the number routes selected as backup from this peer.";
                                }

                                leaf received {
                                    type uint32;
                                    description "specifies the number of prefixes received from this peer.";
                                }

                                leaf active {
                                    type uint32;
                                    description "specifies the number of active prefixes from this peer.";
                                }

                                leaf suppressed {
                                    type uint32;
                                    description "specifies the number prefixes from this peer, which have been suppressed by damping.";
                                }

                                leaf rejected {
                                    type uint32;
                                    description "specifies the number of prefixes rejected from this peer.";
                                }

                                leaf sent {
                                    type uint32;
                                    description "specifies the number of prefixes transmitted to this peer.";
                                }

                            } // container flow-ipv6

                            container label-ipv4 {
                                description "label-ipv4 counter values.";

                                leaf backup {
                                    type uint32;
                                    description "specifies the number routes selected as backup from this peer.";
                                }

                                leaf received {
                                    type uint32;
                                    description "specifies the number of prefixes received from this peer.";
                                }

                                leaf active {
                                    type uint32;
                                    description "specifies the number of active prefixes from this peer.";
                                }

                                leaf suppressed {
                                    type uint32;
                                    description "specifies the number prefixes from this peer, which have been suppressed by damping.";
                                }

                                leaf rejected {
                                    type uint32;
                                    description "specifies the number of prefixes rejected from this peer.";
                                }

                                leaf sent {
                                    type uint32;
                                    description "specifies the number of prefixes transmitted to this peer.";
                                }

                            } // container label-ipv4

                        } // container family-prefix

                        container sent {
                            description "the counter values for queues, messages, octets, updates sent to the peer.";

                            leaf queues {
                                type uint64;
                            }

                            leaf messages {
                                type uint64;
                            }

                            leaf octets {
                                type uint64;
                            }

                            leaf updates {
                                type uint64;
                            }

                            leaf route-refresh {
                                type uint64;
                            }

                        } // container sent

                        container received {
                            description "the counter values for queues, messages, octets, updates received from the peer.";

                            leaf queues {
                                type uint64;
                            }

                            leaf messages {
                                type uint64;
                            }

                            leaf octets {
                                type uint64;
                            }

                            leaf updates {
                                type uint64;
                            }

                            leaf route-refresh {
                                type uint64;
                            }

                        } // container received

                    } // container statistics

                    container graceful-restart {
                        description "Enter the graceful-restart context";

                        leaf support {
                            type boolean;
                            description "specifies graceful-restart capability signaled by the peer.";
                        }

                        leaf restart-time-requested {
                            type uint32;
                            description "specifies the restart time requested by the peer.";
                        }

                        leaf stale-route-time {
                            type uint32;
                            description "specifies the time value until when stale routes can be used.";
                        }

                        leaf peer-status {
                            type string {
                                length "0..32";
                            }
                            description "specifies the graceful-restart operational status on the peer.";
                        }

                        leaf number-of-restarts {
                            type uint32;
                            description "specifies the number of times the peer has attempted restart.";
                        }

                        leaf last-restart-time {
                            type yang:date-and-time;
                            description "specifies the last time the peer attempted restart.";
                        }

                        container restart-family {
                            description "specifies the AFI/SAFI the peer supports restart for.";

                            leaf-list family {
                                type string {
                                    length "0..16";
                                }
                            }

                        } // container restart-family

                        container forwarding-family {
                            description "specifies the AFI/SAFI the peer saved forwarding for.";

                            leaf-list family {
                                type string {
                                    length "0..16";
                                }
                            }

                        } // container forwarding-family

                        container negotiated-family {
                            description
                                "specifies the capability type of NLRI that NOTIFICATION-triggered
                                 restart is negotiated for by the peer.";

                            leaf-list family {
                                type string {
                                    length "0..16";
                                }
                            }

                        } // container negotiated-family

                        container received-end-of-rib-marker {
                            description "specifies the NLRI types that the peer received end of rib marker for.";

                            leaf-list family {
                                type string {
                                    length "0..16";
                                }
                            }

                        } // container received-end-of-rib-marker

                        container sent-end-of-rib-marker {
                            description "specifies the NLRI types the peer sent end of rib marker for.";

                            leaf-list family {
                                type string {
                                    length "0..16";
                                }
                            }

                        } // container sent-end-of-rib-marker

                        container notification-family {
                            description "specifies the NLRI types that the peer supports notification for.";

                            leaf-list family {
                                type string {
                                    length "0..16";
                                }
                            }

                        } // container notification-family

                        container long-lived {
                            description "Enter the long-lived context";

                            list family {
                                key "family-type";
                                description "Enter the family list instance";

                                leaf family-type {
                                    type types-bgp:vprn-bgp-llgr-family-identifiers;
                                    description "Address family type for LLGR";
                                }

                                leaf advertised-stale-time-received {
                                    type uint32;
                                    description "Long Lived stale time received from the peer for this family.";
                                }

                                leaf stale-time-negotiated {
                                    type uint32;
                                    description "Long Lived stale time negotiated with the peer for this family.";
                                }

                                leaf flags-received {
                                    type boolean;
                                    description "specifies F-bit recieved  by the peer.";
                                }

                                leaf flags-supported {
                                    type boolean;
                                    description "specifies F-bit supported  by the peer.";
                                }

                            } // list family

                        } // container long-lived

                    } // container graceful-restart

                    list prefix-limit {
                        key "family";
                        description "Enter the prefix-limit list instance";

                        leaf family {
                            type enumeration {
                                enum "ipv4"                         { value 1; }
                                enum "ipv6"                         { value 3; }
                                enum "mcast-ipv4"                   { value 4; }
                                enum "flow-ipv4"                    { value 10; }
                                enum "flow-ipv6"                    { value 14; }
                                enum "mcast-ipv6"                   { value 16; }
                                enum "label-ipv4"                   { value 17; }
                            }
                            description "Address family to which the limit applies";
                        }

                        leaf inherit {
                            type boolean;
                            description
                                "The value of this object specifies if the peer entry in this row, should inherit the operational value of an object,
                                 or use the administratively set value.";
                        }

                    } // list prefix-limit

                } // list neighbor

                list bmp-session {
                    key "station-name";
                    description
                        "Statistics for the BMP sessions between this VPRN service
                         and a BMP station.";

                    leaf station-name {
                        type types-sros:named-item;
                        description "BMP station used for the BMP session.";
                    }

                    leaf connection-state {
                        type enumeration {
                            enum "inactive"                     { value 0; description "The BMP station is configured, but other constraints prevent BMP from starting a session."; }
                            enum "shutdown"                     { value 1; description "The connection to the BMP-station is administratively disabled."; }
                            enum "idle"                         { value 2; description "BMP is in between attempts to open a new session to the BMP-station."; }
                            enum "connecting"                   { value 3; description "BMP is actively trying to set up a TCP connection to the BMP-station."; }
                            enum "welcoming"                    { value 4; description "BMP has succesfully set up a TCP connection, but hasn't started sending BMP messages yet."; }
                            enum "established"                  { value 5; description "BMP has a fully functional BMP-session to the BMP-station."; }
                        }
                        description "Operational state of the BMP session with the BMP station.";
                    }

                    leaf local-address {
                        type types-sros:ip-address;
                        description "Local IP address of the BMP session with the BMP station.";
                    }

                    leaf local-port {
                        type types-sros:tcp-udp-port;
                        description "Local TCP port of the BMP session with the BMP station.";
                    }

                    leaf connection-state-changed {
                        type yang:date-and-time;
                        description "Last time the connection-state of the BMP session with the BMP station was changed.";
                    }

                    leaf last-message-sent {
                        type yang:date-and-time;
                        description "Last time a message was sent in the BMP session with the BMP station.";
                    }

                    leaf bytes-sent {
                        type uint64;
                        description "Total number of bytes that were sent in the BMP session with the BMP station.";
                    }

                    leaf route-monitoring-messages {
                        type uint64;
                        description "Total number of route monitoring messages that were sent in the BMP session with the BMP station.";
                    }

                    leaf statistics-messages {
                        type uint64;
                        description "Total number of statistics messages that were sent in the BMP session with the BMP station.";
                    }

                    leaf peer-up-notifications {
                        type uint64;
                        description "Total number of peer-up notifications that were sent in the BMP session with the BMP station.";
                    }

                    leaf peer-down-notifications {
                        type uint64;
                        description "Total number of peer-down notification that were sent in the BMP session with the BMP station.";
                    }

                    leaf initiation-messages {
                        type uint64;
                        description "Total number of initiation messages that were sent in the BMP session with the BMP station.";
                    }

                    leaf termination-messages {
                        type uint64;
                        description "Total number of termination messages that were sent in the BMP session with the BMP station.";
                    }

                    leaf route-mirroring-messages {
                        type uint64;
                        description "Total number of route monitoring messages that were sent in the BMP session with the BMP station.";
                    }

                } // list bmp-session

            } // container bgp

            container maximum-ipv4-routes {
                description "Enter the maximum-ipv4-routes context";

                leaf high-threshold {
                    type uint32;
                    units "percent";
                    description
                        "The high-level water marker for the number of routes
                         which this VRF may hold.

                         When this limit is exceeded a notification is generated.
                         A value of 0 (zero) for this object indicates that the threshold
                         is infinite, and a notification will never be sent.";
                }

            } // container maximum-ipv4-routes

            container maximum-ipv6-routes {
                description "Enter the maximum-ipv6-routes context";

                leaf high-threshold {
                    type uint32;
                    units "percent";
                    description
                        "The high-level water marker for the number of routes
                         which this VRF may hold.

                         When this limit is exceeded a notification is generated.
                         A value of 0 (zero) for this object indicates that the threshold
                         is infinite, and a notification will never be sent.";
                }

            } // container maximum-ipv6-routes

            container sfm-overload {
                description "Enter the sfm-overload context";

                leaf state {
                    type enumeration {
                        enum "not-applicable"               { value 0; }
                        enum "normal"                       { value 1; }
                        enum "overload"                     { value 2; }
                    }
                    description "The IGP SFM overload state.";
                }

                leaf start {
                    type types-sros:date-time;
                    description "The last time the SFM overload state had a transition to 'overload'.";
                }

                leaf time {
                    type int32 {
                        range "0..max";
                    }
                    description "The duration of the most recent overload.";
                }

            } // container sfm-overload

            list interface {
                key "interface-name";
                description "Enter the interface list instance";

                leaf interface-name {
                    type types-sros:interface-name;
                    description "Name of the interface";
                }

                leaf if-index {
                    type int32;
                    description "The interface index.";
                }

                leaf system-if-index {
                    type int32;
                    description "The interface system index.";
                }

                leaf mcast-net-domain-egr {
                    type enumeration {
                        enum "not-applicable"               { value 1; }
                        enum "not-available"                { value 2; }
                        enum "consistent"                   { value 3; }
                        enum "inconsistent"                 { value 4; }
                    }
                    description "The value of this object indicates whether the spoke sdp leaves the router interface in the multicast network domain indicated by vRtrIfMcastNetworkDomainName";
                }

                leaf protocol {
                    type bits {
                        bit ospfv2                         { position 0; }
                        bit rip                            { position 1; }
                        bit isis                           { position 2; }
                        bit bgp                            { position 3; }
                        bit mpls                           { position 4; }
                        bit rsvp                           { position 5; }
                        bit ldp                            { position 6; }
                        bit igmp                           { position 7; }
                        bit pim                            { position 8; }
                        bit ospfv3                         { position 9; }
                        bit mld                            { position 10; }
                        bit ripng                          { position 11; }
                    }
                    description
                        "Indicates which protocols are configured on the interface.;
                                         
                         Values:
                             ospfv2 - Indicates if OSPFv2 is configured.
                             rip    - Indicates if RIP is configured.
                             isis   - Indicates if ISIS is configured.
                             bgp    - Indicates if BGP is configured.
                             mpls   - Indicates if MPLS is configured.
                             rsvp   - Indicates if RSVP is configured.
                             ldp    - Indicates if LDP is configured.
                             igmp   - Indicates if IGMP is configured.
                             pim    - Indicates if PIM is configured.
                             ospfv3 - Indicates if OSPFv3 is configured.
                             mld    - Indicates if MLD is configured.
                             ripng  - Indicates if RIPng is configured.";
                }

                leaf oper-ip-mtu {
                    type uint32;
                    units "bytes";
                    description "Indicates the interface operational IP MTU.";
                }

                leaf creation-origin {
                    type types-sros:creation-origin;
                    description "Indicates the mechanism used to create this entry.";
                }

                leaf if-oper-status {
                    type enumeration {
                        enum "up"                           { value 1; }
                        enum "down"                         { value 2; }
                        enum "testing"                      { value 3; }
                        enum "unknown"                      { value 4; }
                        enum "dormant"                      { value 5; }
                        enum "not-present"                  { value 6; }
                        enum "lower-layer-down"             { value 7; }
                    }
                    description
                        "The current operational state of the interface.
                         This leaf has the same semantics as ifOperStatus. 
                         in RFC 2863: The Interfaces Group MIB";
                }

                leaf last-oper-change {
                    type yang:date-and-time;
                    description "The sysUpTime when the operational state of this interface last changed.";
                }

                container hold-time {
                    description "Enter the hold-time context";

                    container ipv4 {
                        description "Enter the ipv4 context";

                        leaf hold-timer {
                            type uint32;
                            units "seconds";
                            description
                                "The hold-timer indicates the time left before
                                 the interface comes up or goes down, depending on the ongoing
                                 transition state of the interface.";
                        }

                    } // container ipv4

                    container ipv6 {
                        description "Enter the ipv6 context";

                        leaf hold-timer {
                            type uint32;
                            units "seconds";
                            description
                                "The hold-timer indicates the time left before
                                 the interface comes up or goes down, depending on the ongoing
                                 transition state of the interface.";
                        }

                    } // container ipv6

                } // container hold-time

                container ipv4 {
                    description "Enter the ipv4 context";

                    leaf oper-state {
                        type types-sros:oper-state;
                        description "The current IPv4 operational status of this router interface.";
                    }

                    leaf down-reason {
                        type bits {
                            bit admin-disabled                 { position 0; }
                            bit service-admin-disabled         { position 1; }
                            bit port-down                      { position 2; }
                            bit address-or-parent-not-ready    { position 3; }
                            bit associated-object-not-ready    { position 4; }
                            bit rvpls-down                     { position 5; }
                            bit operational-group-down         { position 6; }
                            bit admin-destroy                  { position 7; }
                            bit no-address                     { position 8; }
                            bit no-info                        { position 9; }
                            bit hold-down-timer-running        { position 10; }
                            bit protocol-down                  { position 11; }
                            bit invalid-port-configuration     { position 12; }
                            bit unknown                        { position 13; }
                            bit no-route-distinguisher         { position 14; }
                            bit wlan-gateway-redundancy-standby { position 15; }
                            bit wlan-gateway-group-degraded    { position 16; }
                            bit ip-control-tunnel-down         { position 17; }
                            bit pdn-address-mismatch           { position 18; }
                        }
                        description
                            "Indicates the reason for why the interface is operationally down.
                                             
                             Values:
                                 admin-disabled                  - Administratively disabled.
                                 service-admin-disabled          - Assiocated service is administratively disabled.
                                 port-down                       - Associated SAP/port is operationally down.
                                 address-or-parent-not-ready     - Associated address or parent interface is not ready.
                                 associated-object-not-ready     - Associated object is not ready.
                                 rvpls-down                      - Associated R-VPLS service is operationally down.
                                 operational-group-down          - Associated operational group is operationally down.
                                 admin-destroy                   - The interface is being destroyed.
                                 no-address                      - There is no address configured.
                                 no-info                         - The interface info is not present.
                                 hold-down-timer-running         - The hold down timer is running.
                                 protocol-down                   - The protocols are operationally down.
                                 invalid-port-configuration      - Invalid port configuration.
                                 unknown                         - The interface is operationally down due to some unknown reason.
                                 no-route-distinguisher          - No route-distinguisher configured in the VRF.
                                 wlan-gateway-redundancy-standby - The interface is in standby state for WLAN-GW redundancy.
                                 wlan-gateway-group-degraded     - The interface associated WLAN-GW group is in a degraded state.
                                 ip-control-tunnel-down          - The IP tunnel associated to a control-tunnel interface is operationally down.
                                 pdn-address-mismatch            - The IP address learned from the packet data network does not match the configured primary IP address.";
                    }

                    container icmp {
                        description "Enter the icmp context";

                        container statistics {
                            description "Interface ICMPv4 statistics.";

                            leaf icmp-in-msgs {
                                type yang:counter32;
                                description
                                    "Total Number of ICMPv4 messages received by this interface.
                                                     
                                     This includes all those counted by icmp-in-errors. Note that this
                                     interface is the interface to which the ICMPv4 messages were
                                     addressed which may not be necessarily the input interface
                                     for the messages.";
                            }

                            leaf icmp-in-errors {
                                type yang:counter32;
                                description
                                    "Number of ICMPv4 errored messages received by this interface.
                                                     
                                     This implies ICMPv4 messages determined as having specific
                                     ICMPv4 errors (bad ICMPv4 checksums, bad length, etc.).";
                            }

                            leaf icmp-in-dest-unreachables {
                                type yang:counter32;
                                description "Number of ICMPv4 destination unreachable messages received by this interface.";
                            }

                            leaf icmp-in-redirects {
                                type yang:counter32;
                                description "Number of ICMPv4 redirect messages received by this interface.";
                            }

                            leaf icmp-in-echos {
                                type yang:counter32;
                                description "Number of ICMPv4 echo (request) messages received by this interface.";
                            }

                            leaf icmp-in-echo-replies {
                                type yang:counter32;
                                description "Number of ICMPv4 echo reply messages received by this interface.";
                            }

                            leaf icmp-in-time-exceeds {
                                type yang:counter32;
                                description "Number of ICMPv4 time exceeded messages received by this interface.";
                            }

                            leaf icmp-in-src-quenches {
                                type yang:counter32;
                                description "Number of ICMPv4 source quench messages received by this interface.";
                            }

                            leaf icmp-in-timestamps {
                                type yang:counter32;
                                description "Number of ICMPv4 timestamp (request) messages received by this interface.";
                            }

                            leaf icmp-in-timestamp-replies {
                                type yang:counter32;
                                description "Number of ICMPv4 timestamp reply messages received by this interface.";
                            }

                            leaf icmp-in-address-masks {
                                type yang:counter32;
                                description "Number of ICMPv4 address mask request messages received by this interface.";
                            }

                            leaf icmp-in-address-mask-replies {
                                type yang:counter32;
                                description "Number of ICMPv4 address mask reply messages received by this interface.";
                            }

                            leaf icmp-in-parm-problems {
                                type yang:counter32;
                                description "Number of ICMPv4 parameter problem messages received by this interface.";
                            }

                            leaf icmp-out-msgs {
                                type yang:counter32;
                                description
                                    "Total number of ICMPv4 messages this interface attempted to send.
                                                     
                                     This includes all those counted by icmp-out-errors.";
                            }

                            leaf icmp-out-errors {
                                type yang:counter32;
                                description
                                    "Number of ICMPv4 messages this interface could not be send due to problems
                                     discovered within ICMPv4 such as lack of buffers.
                                                     
                                     This value should not include errors discovered outside the ICMPv4 layer such as
                                     the inability of VRtr IPv4 to route the resultant datagram. In some implementations
                                     there may be no types of error which contribute to this counter's value.";
                            }

                            leaf icmp-out-dest-unreachables {
                                type yang:counter32;
                                description "Number of ICMPv4 destination unreachable messages sent by this interface.";
                            }

                            leaf icmp-out-redirects {
                                type yang:counter32;
                                description "Number of ICMPv4 redirect messages sent by this interface.";
                            }

                            leaf icmp-out-echos {
                                type yang:counter32;
                                description "Number of ICMPv4 echo request messages sent by this interface.";
                            }

                            leaf icmp-out-echo-replies {
                                type yang:counter32;
                                description "Number of ICMPv4 echo reply messages sent by this interface.";
                            }

                            leaf icmp-out-time-exceeds {
                                type yang:counter32;
                                description "Number of ICMPv4 time exceeded messages sent by this interface.";
                            }

                            leaf icmp-out-src-quenches {
                                type yang:counter32;
                                description "Number of ICMPv4 source quench messages sent by this interface.";
                            }

                            leaf icmp-out-timestamps {
                                type yang:counter32;
                                description "Number of ICMPv4 timestamp (request) messages sent by this interface.";
                            }

                            leaf icmp-out-timestamp-replies {
                                type yang:counter32;
                                description "Number of ICMPv4 timestamp reply messages sent by this interface.";
                            }

                            leaf icmp-out-address-masks {
                                type yang:counter32;
                                description "Number of ICMPv4 address mask request messages sent by this interface.";
                            }

                            leaf icmp-out-address-mask-replies {
                                type yang:counter32;
                                description "Number of ICMPv4 address mask reply messages sent by this interface.";
                            }

                            leaf icmp-out-parm-problems {
                                type yang:counter32;
                                description "Number of ICMPv4 parameter problem messages sent by this interface.";
                            }

                            leaf icmp-out-discards {
                                type yang:counter32;
                                description "Number of discarded ICMPv4 messages on this interface.";
                            }

                        } // container statistics

                    } // container icmp

                    container primary {
                        description "Enter the primary context";

                        leaf oper-address {
                            type types-sros:ip-address;
                            description "Indicates the operational address of this entry.";
                        }

                        leaf creation-origin {
                            type types-sros:creation-origin;
                            description "Indicates the mechanism used to create this entry.";
                        }

                    } // container primary

                    list secondary {
                        key "address";
                        description "Enter the secondary list instance";

                        leaf address {
                            type types-sros:ipv4-unicast-address;
                            description "Secondary IPv4 address assigned to the interface";
                        }

                        leaf oper-address {
                            type types-sros:ip-address;
                            description "Indicates the operational address of this entry.";
                        }

                        leaf creation-origin {
                            type types-sros:creation-origin;
                            description "Indicates the mechanism used to create this entry.";
                        }

                    } // list secondary

                    container addresses {
                        description "Enter the addresses context";

                        list address {
                            key "ipv4-address";
                            description "Enter the address list instance";

                            leaf ipv4-address {
                                type types-sros:ipv4-unicast-address;
                                description "IPv4 address for the interface";
                            }

                            leaf oper-address {
                                type types-sros:ip-address;
                                description "Indicates the operational address of this entry.";
                            }

                            leaf creation-origin {
                                type types-sros:creation-origin;
                                description "Indicates the mechanism used to create this entry.";
                            }

                        } // list address

                    } // container addresses

                    container neighbor-discovery {
                        description "Enter the neighbor-discovery context";

                        container neighbor-unnumbered {
                            description "IP-to-MAC address mapping state parameters on the unnumbered interface.";

                            leaf oper-state {
                                type types-sros:oper-state;
                                description "Indicates if the ARP entry is being used actively in the ARP table.";
                            }

                            leaf mac-address {
                                type yang:mac-address;
                                description "The media-dependent physical address.";
                            }

                            leaf type {
                                type enumeration {
                                    enum "other"                        { value 0; }
                                    enum "static"                       { value 1; }
                                    enum "dynamic"                      { value 2; }
                                    enum "managed"                      { value 100; }
                                    enum "evpn"                         { value 101; }
                                }
                                description "The type of mapping.";
                            }

                            leaf timer {
                                type uint32 {
                                    range "0..65535";
                                }
                                units "seconds";
                                description
                                    "Indicates how much longer an ARP entry remains in the ARP cache.

                                     When timer has a value of zero, the entry is cleared from the cache.";
                            }

                        } // container neighbor-unnumbered

                        list neighbor {
                            key "ipv4-address";
                            description "IP-to-MAC address mapping state parameters on the interface.";

                            leaf ipv4-address {
                                type types-sros:ipv4-address;
                                description "IPv4 address corresponding to the media-dependent physical address";
                            }

                            leaf oper-state {
                                type types-sros:oper-state;
                                description "Indicates if the ARP entry is being used actively in the ARP table.";
                            }

                            leaf mac-address {
                                type yang:mac-address;
                                description "The media-dependent physical address.";
                            }

                            leaf type {
                                type enumeration {
                                    enum "other"                        { value 0; }
                                    enum "static"                       { value 1; }
                                    enum "dynamic"                      { value 2; }
                                    enum "managed"                      { value 100; }
                                    enum "evpn"                         { value 101; }
                                }
                                description "The type of mapping.";
                            }

                            leaf timer {
                                type uint32 {
                                    range "0..65535";
                                }
                                units "seconds";
                                description
                                    "Indicates how much longer an ARP entry remains in the ARP cache.

                                     When timer has a value of zero, the entry is cleared from the cache.";
                            }

                        } // list neighbor

                    } // container neighbor-discovery

                    container dhcp {
                        description "Enter the dhcp context";

                        container lease-populate {
                            description "Enter the lease-populate context";

                            leaf current-lease-states {
                                type uint32 {
                                    range "0..511999";
                                }
                                description "The number of DHCP lease states currently allocated on this interface.";
                            }

                        } // container lease-populate

                        container statistics {
                            description "Packet statistics";

                            container client-packets {
                                description "Client packet statistics";

                                leaf snooped {
                                    type yang:counter32;
                                    description "The number of DHCP client packets that have been snooped on this SAP.";
                                }

                                leaf forwarded {
                                    type yang:counter32;
                                    description "The number  of  DHCP  client  packets  that have been forwarded on this SAP.";
                                }

                                leaf dropped {
                                    type yang:counter32;
                                    description "The number  of  DHCP  client  packets  that have been dropped on this SAP.";
                                }

                                container proxied {
                                    description "Proxied packet statistics";

                                    leaf radius {
                                        type yang:counter32;
                                        description
                                            "The number of DHCP client packets that have been proxied on this SAP
                                             based on data received from a RADIUS server.";
                                    }

                                    leaf lease-split {
                                        type yang:counter32;
                                        description
                                            "The number of DHCP client packets that have been proxied on this SAP
                                             based on lease state.";
                                    }

                                } // container proxied

                            } // container client-packets

                            container server-packets {
                                description "Server packet statistics";

                                leaf snooped {
                                    type yang:counter32;
                                    description "The number of DHCP server packets that have been snooped on this SAP.";
                                }

                                leaf forwarded {
                                    type yang:counter32;
                                    description "The number  of  DHCP  server  packets  that have been forwarded on this SAP.";
                                }

                                leaf dropped {
                                    type yang:counter32;
                                    description "The number  of  DHCP  server  packets  that have been dropped on this SAP.";
                                }

                            } // container server-packets

                            container spoofed {
                                description "Spoofed packet statistics";

                                leaf force-renews {
                                    type yang:counter32;
                                    description "The number of DHCP FORCERENEW messages spoofed on this SAP to the DHCP clients.";
                                }

                                leaf releases {
                                    type yang:counter32;
                                    description "The number of DHCP RELEASE messages spoofed on this SAP to the DHCP server.";
                                }

                            } // container spoofed

                        } // container statistics

                    } // container dhcp

                    list vrrp {
                        key "virtual-router-id";
                        description "Enter the vrrp list instance";

                        leaf virtual-router-id {
                            type int32 {
                                range "1..255";
                            }
                            description "Virtual Router Identifier (VRID) for the VRRP virtual router instance";
                        }

                        leaf authentication-type {
                            type enumeration {
                                enum "no-authentication"            { value 1; }
                                enum "simple-text-password"         { value 2; }
                                enum "ip-authentication-header"     { value 3; }
                            }
                            description
                                "Authentication type used for VRRP protocol exchanges between
                                 virtual routers. This value of this object is the same for a
                                 given ifIndex.

                                 New enumerations to this list can only be added via a new
                                 RFC on the standards track.";
                        }

                        leaf oper-state {
                            type types-sros:oper-state;
                            description "Operational state.";
                        }

                        leaf router-state {
                            type enumeration {
                                enum "initialize"                   { value 1; }
                                enum "backup"                       { value 2; }
                                enum "master"                       { value 3; }
                            }
                            description
                                "The current state of the virtual router. This object has
                                 three defined values:
                                  - `initialize', which indicates that all the
                                     virtual router is waiting for a startup event.

                                  - `backup', which indicates the virtual router is
                                     monitoring the availability of the master router.

                                  - `master', which indicates that the virtual router
                                     is forwarding packets for IP addresses that are
                                     associated with this router.

                                 Setting the `admin-state' object initiates
                                 transitions in the value of this object.";
                        }

                        leaf virtual-mac {
                            type yang:mac-address;
                            description
                                "The virtual MAC address of the virtual router. Although this
                                 object can be derived from the 'virtual-router-id' object, it is
                                 defined so that it is easily obtainable by a management
                                 application and can be included in VRRP-related SNMP traps.";
                        }

                        leaf master-ip-address {
                            type types-sros:ip-address;
                            description
                                "The master router's real (primary) IP address. This is
                                 the IP address listed as the source in VRRP advertisement
                                 last received by this virtual router.";
                        }

                        leaf primary-ip-address {
                            type types-sros:ip-address;
                            description
                                "In the case where there is more than one IP address for
                                 a given `interface', this object is used to specify the IP
                                 address that will become the `master-ip-addr', should
                                 the virtual router transition from backup to master. If
                                 this object is set to 0.0.0.0, the IP address which is
                                 numerically lowest will be selected.";
                        }

                        leaf up-time {
                            type yang:date-and-time;
                            description
                                "This is the value of the `system up time' object when this
                                 virtual router (i.e., the `oper-state') transitioned
                                 out of `initialized'.";
                        }

                        leaf in-use-priority {
                            type uint32 {
                                range "0..255";
                            }
                            description
                                "Indicates the current in-use priority
                                 associated with the VRRP VRRP.";
                        }

                        leaf master-since {
                            type yang:date-and-time;
                            description
                                "In case of a virtual router which
                                 is the current master, is the sysUpTime when operational state
                                 (oper-state) of the virtual router changed to master(3).
                                 In case of a backup virtual router, this value specifies the
                                 sysUpTime when it received the first VRRP advertisement message
                                 from the virtual router which is the current master.";
                        }

                        leaf master-priority {
                            type uint32 {
                                range "0..255";
                            }
                            description
                                "The value indicates the priority of
                                 the VRRP which is the current master";
                        }

                        leaf master-down-interval {
                            type types-sros:time-duration;
                            units "milliseconds";
                            description
                                "The value indicates the time
                                 interval for the backup router to declare the master as down.
                                 It is calculated as
                                        (3 * Advertisement_Interval) + Skew_time
                                 where Skew_Time is calculated as
                                        (256 - Priority) / 256";
                        }

                        leaf master-down-timer {
                            type types-sros:time-duration;
                            units "milliseconds";
                            description
                                "The value indicates the current
                                 value of the Master Down Timer.

                                 When a backup router receives a VRRP advertisement from a master,
                                 it resets this timer to the value of the Master Down Interval
                                 and begins to count down. If the backup router does not receive
                                 an advertisement till this timer times out, it will assume that
                                 the master is down and will declare itself to be the master.";
                        }

                        leaf in-use-advertisement-interval {
                            type int64;
                            units "milliseconds";
                            description "Indicates the operational value for the advertisement interval.";
                        }

                        leaf init-timer {
                            type types-sros:time-duration;
                            units "milliseconds";
                            description
                                "The value indicates the current value of
                                 initialization delay timer for VRRP, in milliseconds.";
                        }

                        leaf down-reason {
                            type enumeration {
                                enum "unknown"                      { value 0; }
                                enum "not-active"                   { value 1; }
                                enum "admin-down"                   { value 2; }
                                enum "if-down"                      { value 3; }
                                enum "no-link-lcl-addr-cfg"         { value 4; }
                                enum "rtr-adv-no-proper-cfg"        { value 5; }
                                enum "invalid-mac"                  { value 6; }
                            }
                            description
                                "The value indicates the reason for the
                                 operational state to be 'down'.";
                        }

                        container bfd-liveness {
                            description "Enter the bfd-liveness context";

                            leaf src-ip {
                                type types-sros:ip-address;
                                description
                                    "The value indicates the source
                                     IP address on the interface running BFD.";
                            }

                            leaf session-state {
                                type enumeration {
                                    enum "unknown"                      { value 1; }
                                    enum "connected"                    { value 2; }
                                    enum "broken"                       { value 3; }
                                    enum "peer-detects-down"            { value 4; }
                                    enum "not-configured"               { value 5; }
                                    enum "no-resources"                 { value 6; }
                                }
                                description
                                    "The value indicates the operational
                                     state of the BFD session the VRRP is relying
                                     upon for its fast triggering mechanism.";
                            }

                        } // container bfd-liveness

                        list master {
                            key "primary-ip-address";
                            description
                                "List of the master primary addresses that have been seen by the
                                 VRRP virtual router instance.";

                            leaf primary-ip-address {
                                type types-sros:ipv4-address;
                                description
                                    "This Object is set as read-only in mib. We use it to pass values to the sia-check
                                     function where it should fail.";
                            }

                            leaf last-seen {
                                type yang:date-and-time;
                                description
                                    "The value indicates the sysUpTime
                                     when the master was last seen by this VRRP. In
                                     other words it is the timestamp of the last advertisement message
                                     that was received from that master.";
                            }

                            leaf auth-sequence {
                                type int32;
                                description
                                    "The value indicates the last
                                     sequence number seen in the IP Authentication header of the
                                     advertisement messages received from the master.
                                     A negative value implies that the master was not being
                                     authenticated via IP authentication header.";
                            }

                            leaf ip-list-match {
                                type boolean;
                                description
                                    "The value indicates whether or not
                                     the IP address list in the advertisement messages received from
                                     the master matched the configured virtual router IP address list.";
                            }

                            container statistics {
                                description "Statistics for the master.";

                                leaf messages-received {
                                    type yang:counter32;
                                    description
                                        "The value indicates the total
                                         number of VRRP advertisement messages that have been received
                                         from the master.";
                                }

                            } // container statistics

                        } // list master

                        container statistics {

                            leaf authentication-failure-packets-received {
                                type yang:counter32;
                                description
                                    "The total number of VRRP packets received that do not pass
                                     the authentication check.";
                            }

                            leaf authentication-type-mismatch-packets-received {
                                type yang:counter32;
                                description
                                    "The total number of packets received with 'Auth Type' not
                                     equal to the locally configured authentication method
                                     (`vrrpOperAuthType').";
                            }

                            leaf address-list-discards {
                                type yang:counter32;
                                description
                                    "The total number of VRRP advertisement packets discarded
                                     because the address list did not match the locally configured
                                     list for the virtual router.";
                            }

                            leaf become-master {
                                type yang:counter32;
                                description
                                    "The total number of times that this virtual router's state
                                     has transitioned to MASTER.";
                            }

                            leaf advertisements-received {
                                type yang:counter32;
                                description
                                    "The total number of VRRP advertisements received by this
                                     virtual router.";
                            }

                            leaf advertisements-sent {
                                type yang:counter32;
                                description
                                    "The total number of VRRP advertisements sent by this virtual
                                     router.";
                            }

                            leaf advertisement-interval-errors {
                                type yang:counter32;
                                description
                                    "The total number of VRRP advertisement packets received
                                     for which the advertisement interval is different than the
                                     one configured for the local virtual router.";
                            }

                            leaf ttl-error-packets-received {
                                type yang:counter32;
                                description
                                    "The total number of VRRP packets received by the virtual
                                     router with IP TTL (Time-To-Live) not equal to 255.";
                            }

                            leaf zero-priority-packets-received {
                                type yang:counter32;
                                description
                                    "The total number of VRRP packets received by the virtual
                                     router with a priority of '0'.";
                            }

                            leaf zero-priority-packets-sent {
                                type yang:counter32;
                                description
                                    "The total number of VRRP packets sent by the virtual router
                                     with a priority of '0'.";
                            }

                            leaf invalid-type-packets-received {
                                type yang:counter32;
                                description
                                    "The number of VRRP packets received by the virtual router
                                     with an invalid value in the 'type' field.";
                            }

                            leaf address-list-error-packets-received {
                                type yang:counter32;
                                description
                                    "The total number of packets received for which the address
                                     list does not match the locally configured list for the
                                     virtual router.";
                            }

                            leaf error-length-packets-received {
                                type yang:counter32;
                                description
                                    "The total number of packets received with a packet length
                                     less than the length of the VRRP header.";
                            }

                            leaf invalid-authentication-type-packets-received {
                                type yang:counter32;
                                description
                                    "The total number of packets received with an unknown
                                     authentication type.";
                            }

                            leaf preempt-events {
                                type yang:counter32;
                                description
                                    "The value indicates the total
                                     number of times the virtual router has preempted another
                                     non-owner master with lower priority.";
                            }

                            leaf preempted-events {
                                type yang:counter32;
                                description
                                    "The value indicates the total
                                     number of times the virtual router has been preempted by another
                                     non-owner master with higher priority.";
                            }

                            leaf master-changes {
                                type yang:counter32;
                                description
                                    "The value indicates the total
                                     number of times the virtual router has seen the master virtual
                                     router change.";
                            }

                            leaf advertise-interval-discards {
                                type yang:counter32;
                                description
                                    "The total number of VRRP advertisement packets discarded
                                     because the advertisement interval in the received packet
                                     was different than the one configured for the local virtual
                                     router.";
                            }

                            leaf total-discards {
                                type yang:counter32;
                                description
                                    "The total number of VRRP advertisement packets discarded
                                     for any reason. This includes the packets discarded due to
                                     advertise interval mismatch and address list mismatch.";
                            }

                        } // container statistics

                    } // list vrrp

                    container statistics {
                        description "Interface IPv4 statistics.";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                        leaf out-discard-dbcast-packets {
                            type yang:counter64;
                            description "The number of directed-broadcast packets dropped.";
                        }

                        leaf out-discard-dbcast-octets {
                            type yang:counter64;
                            description "The number of directed-broadcast octets dropped.";
                        }

                    } // container statistics

                } // container ipv4

                list spoke-sdp {
                    key "sdp-bind-id";
                    description "Enter the spoke-sdp list instance";

                    leaf sdp-bind-id {
                        type types-services:sdp-bind-id;
                        description "SDP Binding identifier as <sdp-id>:<vc-id>. sdp-id - [1..32767] vc-id - [1..4294967295].";
                    }

                    leaf oper-state {
                        type enumeration {
                            enum "up"                           { value 1; }
                            enum "down"                         { value 5; }
                        }
                        description "Indicates the operating status of this Service-SDP binding.";
                    }

                    leaf oper-flags {
                        type bits {
                            bit sdp-bind-admin-down            { position 0; }
                            bit svc-admin-down                 { position 1; }
                            bit stitching-svc-txdown           { position 2; }
                            bit sdp-oper-down                  { position 3; }
                            bit sdp-path-mtu-too-small         { position 4; }
                            bit no-ingress-vc-label            { position 5; }
                            bit no-egress-vc-label             { position 6; }
                            bit svc-mtu-mismatch               { position 7; }
                            bit vc-type-mismatch               { position 8; }
                            bit relearn-limit-exceeded         { position 9; }
                            bit ies-if-admin-down              { position 10; }
                            bit released-ingress-vc-label      { position 11; }
                            bit labels-exhausted               { position 12; }
                            bit svc-param-mismatch             { position 13; }
                            bit insufficient-bandwidth         { position 14; }
                            bit pw-peer-fault-status-bits      { position 15; }
                            bit mesh-sdp-down                  { position 16; }
                            bit not-managed-by-mcring          { position 17; }
                            bit out-of-resource                { position 18; }
                            bit mh-standby                     { position 19; }
                            bit oam-down-mep-fault             { position 20; }
                            bit oam-up-mep-fault               { position 21; }
                            bit standby-sig-slave-tx-down      { position 22; }
                            bit oper-grp-down                  { position 23; }
                            bit withdrawn-ingress-vc-label     { position 24; }
                            bit vpls-pmsi-down                 { position 25; }
                            bit rec-prot-src-mac               { position 26; }
                            bit peer-fault-status-tx-down      { position 27; }
                            bit evpn-route-conflict            { position 28; }
                            bit admin-locked                   { position 29; }
                            bit evpn-p2mp-conflict             { position 30; }
                            bit label-stack-limit-exceeded     { position 31; }
                        }
                        description
                            "This object indicates all the conditions that affect the
                             operating status of this SDP Bind.";
                    }

                    leaf pw-peer-status-bits {
                        type bits {
                            bit pw-not-forwarding              { position 0; }
                            bit lac-ingress-fault              { position 1; }
                            bit lac-egress-fault               { position 2; }
                            bit psn-ingress-fault              { position 3; }
                            bit psn-egress-fault               { position 4; }
                            bit pw-fwding-standby              { position 5; }
                        }
                        description
                            "Indicates bits set by the LDP peer when there is a fault on its
                             side of the pseudowire";
                    }

                    leaf pw-local-status-bits {
                        type bits {
                            bit pw-not-forwarding              { position 0; }
                            bit lac-ingress-fault              { position 1; }
                            bit lac-egress-fault               { position 2; }
                            bit psn-ingress-fault              { position 3; }
                            bit psn-egress-fault               { position 4; }
                            bit pw-fwding-standby              { position 5; }
                        }
                        description "Indicates locally set bits when there is a fault.";
                    }

                    leaf peer-vccv-cv-bits {
                        type bits {
                            bit icmp-ping                      { position 0; }
                            bit lsp-ping                       { position 1; }
                            bit bfd-fault-detection            { position 2; }
                            bit bfd-fault-detection-and-signalling { position 3; }
                        }
                        description "Indicates CV type bits set by the LDP peer if it supports VCCV.";
                    }

                    leaf peer-vccv-cc-bits {
                        type bits {
                            bit pwe3-control-word              { position 0; }
                            bit mpls-router-alert-label        { position 1; }
                            bit mpls-pw-demultiplex-or-label   { position 2; }
                        }
                        description "Indicates CC type bits set by the LDP peer if it supports VCCV.";
                    }

                    leaf oper-control-word {
                        type boolean;
                        description "Status of control word.";
                    }

                    leaf pw-fault-ip-address {
                        type types-sros:ip-address;
                        description "Faulty IP address sent by peer.";
                    }

                    leaf class-forwarding-oper-state {
                        type types-sros:oper-state;
                        description "Operational state of forwarding-class based forwarding on this SDP bind.";
                    }

                    leaf creation-origin {
                        type types-sros:creation-origin;
                        description "Creation origin of the service.";
                    }

                    leaf oper-hash-label {
                        type boolean;
                        description "Indicates the negotiated value of hash lavel that is used on this SDP binding.";
                    }

                    leaf min-required-sdp-oper-mtu {
                        type int32;
                        description "Minimum required SDP MTU size used with this SDP binding.";
                    }

                    container ingress {
                        description "Enter the ingress context";

                        leaf oper-label {
                            type uint32;
                            description "MPLS service label used by the far-end device to send packets to the local PEs sdp-bind.";
                        }

                        container statistics {
                            description "Ingress side statistics";

                            leaf forwarded-packets {
                                type yang:counter64;
                                description "Forwarded packets";
                            }

                            leaf forwarded-octets {
                                type yang:counter64;
                                description "Forwarded octets";
                            }

                            leaf dropped-packets {
                                type yang:counter64;
                                description "Dropped packets";
                            }

                            leaf dropped-octets {
                                type yang:counter64;
                                description "Dropped octets";
                            }

                        } // container statistics

                    } // container ingress

                    container egress {
                        description "Enter the egress context";

                        leaf oper-label {
                            type uint32;
                            description "MPLS service label used to send packets to the far-end device via this sdp-bind.";
                        }

                        container statistics {
                            description "Egress side statistics";

                            leaf forwarded-packets {
                                type yang:counter64;
                                description "Forwarded packets";
                            }

                            leaf forwarded-octets {
                                type yang:counter64;
                                description "Forwarded octets";
                            }

                        } // container statistics

                    } // container egress

                    container eth-cfm {
                        description "Enter the eth-cfm context";

                        list mep {
                            key "md-admin-name ma-admin-name mep-id";
                            description "Enter the mep list instance";

                            leaf md-admin-name {
                                type leafref {
                                    path "../../../../../../../eth-cfm/domain/md-admin-name";
                                }
                                description "Admin-assigned maintenance domain index value";
                            }

                            leaf ma-admin-name {
                                type leafref {
                                    path "../../../../../../../eth-cfm/domain[md-admin-name=current()/../md-admin-name]/association/ma-admin-name";
                                }
                                description "Admin-assigned maintenance association index value";
                            }

                            leaf mep-id {
                                type types-eth-cfm:mep-id-type;
                                description "MEP identifier";
                            }

                        } // list mep

                    } // container eth-cfm

                } // list spoke-sdp

                list sap {
                    key "sap-id";
                    description "Enter the sap list instance";

                    leaf sap-id {
                        type types-sros:sap;
                        description "SAP identifier";
                    }

                    leaf oper-state {
                        type enumeration {
                            enum "up"                           { value 1; }
                            enum "down"                         { value 2; }
                        }
                        description "Operating state of this SAP";
                    }

                    leaf oper-flags {
                        type types-services:l3-sap-oper-flags;
                        description "Conditions that affect the operating status of this SAP.";
                    }

                    leaf mirror-state {
                        type enumeration {
                            enum "ingress"                      { value 1; }
                            enum "egress"                       { value 2; }
                            enum "ingress-and-egress"           { value 3; }
                            enum "disabled"                     { value 4; }
                        }
                        description "Indicates whether traffic mirroring has been enabled on this SAP";
                    }

                    leaf template-used {
                        type types-sros:named-item-or-empty;
                        description "Name of the sap-template used to create this sap.";
                    }

                    leaf oper-dist-cpu-prot-policy {
                        type types-sros:named-item-or-empty;
                        description "Operational Distributed CPU Protection Policy.";
                    }

                    container statistics {
                        description "Statistics information";

                        container authentication {
                            description "Authentication statistics information";

                            leaf discarded-packets {
                                type yang:counter32;
                                description
                                    "The number of DHCP packets discarded
                                     as result of authentication.";
                            }

                            leaf success-packets {
                                type yang:counter32;
                                description "The number of DHCP packets successfully authenticated.";
                            }

                        } // container authentication

                    } // container statistics

                    container ingress {
                        description "Enter the ingress context";

                        container qos {
                            description "Enter the qos context";

                            container sap-ingress {
                                description "Enter the sap-ingress context";

                                container forwarding-engine {
                                    description "Forwarding engine information";

                                    container statistics {
                                        description "Statistics information";

                                        leaf dropped-packets {
                                            type yang:counter64;
                                            description "Policy identifier";
                                        }

                                        leaf dropped-octets {
                                            type yang:counter64;
                                            description
                                                "The number of octets dropped by the
                                                 ingress packet processor due to: SAP state,
                                                 ingress MAC, IP or IPv6 filter, same segment
                                                 discard, bad checksum, etc.";
                                        }

                                        leaf received-valid-packets {
                                            type yang:counter64;
                                            description
                                                "The value of received-valid indicates
                                                 number of received valid packets, as determined by the SAP
                                                 ingress QoS policy, offered by the packet processor to the traffic manager.";
                                        }

                                        leaf received-valid-octets {
                                            type yang:counter64;
                                            description
                                                "The value of received-valid indicates
                                                 number of received valid octets, as determined by the SAP
                                                 ingress QoS policy, offered by the packet processor to the traffic manager.";
                                        }

                                        leaf high-priority-offered-packets {
                                            type yang:counter64;
                                            description
                                                "The number of high priority packets,
                                                 as determined by the SAP ingress QoS
                                                 policy, offered by the packet processor to the
                                                 traffic manager.";
                                        }

                                        leaf high-priority-offered-octets {
                                            type yang:counter64;
                                            description
                                                "The number of high priority octets,
                                                 as determined by the SAP ingress QoS
                                                 policy, offered by the packet processor to the
                                                 traffic manager.";
                                        }

                                        leaf low-priority-offered-packets {
                                            type yang:counter64;
                                            description
                                                "The number of low priority packets,
                                                 as determined by the SAP ingress QoS
                                                 policy, offered by the packet processor to the
                                                 traffic manager.";
                                        }

                                        leaf low-priority-offered-octets {
                                            type yang:counter64;
                                            description
                                                "The number of low priority octets,
                                                 as determined by the SAP ingress QoS
                                                 policy, offered by the packet processor to the
                                                 traffic manager.";
                                        }

                                        leaf uncolor-offered-packets {
                                            type yang:counter64;
                                            description
                                                "The number of uncolored packets,
                                                 as determined by the SAP ingress QoS
                                                 policy, offered by the packet processor to the
                                                 traffic manager.";
                                        }

                                        leaf uncolor-offered-octets {
                                            type yang:counter64;
                                            description
                                                "The number of uncolored octets,
                                                 as determined by the SAP ingress QoS
                                                 policy, offered by the packet processor to the
                                                 traffic manager.";
                                        }

                                        leaf managed-offered-packets {
                                            type yang:counter64;
                                            description
                                                "The value of managed-offered indicates
                                                 number of managed multicast packets, as determined by the SAP
                                                 ingress QoS policy, offered by the packet processor to the traffic manager.";
                                        }

                                        leaf managed-offered-octets {
                                            type yang:counter64;
                                            description
                                                "The value of managed-offered indicates
                                                 number of managed multicast octets, as determined by the SAP
                                                 ingress QoS policy, offered by the packet processor to the traffic manager.";
                                        }

                                        leaf aggregate-offered-packets {
                                            type yang:counter64;
                                            description
                                                "The value of aggregate-offered indicates aggregate
                                                 number of hi, lo priority and uncolour packets,
                                                 as determined by the SAP ingress QoS policy,
                                                 offered by the packet processor to the traffic manager.";
                                        }

                                        leaf aggregate-offered-octets {
                                            type yang:counter64;
                                            description
                                                "The value of managed-offered indicates aggregate
                                                 number of hi, lo priority and uncolour octets,
                                                 as determined by the SAP ingress QoS policy,
                                                 offered by the packet processor to the traffic manager.";
                                        }

                                        leaf last-cleared-time {
                                            type yang:date-and-time;
                                            description "Time when the counters in this table were last cleared.";
                                        }

                                    } // container statistics

                                } // container forwarding-engine

                                container traffic-manager {
                                    description "Traffic manager information";

                                    container statistics {
                                        description "Statistics information";

                                        leaf cpm-packets {
                                            type yang:counter64;
                                            description
                                                "The value of cpm-packets indicates
                                                 ingress traffic in terms of packets destined to CPM
                                                 associated with this SAP.";
                                        }

                                        leaf cpm-octets {
                                            type yang:counter64;
                                            description
                                                "The value of cpm indicates
                                                 ingress traffic in terms of bytes destined to CPM
                                                 associated with this SAP.";
                                        }

                                        leaf high-priority-dropped-packets {
                                            type yang:counter64;
                                            description
                                                "The number of high priority packets,
                                                 as determined by the SAP ingress QoS
                                                 policy, dropped by the traffic manager due to:
                                                 MBS exceeded, buffer pool limit
                                                 exceeded, etc.";
                                        }

                                        leaf high-priority-dropped-octets {
                                            type yang:counter64;
                                            description
                                                "The number of high priority octets,
                                                 as determined by the SAP ingress QoS
                                                 policy, dropped by the traffic manager due to:
                                                 MBS exceeded, buffer pool limit
                                                 exceeded, etc.";
                                        }

                                        leaf low-priority-dropped-packets {
                                            type yang:counter64;
                                            description
                                                "The number of low priority packets,
                                                 as determined by the SAP ingress QoS
                                                 policy, dropped by the traffic manager due to:
                                                 MBS exceeded, buffer pool limit
                                                 exceeded, etc.";
                                        }

                                        leaf low-priority-dropped-octets {
                                            type yang:counter64;
                                            description
                                                "The number of low priority octets,
                                                 as determined by the SAP ingress QoS
                                                 policy, dropped by the traffic manager due to:
                                                 MBS exceeded, buffer pool limit
                                                 exceeded, etc.";
                                        }

                                        leaf in-profile-forwarded-packets {
                                            type yang:counter64;
                                            description
                                                "The number of in-profile packets
                                                 (rate below CIR) forwarded by the
                                                 ingress traffic manager.";
                                        }

                                        leaf in-profile-forwarded-octets {
                                            type yang:counter64;
                                            description
                                                "The number of in-profile octets
                                                 (rate below CIR) forwarded by the
                                                 ingress traffic manager.";
                                        }

                                        leaf out-profile-forwarded-packets {
                                            type yang:counter64;
                                            description
                                                "The number of out-of-profile packets
                                                 (rate above CIR) forwarded by the
                                                 ingress traffic manager.";
                                        }

                                        leaf out-profile-forwarded-octets {
                                            type yang:counter64;
                                            description
                                                "The number of out-of-profile octets
                                                 (rate above CIR) forwarded by the
                                                 ingress traffic manager.";
                                        }

                                        leaf aggregate-forwarded-packets {
                                            type yang:counter64;
                                            description
                                                "The aggregate number of in and out-of profile
                                                  packets forwarded by the ingress traffic manager.";
                                        }

                                        leaf aggregate-forwarded-octets {
                                            type yang:counter64;
                                            description
                                                "The aggregate number of in and out-of-profile
                                                 octets forwarded by the ingress traffic manager.";
                                        }

                                        leaf aggregate-dropped-packets {
                                            type yang:counter64;
                                            description
                                                "The aggregate number of in and out-of profile
                                                 packets, dropped by the traffic manager due to:
                                                 MBS exceeded, buffer pool limit
                                                 exceeded, etc.";
                                        }

                                        leaf aggregate-dropped-octets {
                                            type yang:counter64;
                                            description
                                                "The aggregate number of in and out-of profile
                                                 octets, dropped by the traffic manager due to:
                                                 MBS exceeded, buffer pool limit
                                                 exceeded, etc.";
                                        }

                                        leaf last-cleared-time {
                                            type yang:date-and-time;
                                            description "Time when the counters in this table were last cleared.";
                                        }

                                    } // container statistics

                                } // container traffic-manager

                                list queue {
                                    key "queue-id";
                                    description "SAP Ingress Queue statistics.";

                                    leaf queue-id {
                                        type types-qos:ingress-queue-id;
                                        description "The unique identifier for the queue.";
                                    }

                                    container statistics {
                                        description "SAP Ingress Queue statistics.";

                                        choice stat-mode {
                                            case unicast-priority {

                                                container unicast-priority {

                                                    leaf high-priority-offered-packets {
                                                        type yang:counter64;
                                                        description "The number of high-priority packets offered by packet processor to traffic manager.";
                                                    }

                                                    leaf high-priority-offered-octets {
                                                        type yang:counter64;
                                                        description "The number of high-priority octets offered by packet processor to traffic manager.";
                                                    }

                                                    leaf low-priority-offered-packets {
                                                        type yang:counter64;
                                                        description "The number of low-priority packets offered by packet processor to traffic manager.";
                                                    }

                                                    leaf low-priority-offered-octets {
                                                        type yang:counter64;
                                                        description "The number of low-priority octets offered by packet processor to traffic manager.";
                                                    }

                                                    leaf high-priority-dropped-packets {
                                                        type yang:counter64;
                                                        description "The number of high-priority packets dropped by packet processor to traffic manager.";
                                                    }

                                                    leaf high-priority-dropped-octets {
                                                        type yang:counter64;
                                                        description "The number of high-priority octets dropped by packet processor to traffic manager.";
                                                    }

                                                    leaf low-priority-dropped-packets {
                                                        type yang:counter64;
                                                        description "The number of low-priority packets dropped by packet processor to traffic manager.";
                                                    }

                                                    leaf low-priority-dropped-octets {
                                                        type yang:counter64;
                                                        description "The number of low-priority octets dropped by packet processor to traffic manager.";
                                                    }

                                                    leaf in-profile-forwarded-packets {
                                                        type yang:counter64;
                                                        description "The number of in-profile packets (rate below CIR) forwarded.";
                                                    }

                                                    leaf in-profile-forwarded-octets {
                                                        type yang:counter64;
                                                        description "The number of in-profile octets (rate below CIR) forwarded.";
                                                    }

                                                    leaf out-profile-forwarded-packets {
                                                        type yang:counter64;
                                                        description "The number of out-of-profile packets (rate below CIR) forwarded.";
                                                    }

                                                    leaf out-profile-forwarded-octets {
                                                        type yang:counter64;
                                                        description "The number of out-of-profile octets (rate below CIR) forwarded.";
                                                    }

                                                } // container unicast-priority

                                            }
                                            case unicast-profile {

                                                container unicast-profile {

                                                    leaf color-in-offered-packets {
                                                        type yang:counter64;
                                                        description "The number of color-in packets offered to traffic manager.";
                                                    }

                                                    leaf color-in-offered-octets {
                                                        type yang:counter64;
                                                        description "The number of color-in octets offered to traffic manager.";
                                                    }

                                                    leaf color-out-offered-packets {
                                                        type yang:counter64;
                                                        description "The number of color-out packets offered to traffic manager.";
                                                    }

                                                    leaf color-out-offered-octets {
                                                        type yang:counter64;
                                                        description "The number of color-out octets offered to traffic manager.";
                                                    }

                                                    leaf uncolor-offered-packets {
                                                        type yang:counter64;
                                                        description "The number of uncolor packets offered to traffic manager.";
                                                    }

                                                    leaf uncolor-offered-octets {
                                                        type yang:counter64;
                                                        description "The number of uncolor octets offered to traffic manager.";
                                                    }

                                                    leaf color-out-dropped-packets {
                                                        type yang:counter64;
                                                        description "The number of color-out packets dropped.";
                                                    }

                                                    leaf color-out-dropped-octets {
                                                        type yang:counter64;
                                                        description "The number of color-out octets dropped.";
                                                    }

                                                    leaf color-in-uncolor-dropped-packets {
                                                        type yang:counter64;
                                                        description "The number of color-in/uncolor packets dropped.";
                                                    }

                                                    leaf color-in-uncolor-dropped-octets {
                                                        type yang:counter64;
                                                        description "The number of color-in/uncolor octets dropped.";
                                                    }

                                                    leaf in-profile-forwarded-packets {
                                                        type yang:counter64;
                                                        description "The number of in-profile packets (rate below CIR) forwarded.";
                                                    }

                                                    leaf in-profile-forwarded-octets {
                                                        type yang:counter64;
                                                        description "The number of in-profile octets (rate below CIR) forwarded.";
                                                    }

                                                    leaf out-profile-forwarded-packets {
                                                        type yang:counter64;
                                                        description "The number of out-of-profile packets (rate below CIR) forwarded.";
                                                    }

                                                    leaf out-profile-forwarded-octets {
                                                        type yang:counter64;
                                                        description "The number of out-of-profile octets (rate below CIR) forwarded.";
                                                    }

                                                } // container unicast-profile

                                            }
                                            case multipoint-priority {

                                                container multipoint-priority {

                                                    leaf high-priority-offered-packets {
                                                        type yang:counter64;
                                                        description "The number of high-priority packets offered by packet processor to traffic manager.";
                                                    }

                                                    leaf high-priority-offered-octets {
                                                        type yang:counter64;
                                                        description "The number of high-priority octets offered by packet processor to traffic manager.";
                                                    }

                                                    leaf low-priority-offered-packets {
                                                        type yang:counter64;
                                                        description "The number of low-priority packets offered by packet processor to traffic manager.";
                                                    }

                                                    leaf low-priority-offered-octets {
                                                        type yang:counter64;
                                                        description "The number of low-priority octets offered by packet processor to traffic manager.";
                                                    }

                                                    leaf managed-offered-packets {
                                                        type yang:counter64;
                                                        description "The number of managed packets offered by packet processor to traffic manager.";
                                                    }

                                                    leaf managed-offered-octets {
                                                        type yang:counter64;
                                                        description "The number of managed octets offered by packet processor to traffic manager.";
                                                    }

                                                    leaf high-priority-dropped-packets {
                                                        type yang:counter64;
                                                        description "The number of high-priority packets dropped by packet processor to traffic manager.";
                                                    }

                                                    leaf high-priority-dropped-octets {
                                                        type yang:counter64;
                                                        description "The number of high-priority octets dropped by packet processor to traffic manager.";
                                                    }

                                                    leaf low-priority-dropped-packets {
                                                        type yang:counter64;
                                                        description "The number of low-priority packets dropped by packet processor to traffic manager.";
                                                    }

                                                    leaf low-priority-dropped-octets {
                                                        type yang:counter64;
                                                        description "The number of low-priority octets dropped by packet processor to traffic manager.";
                                                    }

                                                    leaf in-profile-forwarded-packets {
                                                        type yang:counter64;
                                                        description "The number of in-profile packets (rate below CIR) forwarded.";
                                                    }

                                                    leaf in-profile-forwarded-octets {
                                                        type yang:counter64;
                                                        description "The number of in-profile octets (rate below CIR) forwarded.";
                                                    }

                                                    leaf out-profile-forwarded-packets {
                                                        type yang:counter64;
                                                        description "The number of out-of-profile packets (rate below CIR) forwarded.";
                                                    }

                                                    leaf out-profile-forwarded-octets {
                                                        type yang:counter64;
                                                        description "The number of out-of-profile octets (rate below CIR) forwarded.";
                                                    }

                                                } // container multipoint-priority

                                            }
                                            case multipoint-profile {

                                                container multipoint-profile {

                                                    leaf color-in-offered-packets {
                                                        type yang:counter64;
                                                        description "The number of color-in packets offered to traffic manager.";
                                                    }

                                                    leaf color-in-offered-octets {
                                                        type yang:counter64;
                                                        description "The number of color-in octets offered to traffic manager.";
                                                    }

                                                    leaf color-out-offered-packets {
                                                        type yang:counter64;
                                                        description "The number of color-out packets offered to traffic manager.";
                                                    }

                                                    leaf color-out-offered-octets {
                                                        type yang:counter64;
                                                        description "The number of color-out octets offered to traffic manager.";
                                                    }

                                                    leaf uncolor-offered-packets {
                                                        type yang:counter64;
                                                        description "The number of uncolor packets offered to traffic manager.";
                                                    }

                                                    leaf uncolor-offered-octets {
                                                        type yang:counter64;
                                                        description "The number of uncolor octets offered to traffic manager.";
                                                    }

                                                    leaf managed-offered-packets {
                                                        type yang:counter64;
                                                        description "The number of managed packets offered by packet processor to traffic manager.";
                                                    }

                                                    leaf managed-offered-octets {
                                                        type yang:counter64;
                                                        description "The number of managed octets offered by packet processor to traffic manager.";
                                                    }

                                                    leaf color-out-dropped-packets {
                                                        type yang:counter64;
                                                        description "The number of color-out packets dropped.";
                                                    }

                                                    leaf color-out-dropped-octets {
                                                        type yang:counter64;
                                                        description "The number of color-out octets dropped.";
                                                    }

                                                    leaf color-in-uncolor-dropped-packets {
                                                        type yang:counter64;
                                                        description "The number of color-in/uncolor packets dropped.";
                                                    }

                                                    leaf color-in-uncolor-dropped-octets {
                                                        type yang:counter64;
                                                        description "The number of color-in/uncolor octets dropped.";
                                                    }

                                                    leaf in-profile-forwarded-packets {
                                                        type yang:counter64;
                                                        description "The number of in-profile packets (rate below CIR) forwarded.";
                                                    }

                                                    leaf in-profile-forwarded-octets {
                                                        type yang:counter64;
                                                        description "The number of in-profile octets (rate below CIR) forwarded.";
                                                    }

                                                    leaf out-profile-forwarded-packets {
                                                        type yang:counter64;
                                                        description "The number of out-of-profile packets (rate below CIR) forwarded.";
                                                    }

                                                    leaf out-profile-forwarded-octets {
                                                        type yang:counter64;
                                                        description "The number of out-of-profile octets (rate below CIR) forwarded.";
                                                    }

                                                } // container multipoint-profile

                                            }
                                            case v4-v6 {

                                                container v4-v6 {

                                                    leaf ipv4-offered-packets {
                                                        type yang:counter64;
                                                        description "The number of ipv4 packets offered by packet processor to traffic manager.";
                                                    }

                                                    leaf ipv4-offered-octets {
                                                        type yang:counter64;
                                                        description "The number of ipv4 octets offered by packet processor to traffic manager.";
                                                    }

                                                    leaf ipv6-offered-packets {
                                                        type yang:counter64;
                                                        description "The number of ipv6 packets offered by packet processor to traffic manager.";
                                                    }

                                                    leaf ipv6-offered-octets {
                                                        type yang:counter64;
                                                        description "The number of ipv6 octets offered by packet processor to traffic manager.";
                                                    }

                                                    leaf ipv4-dropped-packets {
                                                        type yang:counter64;
                                                        description "The number of ipv4 packets dropped by packet processor to traffic manager.";
                                                    }

                                                    leaf ipv4-dropped-octets {
                                                        type yang:counter64;
                                                        description "The number of ipv4 octets dropped by packet processor to traffic manager.";
                                                    }

                                                    leaf ipv6-dropped-packets {
                                                        type yang:counter64;
                                                        description "The number of ipv6 packets dropped by packet processor to traffic manager.";
                                                    }

                                                    leaf ipv6-dropped-octets {
                                                        type yang:counter64;
                                                        description "The number of ipv6 octets dropped by packet processor to traffic manager.";
                                                    }

                                                    leaf ipv4-forwarded-packets {
                                                        type yang:counter64;
                                                        description "The number of ipv4 packets forwarded.";
                                                    }

                                                    leaf ipv4-forwarded-octets {
                                                        type yang:counter64;
                                                        description "The number of ipv4 octets forwarded.";
                                                    }

                                                    leaf ipv6-forwarded-packets {
                                                        type yang:counter64;
                                                        description "The number of ipv6 packets forwarded.";
                                                    }

                                                    leaf ipv6-forwarded-octets {
                                                        type yang:counter64;
                                                        description "The number of ipv6 octets forwarded.";
                                                    }

                                                } // container v4-v6

                                            }
                                        }
                                    } // container statistics

                                } // list queue

                                list policer {
                                    key "policer-id";
                                    description "SAP Ingress Policer statistics.";

                                    leaf policer-id {
                                        type types-qos:ingress-policer-id;
                                        description "The unique identifier for the policer.";
                                    }

                                    container statistics {
                                        description "SAP Ingress Policer statistics.";

                                        choice stat-mode {
                                            case minimal {

                                                container minimal {

                                                    leaf all-offered-packets {
                                                        type yang:counter64;
                                                        description "The number of all the priority packets offered by the packet processor to traffic manager";
                                                    }

                                                    leaf all-offered-octets {
                                                        type yang:counter64;
                                                        description "The number of all the priority octets offered by the packet processor to traffic manager";
                                                    }

                                                    leaf all-dropped-packets {
                                                        type yang:counter64;
                                                        description "The number of all the priority packets dropped by the packet processor to traffic manager";
                                                    }

                                                    leaf all-dropped-octets {
                                                        type yang:counter64;
                                                        description "The number of all the priority octets dropped by the packet processor to traffic manager";
                                                    }

                                                    leaf all-forwarded-packets {
                                                        type yang:counter64;
                                                        description "The number of all the priority packets forwarded by the packet processor to traffic manager";
                                                    }

                                                    leaf all-forwarded-octets {
                                                        type yang:counter64;
                                                        description "The number of all the priority octets forwarded by the packet processor to traffic manager";
                                                    }

                                                } // container minimal

                                            }
                                            case offered-profile-no-cir {

                                                container offered-profile-no-cir {

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-profile-no-cir

                                            }
                                            case offered-priority-no-cir {

                                                container offered-priority-no-cir {

                                                    leaf high-priority-offered-packets {
                                                        type yang:counter64;
                                                        description "The number of high-priority packets offered by the packet processor to traffic manager";
                                                    }

                                                    leaf high-priority-offered-octets {
                                                        type yang:counter64;
                                                        description "The number of high-priority octets offered by the packet processor to traffic manager";
                                                    }

                                                    leaf low-priority-offered-packets {
                                                        type yang:counter64;
                                                        description "The number of low-priority packets offered by the packet processor to traffic manager";
                                                    }

                                                    leaf low-priority-offered-octets {
                                                        type yang:counter64;
                                                        description "The number of low-priority octets offered by the packet processor to traffic manager";
                                                    }

                                                    leaf high-priority-dropped-packets {
                                                        type yang:counter64;
                                                        description "The number of high-priority packets dropped by the packet processor to traffic manager";
                                                    }

                                                    leaf high-priority-dropped-octets {
                                                        type yang:counter64;
                                                        description "The number of high-priority octets dropped by the packet processor to traffic manager";
                                                    }

                                                    leaf low-priority-dropped-packets {
                                                        type yang:counter64;
                                                        description "The number of low-priority packets dropped by the packet processor to traffic manager";
                                                    }

                                                    leaf low-priority-dropped-octets {
                                                        type yang:counter64;
                                                        description "The number of low-priority octets dropped by the packet processor to traffic manager";
                                                    }

                                                    leaf high-priority-forwarded-packets {
                                                        type yang:counter64;
                                                        description "The number of high-priority packets forwarded by the packet processor to traffic manager";
                                                    }

                                                    leaf high-priority-forwarded-octets {
                                                        type yang:counter64;
                                                        description "The number of high-priority octets forwarded by the packet processor to traffic manager";
                                                    }

                                                    leaf low-priority-forwarded-packets {
                                                        type yang:counter64;
                                                        description "The number of low-priority packets forwarded by the packet processor to traffic manager";
                                                    }

                                                    leaf low-priority-forwarded-octets {
                                                        type yang:counter64;
                                                        description "The number of low-priority octets forwarded by the packet processor to traffic manager";
                                                    }

                                                } // container offered-priority-no-cir

                                            }
                                            case offered-profile-cir {

                                                container offered-profile-cir {

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf uncolor-offered-packets {
                                                        type yang:counter64;
                                                        description "The number of uncolor packets offered by the packet processor to traffic manager";
                                                    }

                                                    leaf uncolor-offered-octets {
                                                        type yang:counter64;
                                                        description "The number of uncolor octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-profile-cir

                                            }
                                            case offered-priority-cir {

                                                container offered-priority-cir {

                                                    leaf high-priority-offered-packets {
                                                        type yang:counter64;
                                                        description "The number of high-priority packets offered by the packet processor to traffic manager";
                                                    }

                                                    leaf high-priority-offered-octets {
                                                        type yang:counter64;
                                                        description "The number of high-priority octets offered by the packet processor to traffic manager";
                                                    }

                                                    leaf low-priority-offered-packets {
                                                        type yang:counter64;
                                                        description "The number of low-priority packets offered by the packet processor to traffic manager";
                                                    }

                                                    leaf low-priority-offered-octets {
                                                        type yang:counter64;
                                                        description "The number of low-priority octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-priority-cir

                                            }
                                            case offered-total-cir {

                                                container offered-total-cir {

                                                    leaf all-offered-packets {
                                                        type yang:counter64;
                                                        description "The number of all the priority packets offered by the packet processor to traffic manager";
                                                    }

                                                    leaf all-offered-octets {
                                                        type yang:counter64;
                                                        description "The number of all the priority octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-total-cir

                                            }
                                            case offered-limited-profile-cir {

                                                container offered-limited-profile-cir {

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf uncolor-offered-packets {
                                                        type yang:counter64;
                                                        description "The number of uncolor packets offered by the packet processor to traffic manager";
                                                    }

                                                    leaf uncolor-offered-octets {
                                                        type yang:counter64;
                                                        description "The number of uncolor octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-limited-profile-cir

                                            }
                                            case offered-profile-capped-cir {

                                                container offered-profile-capped-cir {

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf uncolor-offered-packets {
                                                        type yang:counter64;
                                                        description "The number of uncolor packets offered by the packet processor to traffic manager";
                                                    }

                                                    leaf uncolor-offered-octets {
                                                        type yang:counter64;
                                                        description "The number of uncolor octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-profile-capped-cir

                                            }
                                            case offered-limited-capped-cir {

                                                container offered-limited-capped-cir {

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                    leaf uncolor-offered-packets {
                                                        type yang:counter64;
                                                        description "The number of out-of-rofile packets offered by the packet processor to traffic manager";
                                                    }

                                                    leaf uncolor-offered-octets {
                                                        type yang:counter64;
                                                        description "The number of out-of-profile octets offered by the packet processor to traffic manager";
                                                    }

                                                } // container offered-limited-capped-cir

                                            }
                                            case v4-v6 {

                                                container v4-v6 {

                                                    leaf ipv4-offered-packets {
                                                        type yang:counter64;
                                                        description "The number of ipv4 packets offered by the packet processor to traffic manager";
                                                    }

                                                    leaf ipv4-offered-octets {
                                                        type yang:counter64;
                                                        description "The number of ipv4 octets offered by the packet processor to traffic manager";
                                                    }

                                                    leaf ipv6-offered-packets {
                                                        type yang:counter64;
                                                        description "The number of ipv6 packets offered by the packet processor to traffic manager";
                                                    }

                                                    leaf ipv6-offered-octets {
                                                        type yang:counter64;
                                                        description "The number of ipv6 octets offered by the packet processor to traffic manager";
                                                    }

                                                    leaf ipv4-dropped-packets {
                                                        type yang:counter64;
                                                        description "The number of ipv4 packets dropped by the packet processor to traffic manager";
                                                    }

                                                    leaf ipv4-dropped-octets {
                                                        type yang:counter64;
                                                        description "The number of ipv4 octets dropped by the packet processor to traffic manager";
                                                    }

                                                    leaf ipv6-dropped-packets {
                                                        type yang:counter64;
                                                        description "The number of ipv6 packets dropped by the packet processor to traffic manager";
                                                    }

                                                    leaf ipv6-dropped-octets {
                                                        type yang:counter64;
                                                        description "The number of ipv6 octets dropped by the packet processor to traffic manager";
                                                    }

                                                    leaf ipv4-forwarded-packets {
                                                        type yang:counter64;
                                                        description "The number of ipv4 packets forwarded by the packet processor to traffic manager";
                                                    }

                                                    leaf ipv4-forwarded-octets {
                                                        type yang:counter64;
                                                        description "The number of ipv4 octets forwarded by the packet processor to traffic manager";
                                                    }

                                                    leaf ipv6-forwarded-packets {
                                                        type yang:counter64;
                                                        description "The number of ipv6 packets forwarded by the packet processor to traffic manager";
                                                    }

                                                    leaf ipv6-forwarded-octets {
                                                        type yang:counter64;
                                                        description "The number of ipv6 octets forwarded by the packet processor to traffic manager";
                                                    }

                                                } // container v4-v6

                                            }
                                        }
                                    } // container statistics

                                } // list policer

                            } // container sap-ingress

                        } // container qos

                    } // container ingress

                    container egress {
                        description "Enter the egress context";

                        container qos {
                            description "Enter the qos context";

                            container sap-egress {
                                description "Enter the sap-egress context";

                                container traffic-manager {
                                    description "Traffic manager information";

                                    container statistics {
                                        description "Statistics information";

                                        leaf in-inplus-profile-dropped-packets {
                                            type yang:counter64;
                                            description "Policy identifier";
                                        }

                                        leaf in-inplus-profile-dropped-octets {
                                            type yang:counter64;
                                            description
                                                "The number of in-profile octets
                                                 discarded by the egress traffic manager due
                                                 to: MBS exceeded, buffer pool limit
                                                 exceeded, etc.";
                                        }

                                        leaf out-exceed-profile-dropped-packets {
                                            type yang:counter64;
                                            description
                                                "The number of out-of-profile packets
                                                 discarded by the egress traffic manager due
                                                 to: MBS exceeded, buffer pool limit
                                                 exceeded, etc.";
                                        }

                                        leaf out-exceed-profile-dropped-octets {
                                            type yang:counter64;
                                            description
                                                "The number of out-of-profile packets
                                                 discarded by the egress traffic manager due
                                                 to: MBS exceeded, buffer pool limit
                                                 exceeded, etc.";
                                        }

                                        leaf in-inplus-profile-forwarded-packets {
                                            type yang:counter64;
                                            description
                                                "The number of in-profile packets
                                                 (rate below CIR) forwarded by the
                                                 egress traffic manager.";
                                        }

                                        leaf in-inplus-profile-forwarded-octets {
                                            type yang:counter64;
                                            description
                                                "The number of in-profile octets
                                                 (rate below CIR) forwarded by the
                                                 egress traffic manager.";
                                        }

                                        leaf out-exceed-profile-forwarded-packets {
                                            type yang:counter64;
                                            description
                                                "The number of out-of-profile packets
                                                 (rate above CIR) forwarded by the
                                                 egress traffic manager.";
                                        }

                                        leaf out-exceed-profile-forwarded-octets {
                                            type yang:counter64;
                                            description
                                                "The number of out-of-profile octets
                                                 (rate above CIR) forwarded by the
                                                 egress traffic manager.";
                                        }

                                        leaf aggregate-forwarded-packets {
                                            type yang:counter64;
                                            description
                                                "The aggregate number of in and out-of profile
                                                 packets forwarded by the egress traffic manager.";
                                        }

                                        leaf aggregate-forwarded-octets {
                                            type yang:counter64;
                                            description
                                                "The aggregate number of in and out-of profile
                                                 octets forwarded by the egress traffic manager.";
                                        }

                                        leaf aggregate-dropped-packets {
                                            type yang:counter64;
                                            description
                                                "The aggregate number of in and out-of profile
                                                 packets discarded by the egress traffic manager due
                                                 to: MBS exceeded, buffer pool limit
                                                 exceeded, etc.";
                                        }

                                        leaf aggregate-dropped-octets {
                                            type yang:counter64;
                                            description
                                                "The aggregate number of in and out-of profile
                                                 octets discarded by the egress traffic manager due
                                                 to: MBS exceeded, buffer pool limit
                                                 exceeded, etc.";
                                        }

                                        leaf last-cleared-time {
                                            type yang:date-and-time;
                                            description "Time when the counters in this table were last cleared.";
                                        }

                                    } // container statistics

                                } // container traffic-manager

                                list queue {
                                    key "queue-id";
                                    description "SAP Egress Queue statistics.";

                                    leaf queue-id {
                                        type types-qos:egress-queue-id;
                                        description "The unique identifier for the queue.";
                                    }

                                    container statistics {
                                        description "SAP Egress Queue statistics.";

                                        choice stat-mode {
                                            case profile {

                                                container profile {

                                                    leaf in-inplus-profile-forwarded-packets {
                                                        type yang:counter64;
                                                        description
                                                            "The number of in-profile/in-plus-profile packets
                                                             (rate below CIR) forwarded.";
                                                    }

                                                    leaf in-inplus-profile-forwarded-octets {
                                                        type yang:counter64;
                                                        description
                                                            "The number of in-profile/in-plus-profile octets
                                                             (rate below CIR) forwarded.";
                                                    }

                                                    leaf out-exceed-profile-forwarded-packets {
                                                        type yang:counter64;
                                                        description
                                                            "The number of out-profile/exceed-profile packets
                                                             (rate above CIR) forwarded.";
                                                    }

                                                    leaf out-exceed-profile-forwarded-octets {
                                                        type yang:counter64;
                                                        description
                                                            "The number of out-profile/exceed-profile octets
                                                             (rate above CIR) forwarded.";
                                                    }

                                                    leaf in-inplus-profile-dropped-packets {
                                                        type yang:counter64;
                                                        description
                                                            "The number of in-profile/in-plus-profile packets
                                                             discarded.";
                                                    }

                                                    leaf in-inplus-profile-dropped-octets {
                                                        type yang:counter64;
                                                        description
                                                            "The number of in-profile/in-plus-profile octets
                                                             discarded.";
                                                    }

                                                    leaf out-exceed-profile-dropped-packets {
                                                        type yang:counter64;
                                                        description
                                                            "The number of out-profile/exceed-profile packets
                                                             discarded.";
                                                    }

                                                    leaf out-exceed-profile-dropped-octets {
                                                        type yang:counter64;
                                                        description
                                                            "The number of out-profile/exceed-profile octets
                                                             discarded.";
                                                    }

                                                } // container profile

                                            }
                                            case v4-v6 {

                                                container v4-v6 {

                                                    leaf ipv4-dropped-packets {
                                                        type yang:counter64;
                                                        description "The number of ipv4 packets discarded.";
                                                    }

                                                    leaf ipv4-dropped-octets {
                                                        type yang:counter64;
                                                        description "The number of ipv4 octets discarded.";
                                                    }

                                                    leaf ipv6-dropped-packets {
                                                        type yang:counter64;
                                                        description "The number of ipv6 packets discarded.";
                                                    }

                                                    leaf ipv6-dropped-octets {
                                                        type yang:counter64;
                                                        description "The number of ipv6 octets discarded.";
                                                    }

                                                    leaf ipv4-forwarded-packets {
                                                        type yang:counter64;
                                                        description "The number of ipv4 packets forwarded.";
                                                    }

                                                    leaf ipv4-forwarded-octets {
                                                        type yang:counter64;
                                                        description "The number of ipv4 octets forwarded.";
                                                    }

                                                    leaf ipv6-forwarded-packets {
                                                        type yang:counter64;
                                                        description "The number of ipv6 packets forwarded.";
                                                    }

                                                    leaf ipv6-forwarded-octets {
                                                        type yang:counter64;
                                                        description "The number of ipv6 octets forwarded.";
                                                    }

                                                } // container v4-v6

                                            }
                                        }
                                    } // container statistics

                                } // list queue

                                list policer {
                                    key "policer-id";
                                    description "SAP Egress Policer statistics.";

                                    leaf policer-id {
                                        type types-qos:sap-egress-policer-id;
                                        description "The unique identifier for the policer.";
                                    }

                                    container statistics {
                                        description "SAP Egress Policer statistics.";

                                        choice stat-mode {
                                            case minimal {

                                                container minimal {

                                                    leaf all-offered-packets {
                                                        type yang:counter64;
                                                        description "The number of all the priority packets offered by the packet processor to traffic manager";
                                                    }

                                                    leaf all-offered-octets {
                                                        type yang:counter64;
                                                        description "The number of all the priority octets offered by the packet processor to traffic manager";
                                                    }

                                                    leaf all-dropped-packets {
                                                        type yang:counter64;
                                                        description "The number of all the priority packets dropped by the packet processor to traffic manager";
                                                    }

                                                    leaf all-dropped-octets {
                                                        type yang:counter64;
                                                        description "The number of all the priority octets dropped by the packet processor to traffic manager";
                                                    }

                                                    leaf all-forwarded-packets {
                                                        type yang:counter64;
                                                        description "The number of all the priority packets forwarded by the packet processor to traffic manager";
                                                    }

                                                    leaf all-forwarded-octets {
                                                        type yang:counter64;
                                                        description "The number of all the priority octets forwarded by the packet processor to traffic manager";
                                                    }

                                                } // container minimal

                                            }
                                            case offered-profile-no-cir {

                                                container offered-profile-no-cir {

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-profile-no-cir

                                            }
                                            case offered-profile-cir {

                                                container offered-profile-cir {

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf uncolor-offered-packets {
                                                        type yang:counter64;
                                                        description "The number of uncolor packets offered by the packet processor to traffic manager";
                                                    }

                                                    leaf uncolor-offered-octets {
                                                        type yang:counter64;
                                                        description "The number of uncolor octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-profile-cir

                                            }
                                            case offered-total-cir {

                                                container offered-total-cir {

                                                    leaf all-offered-packets {
                                                        type yang:counter64;
                                                        description "The number of all the priority packets offered by the packet processor to traffic manager";
                                                    }

                                                    leaf all-offered-octets {
                                                        type yang:counter64;
                                                        description "The number of all the priority octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-total-cir

                                            }
                                            case offered-limited-capped-cir {

                                                container offered-limited-capped-cir {

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                    leaf out-profile-offered-packets {
                                                        type yang:counter64;
                                                        description "The number of out-of-rofile packets offered by the packet processor to traffic manager";
                                                    }

                                                    leaf out-profile-offered-octets {
                                                        type yang:counter64;
                                                        description "The number of out-of-profile octets offered by the packet processor to traffic manager";
                                                    }

                                                } // container offered-limited-capped-cir

                                            }
                                            case offered-profile-capped-cir {

                                                container offered-profile-capped-cir {

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf uncolor-offered-packets {
                                                        type yang:counter64;
                                                        description "The number of uncolor packets offered by the packet processor to traffic manager";
                                                    }

                                                    leaf uncolor-offered-octets {
                                                        type yang:counter64;
                                                        description "The number of uncolor octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-profile-capped-cir

                                            }
                                            case offered-total-cir-exceed {

                                                container offered-total-cir-exceed {

                                                    leaf all-offered-packets {
                                                        type yang:counter64;
                                                        description "The number of all the priority packets offered by the packet processor to traffic manager";
                                                    }

                                                    leaf all-offered-octets {
                                                        type yang:counter64;
                                                        description "The number of all the priority octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf exceed-profile-dropped-packets {
                                                        type yang:counter64;
                                                        description "The number of exceed-profile packets dropped by the packet processor to traffic manager";
                                                    }

                                                    leaf exceed-profile-dropped-octets {
                                                        type yang:counter64;
                                                        description "The number of exceed-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                    leaf exceed-profile-forwarded-packets {
                                                        type yang:counter64;
                                                        description "The number of exceed-profile packets forwarded by the packet processor to traffic manager";
                                                    }

                                                    leaf exceed-profile-forwarded-octets {
                                                        type yang:counter64;
                                                        description "The number of exceed-profile octets forwarded by the packet processor to traffic manager";
                                                    }

                                                } // container offered-total-cir-exceed

                                            }
                                            case offered-four-profile-no-cir {

                                                container offered-four-profile-no-cir {

                                                    leaf inplus-profile-offered-packets {
                                                        type yang:counter64;
                                                        description "The number of inplus-profile packets offered by the packet processor to traffic manager";
                                                    }

                                                    leaf inplus-profile-offered-octets {
                                                        type yang:counter64;
                                                        description "The number of inplus-profile octets offered by the packet processor to traffic manager";
                                                    }

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf exceed-profile-offered-packets {
                                                        type yang:counter64;
                                                        description "The number of exceed-profile packets offered by the packet processor to traffic manager";
                                                    }

                                                    leaf exceed-profile-offered-octets {
                                                        type yang:counter64;
                                                        description "The number of exceed-profile octets offered by the packet processor to traffic manager";
                                                    }

                                                    leaf inplus-profile-dropped-packets {
                                                        type yang:counter64;
                                                        description "The number of inplus-profile packets dropped by the packet processor to traffic manager";
                                                    }

                                                    leaf inplus-profile-dropped-octets {
                                                        type yang:counter64;
                                                        description "The number of inplus-profile octets dropped by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf exceed-profile-dropped-packets {
                                                        type yang:counter64;
                                                        description "The number of exceed-profile packets dropped by the packet processor to traffic manager";
                                                    }

                                                    leaf exceed-profile-dropped-octets {
                                                        type yang:counter64;
                                                        description "The number of exceed-profile octets dropped by the packet processor to traffic manager";
                                                    }

                                                    leaf inplus-profile-forwarded-packets {
                                                        type yang:counter64;
                                                        description "The number of inplus-profile packets forwarded by the packet processor to traffic manager";
                                                    }

                                                    leaf inplus-profile-forwarded-octets {
                                                        type yang:counter64;
                                                        description "The number of inplus-profile octets forwarded by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                    leaf exceed-profile-forwarded-packets {
                                                        type yang:counter64;
                                                        description "The number of exceed-profile packets forwarded by the packet processor to traffic manager";
                                                    }

                                                    leaf exceed-profile-forwarded-octets {
                                                        type yang:counter64;
                                                        description "The number of exceed-profile octets forwarded by the packet processor to traffic manager";
                                                    }

                                                } // container offered-four-profile-no-cir

                                            }
                                            case offered-total-cir-four-profile {

                                                container offered-total-cir-four-profile {

                                                    leaf all-offered-packets {
                                                        type yang:counter64;
                                                        description "The number of all the priority packets offered by the packet processor to traffic manager";
                                                    }

                                                    leaf all-offered-octets {
                                                        type yang:counter64;
                                                        description "The number of all the priority octets offered by the packet processor to traffic manager";
                                                    }

                                                    leaf inplus-profile-dropped-packets {
                                                        type yang:counter64;
                                                        description "The number of inplus-profile packets dropped by the packet processor to traffic manager";
                                                    }

                                                    leaf inplus-profile-dropped-octets {
                                                        type yang:counter64;
                                                        description "The number of inplus-profile octets dropped by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf exceed-profile-dropped-packets {
                                                        type yang:counter64;
                                                        description "The number of exceed-profile packets dropped by the packet processor to traffic manager";
                                                    }

                                                    leaf exceed-profile-dropped-octets {
                                                        type yang:counter64;
                                                        description "The number of exceed-profile octets dropped by the packet processor to traffic manager";
                                                    }

                                                    leaf inplus-profile-forwarded-packets {
                                                        type yang:counter64;
                                                        description "The number of inplus-profile packets forwarded by the packet processor to traffic manager";
                                                    }

                                                    leaf inplus-profile-forwarded-octets {
                                                        type yang:counter64;
                                                        description "The number of inplus-profile octets forwarded by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                    leaf exceed-profile-forwarded-packets {
                                                        type yang:counter64;
                                                        description "The number of exceed-profile packets forwarded by the packet processor to traffic manager";
                                                    }

                                                    leaf exceed-profile-forwarded-octets {
                                                        type yang:counter64;
                                                        description "The number of exceed-profile octets forwarded by the packet processor to traffic manager";
                                                    }

                                                } // container offered-total-cir-four-profile

                                            }
                                            case v4-v6 {

                                                container v4-v6 {

                                                    leaf ipv4-offered-packets {
                                                        type yang:counter64;
                                                        description "The number of ipv4 packets offered by the packet processor to traffic manager";
                                                    }

                                                    leaf ipv4-offered-octets {
                                                        type yang:counter64;
                                                        description "The number of ipv4 octets offered by the packet processor to traffic manager";
                                                    }

                                                    leaf ipv6-offered-packets {
                                                        type yang:counter64;
                                                        description "The number of ipv6 packets offered by the packet processor to traffic manager";
                                                    }

                                                    leaf ipv6-offered-octets {
                                                        type yang:counter64;
                                                        description "The number of ipv6 octets offered by the packet processor to traffic manager";
                                                    }

                                                    leaf ipv4-dropped-packets {
                                                        type yang:counter64;
                                                        description "The number of ipv4 packets dropped by the packet processor to traffic manager";
                                                    }

                                                    leaf ipv4-dropped-octets {
                                                        type yang:counter64;
                                                        description "The number of ipv4 octets dropped by the packet processor to traffic manager";
                                                    }

                                                    leaf ipv6-dropped-packets {
                                                        type yang:counter64;
                                                        description "The number of ipv6 packets dropped by the packet processor to traffic manager";
                                                    }

                                                    leaf ipv6-dropped-octets {
                                                        type yang:counter64;
                                                        description "The number of ipv6 octets dropped by the packet processor to traffic manager";
                                                    }

                                                    leaf ipv4-forwarded-packets {
                                                        type yang:counter64;
                                                        description "The number of ipv4 packets forwarded by the packet processor to traffic manager";
                                                    }

                                                    leaf ipv4-forwarded-octets {
                                                        type yang:counter64;
                                                        description "The number of ipv4 octets forwarded by the packet processor to traffic manager";
                                                    }

                                                    leaf ipv6-forwarded-packets {
                                                        type yang:counter64;
                                                        description "The number of ipv6 packets forwarded by the packet processor to traffic manager";
                                                    }

                                                    leaf ipv6-forwarded-octets {
                                                        type yang:counter64;
                                                        description "The number of ipv6 octets forwarded by the packet processor to traffic manager";
                                                    }

                                                } // container v4-v6

                                            }
                                            case bonding {

                                                container bonding {

                                                    leaf connection-1-offered-packets {
                                                        type yang:counter64;
                                                        description "The number of connection-1 packets offered by the packet processor to traffic manager";
                                                    }

                                                    leaf connection-1-offered-octets {
                                                        type yang:counter64;
                                                        description "The number of connection-1 octets offered by the packet processor to traffic manager";
                                                    }

                                                    leaf connection-2-offered-packets {
                                                        type yang:counter64;
                                                        description "The number of connection-2 packets offered by the packet processor to traffic manager";
                                                    }

                                                    leaf connection-2-offered-octets {
                                                        type yang:counter64;
                                                        description "The number of connection-2 octets offered by the packet processor to traffic manager";
                                                    }

                                                    leaf connection-1-dropped-packets {
                                                        type yang:counter64;
                                                        description "The number of connection-1 packets dropped by the packet processor to traffic manager";
                                                    }

                                                    leaf connection-1-dropped-octets {
                                                        type yang:counter64;
                                                        description "The number of connection-1 octets dropped by the packet processor to traffic manager";
                                                    }

                                                    leaf connection-2-dropped-packets {
                                                        type yang:counter64;
                                                        description "The number of connection-2 packets dropped by the packet processor to traffic manager";
                                                    }

                                                    leaf connection-2-dropped-octets {
                                                        type yang:counter64;
                                                        description "The number of connection-2 octets dropped by the packet processor to traffic manager";
                                                    }

                                                    leaf connection-1-forwarded-packets {
                                                        type yang:counter64;
                                                        description "The number of connection-1 packets forwarded by the packet processor to traffic manager";
                                                    }

                                                    leaf connection-1-forwarded-octets {
                                                        type yang:counter64;
                                                        description "The number of connection-1 octets forwarded by the packet processor to traffic manager";
                                                    }

                                                    leaf connection-2-forwarded-packets {
                                                        type yang:counter64;
                                                        description "The number of connection-2 packets forwarded by the packet processor to traffic manager";
                                                    }

                                                    leaf connection-2-forwarded-octets {
                                                        type yang:counter64;
                                                        description "The number of connection-2 octets forwarded by the packet processor to traffic manager";
                                                    }

                                                } // container bonding

                                            }
                                        }
                                    } // container statistics

                                } // list policer

                            } // container sap-egress

                        } // container qos

                    } // container egress

                    container lag {
                        description "Lag information";

                        leaf active-port {
                            type types-sros:port;
                            description
                                "Port on the lag associated with this SAP, that is used when
                                 lag-per-link-hash is enabled on the lag or when lag-link-map-profile
                                 is configured on this SAP.";
                        }

                        container per-link-hash-oper {
                            description "Lag per-link-hash information";

                            leaf class {
                                type int32;
                                description "Operational value for class associated with this SAP.";
                            }

                            leaf weight {
                                type int32;
                                description "Operational value used for weight associated with this SAP.";
                            }

                            leaf is-overriden {
                                type boolean;
                                description
                                    "Whether administrative values, subscriber management determined
                                     operational weight and class are used for this SAP.";
                            }

                        } // container per-link-hash-oper

                    } // container lag

                    container eth-cfm {
                        description "Enter the eth-cfm context";

                        list mep {
                            key "md-admin-name ma-admin-name mep-id";
                            description "Enter the mep list instance";

                            leaf md-admin-name {
                                type leafref {
                                    path "../../../../../../../eth-cfm/domain/md-admin-name";
                                }
                                description "Admin-assigned maintenance domain index value";
                            }

                            leaf ma-admin-name {
                                type leafref {
                                    path "../../../../../../../eth-cfm/domain[md-admin-name=current()/../md-admin-name]/association/ma-admin-name";
                                }
                                description "Admin-assigned maintenance association index value";
                            }

                            leaf mep-id {
                                type types-eth-cfm:mep-id-type;
                                description "MEP identifier";
                            }

                        } // list mep

                    } // container eth-cfm

                    list ip-tunnel {
                        key "tunnel-name";
                        description "Enter the ip-tunnel list instance";

                        leaf tunnel-name {
                            type types-sros:interface-name;
                            description "IP tunnel name";
                        }

                        leaf host-mda {
                            type types-isa:slot-mda;
                            description "Active ISA that is being used to host this tunnel.";
                        }

                        leaf last-oper-changed {
                            type types-sros:date-time;
                            description "Last operational status change time.";
                        }

                        leaf oper-state {
                            type types-sros:oper-state;
                            description "Operational state of the tunnel.";
                        }

                        leaf oper-flags {
                            type bits {
                                bit unresolved-local-ip            { position 0; }
                                bit tunnel-admin-down              { position 1; }
                                bit sap-down                       { position 2; }
                                bit unresolved-delivery-svc        { position 3; }
                                bit unregistered-local-ip          { position 4; }
                                bit remote-ip-unreachable          { position 5; }
                                bit unresolved-dst-ip              { position 6; }
                            }
                            description "Reason why the tunnel is operationally down";
                        }

                        leaf oper-remote-ip-address {
                            type types-sros:ip-address;
                            description "Operational remote IP address.";
                        }

                        list dest-ip {
                            key "dest-ip-address";
                            description "Add a list entry for dest-ip";

                            leaf dest-ip-address {
                                type types-sros:ip-address;
                                description "Destination IP address of the tunnel";
                            }

                            leaf dest-ip-address-resolved {
                                type boolean;
                                description
                                    "IP tunnel destination address has been resolved
                                     as reachable by the virtual router";
                            }

                        } // list dest-ip

                    } // list ip-tunnel

                    list ipsec-gateway {
                        key "name";
                        description "Enter the ipsec-gateway list instance";

                        leaf name {
                            type types-sros:named-item;
                            description "IPsec gateway name.";
                        }

                        leaf oper-flags {
                            type bits {
                                bit local-ip-unreachable           { position 0; }
                                bit gateway-admin-down             { position 1; }
                                bit x509-cert-unavailable          { position 2; }
                                bit private-key-unavailable        { position 3; }
                                bit ca-cert-unavailable            { position 4; }
                                bit ca-crl-unavailable             { position 5; }
                                bit trust-anchors-down             { position 6; }
                                bit cert-profile-down              { position 7; }
                                bit invalid-cert-key-combo         { position 8; }
                                bit ike-not-ready                  { position 9; }
                            }
                            description "The reason why the IPsec gateway is operationally down.";
                        }

                        leaf oper-state {
                            type types-ipsec:oper-state;
                            description "The operational status of this IPsec gateway.";
                        }

                        container statistics {
                            description "Statistics for a specific IPsec gateway.";

                            leaf dynamic-lan-to-lan-tunnels {
                                type yang:gauge32;
                                description
                                    "The number of dynamic LAN-to-LAN (SL2L) tunnels associated
                                     with this IPsec gateway.";
                            }

                            leaf remote-access-tunnels {
                                type yang:gauge32;
                                description
                                    "The number of remote access (RA) tunnels associated
                                     to this IPsec gateway";
                            }

                            container number-of-tunnels {

                                container current {
                                    description "Current number of operational up IPsec tunnels.";

                                    leaf dynamic-lan-to-lan {
                                        type yang:counter64;
                                        description "Number of IPsec dynamic LAN-to-LAN (DL2L) tunnels.";
                                    }

                                    leaf remote-access {
                                        type yang:counter64;
                                        description "Number of IPsec remote access (RA) tunnels.";
                                    }

                                    leaf total {
                                        type yang:counter64;
                                        description "Total number of IPsec tunnels.";
                                    }

                                    leaf start-time {
                                        type yang:date-and-time;
                                        description "The time when the sampling interval started.";
                                    }

                                } // container current

                                list historical {
                                    key "index";
                                    description "Historical number of operational up IPsec tunnels.";

                                    leaf index {
                                        type uint32 {
                                            range "2..max";
                                        }
                                        description
                                            "The index of the finished sampling interval period for this statistic.
                                             It starts with '2' and is ordered by start time of intervals so that
                                             smaller index indicate more recent intervals.";
                                    }

                                    leaf dynamic-lan-to-lan {
                                        type yang:counter64;
                                        description "Number of IPsec dynamic LAN-to-LAN (DL2L) tunnels.";
                                    }

                                    leaf remote-access {
                                        type yang:counter64;
                                        description "Number of IPsec remote access (RA) tunnels.";
                                    }

                                    leaf total {
                                        type yang:counter64;
                                        description "Total number of IPsec tunnels.";
                                    }

                                    leaf start-time {
                                        type yang:date-and-time;
                                        description "The time when the sampling interval started.";
                                    }

                                } // list historical

                            } // container number-of-tunnels

                            container throughput {

                                container current {
                                    description "Current statistics of the encrypted and decrypted IPsec throughput.";

                                    leaf start-time {
                                        type yang:date-and-time;
                                        description "The time when the sampling interval started.";
                                    }

                                    leaf sampling-duration {
                                        type types-sros:time-duration;
                                        description "The duration of the corresponding sampling interval.";
                                    }

                                    container packets {

                                        leaf encrypted {
                                            type yang:counter64;
                                            units "packets per second";
                                            description "Encrypted IPsec traffic throughput.";
                                        }

                                        leaf decrypted {
                                            type yang:counter64;
                                            units "packets per second";
                                            description "Decrypted IPsec traffic throughput.";
                                        }

                                        leaf total {
                                            type yang:counter64;
                                            units "packets per second";
                                            description "Encrypted and decrypted IPsec traffic throughput.";
                                        }

                                    } // container packets

                                    container bytes {

                                        leaf encrypted {
                                            type yang:counter64;
                                            units "megabps";
                                            description "Encrypted IPsec traffic throughput.";
                                        }

                                        leaf decrypted {
                                            type yang:counter64;
                                            units "megabps";
                                            description "Decrypted IPsec traffic throughput.";
                                        }

                                        leaf total {
                                            type yang:counter64;
                                            units "megabps";
                                            description "Encrypted and decrypted IPsec traffic throughput.";
                                        }

                                    } // container bytes

                                } // container current

                                list historical {
                                    key "index";
                                    description "Historical statistics of the encrypted and decrypted IPsec throughput.";

                                    leaf index {
                                        type uint32 {
                                            range "2..max";
                                        }
                                        description
                                            "The index of the finished sampling interval period for this statistic.
                                             It starts with '2' and is ordered by start time of intervals so that
                                             smaller index indicate more recent intervals.";
                                    }

                                    leaf start-time {
                                        type yang:date-and-time;
                                        description "The time when the sampling interval started.";
                                    }

                                    leaf sampling-duration {
                                        type types-sros:time-duration;
                                        description "The duration of the corresponding sampling interval.";
                                    }

                                    container packets {

                                        leaf encrypted {
                                            type yang:counter64;
                                            units "packets per second";
                                            description "Encrypted IPsec traffic throughput.";
                                        }

                                        leaf decrypted {
                                            type yang:counter64;
                                            units "packets per second";
                                            description "Decrypted IPsec traffic throughput.";
                                        }

                                        leaf total {
                                            type yang:counter64;
                                            units "packets per second";
                                            description "Encrypted and decrypted IPsec traffic throughput.";
                                        }

                                    } // container packets

                                    container bytes {

                                        leaf encrypted {
                                            type yang:counter64;
                                            units "megabps";
                                            description "Encrypted IPsec traffic throughput.";
                                        }

                                        leaf decrypted {
                                            type yang:counter64;
                                            units "megabps";
                                            description "Decrypted IPsec traffic throughput.";
                                        }

                                        leaf total {
                                            type yang:counter64;
                                            units "megabps";
                                            description "Encrypted and decrypted IPsec traffic throughput.";
                                        }

                                    } // container bytes

                                } // list historical

                            } // container throughput

                            container tunnel-setup-rate {

                                container current {
                                    description "Current statistics of successfully established IPsec tunnels.";

                                    leaf total {
                                        type decimal64 {
                                            fraction-digits 2;
                                        }
                                        units "tunnels per second";
                                        description "Total IPsec tunnel setup rate.";
                                    }

                                    leaf dynamic-lan-to-lan {
                                        type decimal64 {
                                            fraction-digits 2;
                                        }
                                        units "tunnels per second";
                                        description "Dynamic LAN-to-LAN (DL2L) tunnel setup rate.";
                                    }

                                    leaf remote-access {
                                        type decimal64 {
                                            fraction-digits 2;
                                        }
                                        units "tunnels per second";
                                        description "Remote access (RA) tunnel setup rate.";
                                    }

                                    leaf start-time {
                                        type yang:date-and-time;
                                        description "The time when the sampling interval started.";
                                    }

                                    leaf sampling-duration {
                                        type types-sros:time-duration;
                                        description "The duration of the corresponding sampling interval.";
                                    }

                                } // container current

                                list historical {
                                    key "index";
                                    description "Historical statistics of successfully established IPsec tunnels.";

                                    leaf index {
                                        type uint32 {
                                            range "2..max";
                                        }
                                        description
                                            "The index of the finished sampling interval period for this statistic.
                                             It starts with '2' and is ordered by start time of intervals so that
                                             smaller index indicate more recent intervals.";
                                    }

                                    leaf total {
                                        type decimal64 {
                                            fraction-digits 2;
                                        }
                                        units "tunnels per second";
                                        description "Total IPsec tunnel setup rate.";
                                    }

                                    leaf dynamic-lan-to-lan {
                                        type decimal64 {
                                            fraction-digits 2;
                                        }
                                        units "tunnels per second";
                                        description "Dynamic LAN-to-LAN (DL2L) tunnel setup rate.";
                                    }

                                    leaf remote-access {
                                        type decimal64 {
                                            fraction-digits 2;
                                        }
                                        units "tunnels per second";
                                        description "Remote access (RA) tunnel setup rate.";
                                    }

                                    leaf start-time {
                                        type yang:date-and-time;
                                        description "The time when the sampling interval started.";
                                    }

                                    leaf sampling-duration {
                                        type types-sros:time-duration;
                                        description "The duration of the corresponding sampling interval.";
                                    }

                                } // list historical

                            } // container tunnel-setup-rate

                            container traffic-forward {

                                container current {

                                    leaf start-time {
                                        type yang:date-and-time;
                                        description "The time when the sampling interval started.";
                                    }

                                    leaf sampling-duration {
                                        type types-sros:time-duration;
                                        description "The duration of the corresponding sampling interval.";
                                    }

                                    container packets {
                                        description "Statistics on encrypted and decrypted IPsec traffic packets.";

                                        leaf encrypted {
                                            type yang:counter64;
                                            units "packets";
                                            description "Number of encrypted IPsec packets.";
                                        }

                                        leaf decrypted {
                                            type yang:counter64;
                                            units "packets";
                                            description "Number of decrypted IPsec packets.";
                                        }

                                        leaf total {
                                            type yang:counter64;
                                            units "packets";
                                            description "Number of encrypted and decrypted IPsec packets.";
                                        }

                                    } // container packets

                                    container bytes {
                                        description "Statistics on encrypted and decrypted IPsec traffic packets.";

                                        leaf encrypted {
                                            type yang:counter64;
                                            units "kilobytes";
                                            description "Number of kilobytes in the encrypted IPsec packets.";
                                        }

                                        leaf decrypted {
                                            type yang:counter64;
                                            units "kilobytes";
                                            description "Number of kilobytes in the decrypted IPsec packets.";
                                        }

                                        leaf total {
                                            type yang:counter64;
                                            units "kilobytes";
                                            description "Number of kilobytes in the encrypted and decrypted IPsec packets.";
                                        }

                                    } // container bytes

                                } // container current

                            } // container traffic-forward

                            container ike-exchange-failure-rate {

                                container current {
                                    description "Current statistics of IKE exchange failures.";

                                    leaf start-time {
                                        type yang:date-and-time;
                                        description "The time when the sampling interval started.";
                                    }

                                    leaf sampling-duration {
                                        type types-sros:time-duration;
                                        description "The duration of the corresponding sampling interval.";
                                    }

                                    container auth-failure {

                                        leaf count {
                                            type decimal64 {
                                                fraction-digits 2;
                                            }
                                            units "failures per second";
                                            description "IKE exchange failure rate - authentication.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container auth-failure

                                    container non-proposal-chosen {

                                        leaf count {
                                            type decimal64 {
                                                fraction-digits 2;
                                            }
                                            units "failures per second";
                                            description "IKE exchange failure rate - non-proposal chosen.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container non-proposal-chosen

                                    container internal-address-assignment {

                                        leaf count {
                                            type decimal64 {
                                                fraction-digits 2;
                                            }
                                            units "failures per second";
                                            description "IKE exchange failure rate - address assignment.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container internal-address-assignment

                                    container invalid-ts {

                                        leaf count {
                                            type decimal64 {
                                                fraction-digits 2;
                                            }
                                            units "failures per second";
                                            description "IKE exchange failure rate - invalid traffic selector.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container invalid-ts

                                    container invalid-ke {

                                        leaf count {
                                            type decimal64 {
                                                fraction-digits 2;
                                            }
                                            units "failures per second";
                                            description "IKE exchange failure rate - invalid key exchange.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container invalid-ke

                                    container dpd-timeout {

                                        leaf count {
                                            type decimal64 {
                                                fraction-digits 2;
                                            }
                                            units "failures per second";
                                            description "IKE exchange failure rate - DPD timeout.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container dpd-timeout

                                    container other {

                                        leaf count {
                                            type decimal64 {
                                                fraction-digits 2;
                                            }
                                            units "failures per second";
                                            description "IKE exchange failure rate - other failure reasons.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container other

                                } // container current

                                list historical {
                                    key "index";
                                    description "Historical statistics of IKE exchange failures.";

                                    leaf index {
                                        type uint32 {
                                            range "2..max";
                                        }
                                        description
                                            "The index of the finished sampling interval period for this statistic.
                                             It starts with '2' and is ordered by start time of intervals so that
                                             smaller index indicate more recent intervals.";
                                    }

                                    leaf start-time {
                                        type yang:date-and-time;
                                        description "The time when the sampling interval started.";
                                    }

                                    leaf sampling-duration {
                                        type types-sros:time-duration;
                                        description "The duration of the corresponding sampling interval.";
                                    }

                                    container auth-failure {

                                        leaf count {
                                            type decimal64 {
                                                fraction-digits 2;
                                            }
                                            units "failures per second";
                                            description "IKE exchange failure rate - authentication.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container auth-failure

                                    container non-proposal-chosen {

                                        leaf count {
                                            type decimal64 {
                                                fraction-digits 2;
                                            }
                                            units "failures per second";
                                            description "IKE exchange failure rate - non-proposal chosen.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container non-proposal-chosen

                                    container internal-address-assignment {

                                        leaf count {
                                            type decimal64 {
                                                fraction-digits 2;
                                            }
                                            units "failures per second";
                                            description "IKE exchange failure rate - address assignment.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container internal-address-assignment

                                    container invalid-ts {

                                        leaf count {
                                            type decimal64 {
                                                fraction-digits 2;
                                            }
                                            units "failures per second";
                                            description "IKE exchange failure rate - invalid traffic selector.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container invalid-ts

                                    container invalid-ke {

                                        leaf count {
                                            type decimal64 {
                                                fraction-digits 2;
                                            }
                                            units "failures per second";
                                            description "IKE exchange failure rate - invalid key exchange.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container invalid-ke

                                    container dpd-timeout {

                                        leaf count {
                                            type decimal64 {
                                                fraction-digits 2;
                                            }
                                            units "failures per second";
                                            description "IKE exchange failure rate - DPD timeout.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container dpd-timeout

                                    container other {

                                        leaf count {
                                            type decimal64 {
                                                fraction-digits 2;
                                            }
                                            units "failures per second";
                                            description "IKE exchange failure rate - other failure reasons.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container other

                                } // list historical

                            } // container ike-exchange-failure-rate

                        } // container statistics

                        list dynamic-tunnel {
                            key "address port";
                            description "Dynamic IPsec Remote-User Tunnel entries.";

                            leaf address {
                                type types-sros:ip-address;
                                description "The address of the SAP IPsec gateway to the tunnel";
                            }

                            leaf port {
                                type types-sros:tcp-udp-port;
                                description "The UDP port of the SAP IPsec gateway to the tunnel";
                            }

                            leaf private-service-name {
                                type types-services:service-name;
                                description "The name of the Tunnel delivery service.";
                            }

                            leaf private-interface-name {
                                type types-sros:interface-name;
                                description "The private interface name used by the tunnel";
                            }

                            leaf private-address {
                                type types-sros:ip-address;
                                description "The private IP address on the IPsec gateway tunnel";
                            }

                            leaf second-private-address {
                                type types-sros:ip-address;
                                description "The second private IP address on the IPsec gateway tunnel";
                            }

                            leaf tunnel-template {
                                type types-ipsec:tunnel-template-id;
                                description "The id of a tunnel template entry used for the tunnel";
                            }

                            leaf replay-window {
                                type uint32 {
                                    range "32|64|128|256|512";
                                }
                                description "The size of the anti-replay window";
                            }

                            leaf bi-direction-sa {
                                type boolean;
                                description "Indicates whether this tunnel has bi-directional Security-Association entries.";
                            }

                            leaf host-mda {
                                type types-isa:slot-mda;
                                description "Active ISA that is being used to host this tunnel";
                            }

                            leaf matched-trust-anchor {
                                type types-sros:named-item;
                                description
                                    "The name for matched Certificate-Authority Profile name associated
                                     with this SAP IPSec tunnel certificate.";
                            }

                            leaf last-oper-changed {
                                type yang:date-and-time;
                                description "Uptime at the time of the last operational status change of this IPsec gateway tunnel";
                            }

                            leaf ike-idi-type {
                                type enumeration {
                                    enum "ipv4-addr"                    { value 1; }
                                    enum "fqdn"                         { value 2; }
                                    enum "rfc-822-addr"                 { value 3; }
                                    enum "ipv6-addr"                    { value 5; }
                                    enum "der-asn1-dn"                  { value 9; }
                                    enum "der-asn1-gn"                  { value 10; }
                                    enum "key-id"                       { value 11; }
                                }
                                description "The direction on the IPsec tunnel to which this SA can be applied.";
                            }

                            leaf ike-idi-value {
                                type types-sros:display-string;
                                description "The ID type for the IKE header used in the tunnel associated with this entry.";
                            }

                            leaf ts-list {
                                type types-sros:named-item;
                                description "The traffic selector (TS) list used by this tunnel.";
                            }

                            leaf ike-policy {
                                type types-ipsec:ike-policy-id;
                                description "The IKE policy identifier used by this tunnel.";
                            }

                            container tcp-mss {

                                leaf public {
                                    type uint32;
                                    units "bytes";
                                    description
                                        "The Maximum Segment Size (MSS) for the TCP traffic in an IPsec tunnel
                                         which is sent from the public network to the private network.";
                                }

                                leaf private {
                                    type uint32;
                                    units "bytes";
                                    description
                                        "The Maximum Segment Size (MSS) for the TCP traffic in an IPsec tunnel
                                         which is sent from the private network to the public network.";
                                }

                            } // container tcp-mss

                            container ike-sa {
                                description "States related to the IKE SA.";

                                leaf oper-state {
                                    type enumeration {
                                        enum "up"                           { value 1; }
                                        enum "down"                         { value 2; }
                                    }
                                    description "The state of IKE SA";
                                }

                                leaf established-time {
                                    type yang:date-and-time;
                                    description "The time the IKE SA completed";
                                }

                                leaf negotiated-lifetime {
                                    type types-sros:time-duration;
                                    description "The lifetime negotiated for the IKE SA";
                                }

                                leaf expiration-time {
                                    type yang:date-and-time;
                                    description "The time when the IKE SA will expire";
                                }

                                leaf authentication-algorithm {
                                    type types-ipsec:auth-algorithms;
                                    description "The authentication algorithm of the IKE SA for this IPsec tunnel";
                                }

                                leaf encryption-algorithm {
                                    type types-ipsec:encryption-algorithms;
                                    description "The encryption algorithm of the IKE SA for this IPsec tunnel";
                                }

                                leaf prf-algorithm {
                                    type types-ipsec:prf-algorithms;
                                    description "The pseudo-random function (PRF)";
                                }

                                leaf dh-group {
                                    type types-ipsec:dh-group;
                                    description "The Diffie-Hellman (DH) group of the IKE SA for this IPsec tunnel";
                                }

                                leaf cert-profile-entry-id {
                                    type uint32;
                                    description "The matching certificate profile entry id used for this tunnel";
                                }

                                leaf cert-profile-name {
                                    type types-sros:named-item;
                                    description "The IPsec tunnel certificate profile name used for this tunnel";
                                }

                                leaf client-database {
                                    type uint32 {
                                        range "1..8000";
                                    }
                                    description "The client ID that was matched for this tunnel in the IPsec client database";
                                }

                                container statistics {
                                    description "Statistics related to the IKE SA.";

                                    leaf ctrl-packets-sent {
                                        type yang:counter32;
                                        description "The number of control packets this IPsec Tunnel has sent";
                                    }

                                    leaf ctrl-packets-received {
                                        type yang:counter32;
                                        description "The number of control packets this IPsec Tunnel has received";
                                    }

                                    leaf ctrl-packets-sent-errors {
                                        type yang:counter32;
                                        description "The number of control packet transmit errors";
                                    }

                                    leaf ctrl-packets-received-errors {
                                        type yang:counter32;
                                        description "The number of control packet receive errors";
                                    }

                                    leaf dpd-packets-sent {
                                        type yang:counter32;
                                        description "The number of number of Dead-Peer-Detection packets transmitted";
                                    }

                                    leaf dpd-packets-received {
                                        type yang:counter32;
                                        description "The number of Dead-Peer-Detection packets received";
                                    }

                                    leaf dpd-ack-packets-sent {
                                        type yang:counter32;
                                        description "The number of Dead-Peer-Detection acknowledgement packets transmitted";
                                    }

                                    leaf dpd-ack-packets-received {
                                        type yang:counter32;
                                        description "The number of Dead-Peer-Detection acknowledgement packets received";
                                    }

                                    leaf dpd-timeout-packets {
                                        type yang:counter32;
                                        description "The number of DPD R-U-THERE packets that have not been acknowledged";
                                    }

                                    leaf dpd-ack-packets-received-errors {
                                        type yang:counter32;
                                        description "The number of malformed DPD R-U-THERE acknowledgement packets received";
                                    }

                                } // container statistics

                            } // container ike-sa

                            list ipsec-sa {
                                key "security-association direction index";
                                description "Dynamic IPsec Remote-User Tunnel SA entries.";

                                leaf security-association {
                                    type uint32 {
                                        range "1..16";
                                    }
                                    description "The unique identifier of an security association (SA).";
                                }

                                leaf direction {
                                    type types-ipsec:direction;
                                    description "The direction on the IPsec tunnel to which this SA can be applied.";
                                }

                                leaf index {
                                    type uint32 {
                                        range "1..2";
                                    }
                                    description "The unique identifier of an security association (SA).";
                                }

                                leaf spi {
                                    type uint32;
                                    description
                                        "The SPI (Security Parameter Index) used to lookup the instruction to verify and decrypt
                                         the incoming IPsec packets when the value of direction is 'inbound'.";
                                }

                                leaf authentication-algorithm {
                                    type types-ipsec:auth-algorithms;
                                    description "The authentication algorithm used with this SA.";
                                }

                                leaf encryption-algorithm {
                                    type types-ipsec:encryption-algorithms;
                                    description "The encryption algorithm used with this SA.";
                                }

                                leaf established-time {
                                    type yang:date-and-time;
                                    description "The time when the IPsec SA negotiation completed.";
                                }

                                leaf negotiated-lifetime {
                                    type types-sros:time-duration;
                                    description "The lifetime negotiated for the IPsec SA.";
                                }

                                list ts {
                                    key "side from-address to-address min-port max-port protocol-id";
                                    description "Dynamic IPsec Remote-User Tunnel SA traffic selector entries.";

                                    leaf side {
                                        type types-ipsec:ts-side;
                                        description
                                            "Whether this SA entry is created manually by the user or
                                             dynamically by the IPsec subsystem.";
                                    }

                                    leaf from-address {
                                        type types-sros:ip-address;
                                        description "The beginning address of the range for this traffic selector entry.";
                                    }

                                    leaf to-address {
                                        type types-sros:ip-address;
                                        description "The end address of the range for this traffic selector entry.";
                                    }

                                    leaf min-port {
                                        type types-sros:tcp-udp-port;
                                        description
                                            "The minimum port number of the range for this IPsec traffic selector entry.

                                             When the value of min-port is 0 and the value of max-port is 65535,
                                             it means that the IPsec traffic selector accepts any port number.

                                             When the value of protocol-id is 1 (ICMP) or 58 (ICMPv6), the bits from 0 to 7 of min-port
                                             represent the minimum ICMP/ICMPv6 code and the bits from 8 to 15
                                             represent the minimum ICMP/ICMPv6 type.";
                                    }

                                    leaf max-port {
                                        type types-sros:tcp-udp-port;
                                        description
                                            "The maximum port number of the range for this IPsec traffic selector entry.

                                             When the value of max-port is 0 and the value of min-port is 65535,
                                             it means that the IPsec traffic selector accepts the packet only when the
                                             corresponding port field is unavailable.

                                             When the value of protocol-id is 1 (ICMP) or 58 (ICMPv6), the bits from 0 to 7 of max-port
                                             represent the maximum ICMP/ICMPv6 code and the bits from 8 to 15
                                             represent the maximum ICMP/ICMPv6 type.";
                                    }

                                    leaf protocol-id {
                                        type uint32 {
                                            range "0..255";
                                        }
                                        description
                                            "The IP protocol number for this IPsec traffic selector entry.

                                             A value of zero specifies that the IPsec traffic selector will accept
                                             packets for any protocol.";
                                    }

                                } // list ts

                                container isa {
                                    description "Dynamic IPsec Remote-User Tunnel SA Statistics.";

                                    leaf multicast-interface-name {
                                        type types-sros:named-item;
                                        description "The multicast interface name associated with this SA";
                                    }

                                    leaf multicast-protocol {
                                        type types-ipsec:multicast-protocol;
                                        description "The supported protocol types of the multicast interface associated to this SA";
                                    }

                                    leaf pfs-dh-group {
                                        type types-ipsec:dh-group;
                                        description "The Diffie-Hellman (DH) group used with this SA";
                                    }

                                    container fragmentation {

                                        leaf encapsulation-overhead {
                                            type uint32;
                                            description "The encapsulation overhead for this outbound SA.";
                                        }

                                        container pre-encapsulation {

                                            leaf last-packet-size {
                                                type uint32;
                                                units "bytes";
                                                description
                                                    "The size of the last packet which caused a pre-encapsulation fragmentation
                                                     to occur for this SA.";
                                            }

                                        } // container pre-encapsulation

                                        container post-encapsulation {

                                            leaf last-packet-size {
                                                type uint32;
                                                units "bytes";
                                                description
                                                    "The size of the last encapsulated packet which caused a post-encapsulation
                                                     fragmentation to occur for this SA.";
                                            }

                                        } // container post-encapsulation

                                    } // container fragmentation

                                    container statistics {

                                        leaf bytes-processed {
                                            type yang:counter64;
                                            description "The number of bytes successfully processed for this SA";
                                        }

                                        leaf packets-processed {
                                            type yang:counter64;
                                            description "The the number of packets successfully processed for this SA";
                                        }

                                        container errors {

                                            leaf crypto {
                                                type yang:counter32;
                                                description
                                                    "The number of crypto errors encountered on this SA.
                                                         
                                                     When the value of direction is 'inbound', the crypto-errors will be set for the following errors:
                                                         MAC miscompare
                                                         Pad errors
                                                         Illegal configure algorithm
                                                         Illegal authentication algorithm
                                                         Inner IP checksum errors
                                                         Payload alignment errors
                                                         Sequence number errors
                                                         Protocol errors
                                                          
                                                     When the value of direction is 'outbound', the crypto-errors will be set for the following errors:
                                                         Sequence wrap errors
                                                         Illegal configure algorithm
                                                         Illegal authentication algorithm
                                                         Expanded packet too big
                                                         TTL decrement errors.";
                                            }

                                            leaf replay {
                                                type yang:counter32;
                                                description "The number of replay errors encountered on this SA";
                                            }

                                            leaf security-association {
                                                type yang:counter32;
                                                description
                                                    "The number of SA errors encountered on this SA.
                                                     The SA errors means ISA tried to use a CHILD SA that is marked for deletion.";
                                            }

                                            leaf policy {
                                                type yang:counter32;
                                                description
                                                    "The number of policy errors encountered on this SA.
                                                     The policy errors include bundled SA, selector check and policy direction error.";
                                            }

                                        } // container errors

                                        container fragmentation {

                                            container pre-encapsulation {

                                                leaf count {
                                                    type yang:counter64;
                                                    description
                                                        "The number of fragmentations that occurred prior to encapsulation for this outbound SA.
                                                         Pre-encapsulation fragmentation occurs for IPv4 packets whose size exceeds tIPsecTnlTempIpMtu.";
                                                }

                                            } // container pre-encapsulation

                                            container post-encapsulation {

                                                leaf count {
                                                    type yang:counter64;
                                                    description
                                                        "The number of fragmentations that occurred after encapsulation for this SA.
                                                         Post-encapsulation fragmentation occurs when the encapsulated packet size exceeds tIPsecTnlTempEncapIpMtu.";
                                                }

                                            } // container post-encapsulation

                                        } // container fragmentation

                                    } // container statistics

                                } // container isa

                            } // list ipsec-sa

                            list dhcp-lease {
                                key "private-address";
                                description
                                    "Information of the private IP address DHCP leases
                                     in the dynamic IPsec remote user tunnel.";

                                leaf private-address {
                                    type types-sros:ip-address;
                                    description
                                        "The private IP address of the dynamic IPsec remote user tunnel.
                                         It can be equal to either private-address or second-private-address.";
                                }

                                leaf acquired {
                                    type yang:date-and-time;
                                    description
                                        "The time when the latest DHCP lease was acquired from the server.
                                         The address of the server is indicated by server-address.

                                         The value can be the time when the private IP address for the dynamic IPsec user remote tunnel
                                         first obtained the DHCP lease, or the time when the lease was renewed or rebound.";
                                }

                                leaf renew {
                                    type yang:date-and-time;
                                    description "The time when the current DHCP lease needs to be renewed";
                                }

                                leaf rebind {
                                    type yang:date-and-time;
                                    description "The time when the current DHCP lease needs to be rebound";
                                }

                                leaf valid-lifetime {
                                    type yang:date-and-time;
                                    description
                                        "The time when the valid lifetime of the private IP address for the dynamic IPsec user remote
                                         tunnel will expire. Once the valid lifetime expires, the private IP address must be renewed or rebound.";
                                }

                                leaf preferred-lifetime {
                                    type yang:date-and-time;
                                    description
                                        "The time when the preferred lifetime of the private IP address for the dynamic IPsec user remote
                                         tunnel will expire. In the preferred state, the private IP address can be used without any restriction.
                                         Once the lifetime expires, the private IP address is still valid, but needs to be renewed or rebound.";
                                }

                                leaf server-address {
                                    type types-sros:ip-address;
                                    description "The DHCP server address";
                                }

                            } // list dhcp-lease

                            container statistics {
                                description "Dynamic IPsec Remote-User Tunnel statistics collection.";

                                container traffic-forward {

                                    container current {

                                        leaf start-time {
                                            type yang:date-and-time;
                                            description "The time when the sampling interval started.";
                                        }

                                        leaf sampling-duration {
                                            type types-sros:time-duration;
                                            description "The duration of the corresponding sampling interval.";
                                        }

                                        container packets {
                                            description "Statistics on encrypted and decrypted IPsec traffic packets.";

                                            leaf encrypted {
                                                type yang:counter64;
                                                units "packets";
                                                description "Number of encrypted IPsec packets.";
                                            }

                                            leaf decrypted {
                                                type yang:counter64;
                                                units "packets";
                                                description "Number of decrypted IPsec packets.";
                                            }

                                            leaf total {
                                                type yang:counter64;
                                                units "packets";
                                                description "Number of encrypted and decrypted IPsec packets.";
                                            }

                                        } // container packets

                                        container bytes {
                                            description "Statistics on encrypted and decrypted IPsec traffic packets.";

                                            leaf encrypted {
                                                type yang:counter64;
                                                units "kilobytes";
                                                description "Number of kilobytes in the encrypted IPsec packets.";
                                            }

                                            leaf decrypted {
                                                type yang:counter64;
                                                units "kilobytes";
                                                description "Number of kilobytes in the decrypted IPsec packets.";
                                            }

                                            leaf total {
                                                type yang:counter64;
                                                units "kilobytes";
                                                description "Number of kilobytes in the encrypted and decrypted IPsec packets.";
                                            }

                                        } // container bytes

                                    } // container current

                                } // container traffic-forward

                            } // container statistics

                        } // list dynamic-tunnel

                    } // list ipsec-gateway

                    list ipsec-tunnel {
                        key "name";
                        description "Enter the ipsec-tunnel list instance";

                        leaf name {
                            type types-sros:named-item;
                            description "IPsec ipsec name.";
                        }

                        leaf host-mda {
                            type types-isa:slot-mda;
                            description "Active ISA that is being used to host this tunnel.";
                        }

                        leaf matched-trust-anchor {
                            type types-sros:named-item;
                            description
                                "The matched Certificate Authority (CA) profile name
                                 associated with the IPSec tunnel certificate.";
                        }

                        leaf oper-flags {
                            type bits {
                                bit unresolved-local-ip            { position 0; }
                                bit tunnel-admin-down              { position 1; }
                                bit sap-down                       { position 2; }
                                bit unresolved-delivery-svc        { position 3; }
                                bit bfd-session-down               { position 4; }
                                bit reserved-1                     { position 5; }
                                bit unresolved-dst-ip              { position 6; }
                                bit invalid-cert-file              { position 7; }
                                bit invalid-key-file               { position 8; }
                                bit trust-anchors-down             { position 9; }
                                bit cert-profile-down              { position 10; }
                                bit invalid-cert-key-combo         { position 11; }
                            }
                            description "The reason why the IPsec tunnel is operationally down.";
                        }

                        leaf oper-state {
                            type types-ipsec:oper-state;
                            description "The operational status of this IPsec tunnel.";
                        }

                        leaf last-oper-changed {
                            type yang:date-and-time;
                            description "Uptime at the time of the last operational status change of this IPsec tunnel";
                        }

                        container bfd {
                            description "Enter the bfd context";

                            container bfd-liveness {
                                description "Enter the bfd-liveness context";

                                leaf src-ip {
                                    type types-sros:ip-address;
                                    description "The source IP address on the interface running BFD.";
                                }

                                leaf oper-state {
                                    type types-ipsec:bfd-session-state;
                                    description
                                        "The operational state of the BFD session the IPsec tunnel
                                         is relying upon for its fast triggering mechanism.";
                                }

                            } // container bfd-liveness

                        } // container bfd

                        container key-exchange {
                            description "Enter the key-exchange context";

                            choice type {
                                case dynamic {

                                    container dynamic {
                                        description "Enter the dynamic context";

                                        container ike-sa {
                                            description "States related to the IKE SA.";

                                            leaf state {
                                                type enumeration {
                                                    enum "up"                           { value 1; }
                                                    enum "down"                         { value 2; }
                                                }
                                                description "The state of IKE SA";
                                            }

                                            leaf established-time {
                                                type yang:date-and-time;
                                                description "The time the IKE SA completed";
                                            }

                                            leaf negotiated-lifetime {
                                                type types-sros:time-duration;
                                                description "The lifetime negotiated for the IKE SA";
                                            }

                                            leaf expiration-time {
                                                type yang:date-and-time;
                                                description "The time when the IKE SA will expire";
                                            }

                                            leaf authentication-algorithm {
                                                type types-ipsec:auth-algorithms;
                                                description "The authentication algorithm of the IKE SA for this IPsec tunnel";
                                            }

                                            leaf encryption-algorithm {
                                                type types-ipsec:encryption-algorithms;
                                                description "The encryption algorithm of the IKE SA for this IPsec tunnel";
                                            }

                                            leaf prf-algorithm {
                                                type types-ipsec:prf-algorithms;
                                                description "The pseudo-random function (PRF)";
                                            }

                                            leaf dh-group {
                                                type types-ipsec:dh-group;
                                                description "The Diffie-Hellman (DH) group of the IKE SA for this IPsec tunnel.";
                                            }

                                            leaf cert-profile-entry-id {
                                                type uint32;
                                                description "The matching certificate profile entry id used for this tunnel";
                                            }

                                            leaf cert-profile-name {
                                                type types-sros:named-item;
                                                description "The IPsec tunnel certificate profile name used for this tunnel";
                                            }

                                            container statistics {
                                                description "Statistics related to the IKE SA.";

                                                leaf ctrl-packets-sent {
                                                    type yang:counter32;
                                                    description "The number of control packets this IPsec Tunnel has sent";
                                                }

                                                leaf ctrl-packets-received {
                                                    type yang:counter32;
                                                    description "The number of control packets this IPsec Tunnel has received";
                                                }

                                                leaf ctrl-packets-sent-errors {
                                                    type yang:counter32;
                                                    description "The number of control packet transmit errors";
                                                }

                                                leaf ctrl-packets-received-errors {
                                                    type yang:counter32;
                                                    description "The number of control packet receive errors";
                                                }

                                                leaf dpd-packets-sent {
                                                    type yang:counter32;
                                                    description "The number of Dead-Peer-Detection packets transmitted";
                                                }

                                                leaf dpd-packets-received {
                                                    type yang:counter32;
                                                    description "The number of Dead-Peer-Detection packets received";
                                                }

                                                leaf dpd-ack-packets-sent {
                                                    type yang:counter32;
                                                    description "The number of Dead-Peer-Detection acknowledgement packets transmitted";
                                                }

                                                leaf dpd-ack-packets-received {
                                                    type yang:counter32;
                                                    description "The number of Dead-Peer-Detection acknowledgement packets received";
                                                }

                                                leaf dpd-timeout-packets {
                                                    type yang:counter32;
                                                    description "The number of DPD R-U-THERE packets that have not been acknowledged";
                                                }

                                                leaf dpd-ack-packets-received-errors {
                                                    type yang:counter32;
                                                    description "The number of malformed DPD R-U-THERE acknowledgement packets received";
                                                }

                                            } // container statistics

                                        } // container ike-sa

                                    } // container dynamic

                                }
                            }
                        } // container key-exchange

                        list ipsec-sa {
                            key "security-association direction index";
                            description "IPsec dynamic tunnel.";

                            leaf security-association {
                                type uint32 {
                                    range "1..16";
                                }
                                description "The unique identifier of an security association (SA).";
                            }

                            leaf direction {
                                type enumeration {
                                    enum "inbound"                      { value 1; }
                                    enum "outbound"                     { value 2; }
                                }
                                description "The direction on the IPsec tunnel to which this SA can be applied.";
                            }

                            leaf index {
                                type uint32 {
                                    range "1..2";
                                }
                                description "The unique identifier of an security association (SA).";
                            }

                            leaf spi {
                                type uint32;
                                description
                                    "The SPI (Security Parameter Index) used to lookup the instruction to verify and decrypt
                                     the incoming IPsec packets when the value of direction is 'inbound'.";
                            }

                            leaf authentication-algorithm {
                                type types-ipsec:auth-algorithms;
                                description "The authentication algorithm used with this SA.";
                            }

                            leaf encryption-algorithm {
                                type types-ipsec:encryption-algorithms;
                                description "The encryption algorithm used with this SA.";
                            }

                            leaf established-time {
                                type yang:date-and-time;
                                description "The time when the IPsec SA negotiation completed.";
                            }

                            leaf negotiated-lifetime {
                                type types-sros:time-duration;
                                description "The lifetime negotiated for the IPsec SA.";
                            }

                            leaf security-association-type {
                                type types-ipsec:keying-type;
                                description
                                    "Whether this SA entry is created manually by the user or
                                     dynamically by the IPsec subsystem.";
                            }

                            container isa {
                                description "IPsec dynamic tunnel isa.";

                                leaf multicast-interface-name {
                                    type types-sros:named-item;
                                    description "The multicast interface name associated with this SA";
                                }

                                leaf multicast-protocol {
                                    type types-ipsec:multicast-protocol;
                                    description "The supported protocol types of the multicast interface associated to this SA";
                                }

                                leaf pfs-dh-group {
                                    type types-ipsec:dh-group;
                                    description "The Diffie-Hellman (DH) group used with this SA";
                                }

                                container fragmentation {

                                    leaf encapsulation-overhead {
                                        type uint32;
                                        description "The encapsulation overhead for this outbound SA.";
                                    }

                                    container pre-encapsulation {

                                        leaf last-packet-size {
                                            type uint32;
                                            units "bytes";
                                            description
                                                "The size of the last packet which caused a pre-encapsulation fragmentation
                                                 to occur for this SA.";
                                        }

                                    } // container pre-encapsulation

                                    container post-encapsulation {

                                        leaf last-packet-size {
                                            type uint32;
                                            units "bytes";
                                            description
                                                "The size of the last encapsulated packet which caused a post-encapsulation
                                                 fragmentation to occur for this SA.";
                                        }

                                    } // container post-encapsulation

                                } // container fragmentation

                                container statistics {

                                    leaf bytes-processed {
                                        type yang:counter64;
                                        description "The number of bytes successfully processed for this SA";
                                    }

                                    leaf packets-processed {
                                        type yang:counter64;
                                        description "The the number of packets successfully processed for this SA";
                                    }

                                    container errors {

                                        leaf crypto {
                                            type yang:counter32;
                                            description
                                                "The number of crypto errors encountered on this SA.
                                                     
                                                 When the value of direction is 'inbound', the crypto-errors will be set for the following errors:
                                                     MAC miscompare
                                                     Pad errors
                                                     Illegal configure algorithm
                                                     Illegal authentication algorithm
                                                     Inner IP checksum errors
                                                     Payload alignment errors
                                                     Sequence number errors
                                                     Protocol errors
                                                      
                                                 When the value of direction is 'outbound', the crypto-errors will be set for the following errors:
                                                     Sequence wrap errors
                                                     Illegal configure algorithm
                                                     Illegal authentication algorithm
                                                     Expanded packet too big
                                                     TTL decrement errors.";
                                        }

                                        leaf replay {
                                            type yang:counter32;
                                            description "The number of replay errors encountered on this SA";
                                        }

                                        leaf security-association {
                                            type yang:counter32;
                                            description
                                                "The number of SA errors encountered on this SA.
                                                 The SA errors means ISA tried to use a CHILD SA that is marked for deletion.";
                                        }

                                        leaf policy {
                                            type yang:counter32;
                                            description
                                                "The number of policy errors encountered on this SA.
                                                 The policy errors include bundled SA, selector check and policy direction error.";
                                        }

                                    } // container errors

                                    container fragmentation {

                                        container pre-encapsulation {

                                            leaf count {
                                                type yang:counter64;
                                                description
                                                    "The number of fragmentations that occurred prior to encapsulation for this outbound SA.
                                                     Pre-encapsulation fragmentation occurs for IPv4 packets whose size exceeds tmnxIPsecTunnelIpMtu.";
                                            }

                                        } // container pre-encapsulation

                                        container post-encapsulation {

                                            leaf count {
                                                type yang:counter64;
                                                description
                                                    "The number of fragmentations that occurred after encapsulation for this SA.
                                                     Post-encapsulation fragmentation occurs when the encapsulated packet size exceeds tmnxIPsecTunnelEncapIpMtu.";
                                            }

                                        } // container post-encapsulation

                                    } // container fragmentation

                                } // container statistics

                            } // container isa

                        } // list ipsec-sa

                        list dest-ip {
                            key "address";
                            description "Add a list entry for dest-ip";

                            leaf address {
                                type types-sros:ip-address;
                                description "Private IP address of the remote IP tunnel endpoint";
                            }

                            leaf resolved-status {
                                type boolean;
                                description "Whether this IPsec tunnel destination address has been resolved as reachable by the virtual router";
                            }

                        } // list dest-ip

                        container statistics {
                            description "IPsec static tunnel statistics.";

                            container traffic-forward {

                                container current {

                                    leaf start-time {
                                        type yang:date-and-time;
                                        description "The time when the sampling interval started.";
                                    }

                                    leaf sampling-duration {
                                        type types-sros:time-duration;
                                        description "The duration of the corresponding sampling interval.";
                                    }

                                    container packets {
                                        description "Statistics on encrypted and decrypted IPsec traffic packets.";

                                        leaf encrypted {
                                            type yang:counter64;
                                            units "packets";
                                            description "Number of encrypted IPsec packets.";
                                        }

                                        leaf decrypted {
                                            type yang:counter64;
                                            units "packets";
                                            description "Number of decrypted IPsec packets.";
                                        }

                                        leaf total {
                                            type yang:counter64;
                                            units "packets";
                                            description "Number of encrypted and decrypted IPsec packets.";
                                        }

                                    } // container packets

                                    container bytes {
                                        description "Statistics on encrypted and decrypted IPsec traffic packets.";

                                        leaf encrypted {
                                            type yang:counter64;
                                            units "kilobytes";
                                            description "Number of kilobytes in the encrypted IPsec packets.";
                                        }

                                        leaf decrypted {
                                            type yang:counter64;
                                            units "kilobytes";
                                            description "Number of kilobytes in the decrypted IPsec packets.";
                                        }

                                        leaf total {
                                            type yang:counter64;
                                            units "kilobytes";
                                            description "Number of kilobytes in the encrypted and decrypted IPsec packets.";
                                        }

                                    } // container bytes

                                } // container current

                            } // container traffic-forward

                        } // container statistics

                    } // list ipsec-tunnel

                } // list sap

                list vpls {
                    key "vpls-name";
                    description "Enter the vpls list instance";

                    leaf vpls-name {
                        type types-sros:named-item-64;
                        description "VPLS service";
                    }

                    leaf status {
                        type types-sros:oper-state;
                        description "The value of this object indicates the operational status of the VPLS service on this interface";
                    }

                    leaf failed-reason {
                        type types-sros:display-string-or-empty;
                        description "The reason when the Vpls is operationally down";
                    }

                } // list vpls

                container ipv6 {
                    description "Enter the ipv6 context";

                    leaf oper-state {
                        type types-sros:oper-state;
                        description "The current IPv6 operational status of this router interface.";
                    }

                    leaf down-reason {
                        type bits {
                            bit admin-disabled                 { position 0; }
                            bit service-admin-disabled         { position 1; }
                            bit port-down                      { position 2; }
                            bit address-or-parent-not-ready    { position 3; }
                            bit associated-object-not-ready    { position 4; }
                            bit rvpls-down                     { position 5; }
                            bit operational-group-down         { position 6; }
                            bit admin-destroy                  { position 7; }
                            bit no-address                     { position 8; }
                            bit no-info                        { position 9; }
                            bit hold-down-timer-running        { position 10; }
                            bit protocol-down                  { position 11; }
                            bit invalid-port-configuration     { position 12; }
                            bit unknown                        { position 13; }
                            bit no-route-distinguisher         { position 14; }
                            bit wlan-gateway-redundancy-standby { position 15; }
                            bit wlan-gateway-group-degraded    { position 16; }
                            bit ip-control-tunnel-down         { position 17; }
                            bit pdn-address-mismatch           { position 18; }
                        }
                        description
                            "Indicates the reason for why the interface is operationally down.
                                             
                             Values:
                                 admin-disabled                  - Administratively disabled.
                                 service-admin-disabled          - Assiocated service is administratively disabled.
                                 port-down                       - Associated SAP/port is operationally down.
                                 address-or-parent-not-ready     - Associated address or parent interface is not ready.
                                 associated-object-not-ready     - Associated object is not ready.
                                 rvpls-down                      - Associated R-VPLS service is operationally down.
                                 operational-group-down          - Associated operational group is operationally down.
                                 admin-destroy                   - The interface is being destroyed.
                                 no-address                      - There is no address configured.
                                 no-info                         - The interface info is not present.
                                 hold-down-timer-running         - The hold down timer is running.
                                 protocol-down                   - The protocols are operationally down.
                                 invalid-port-configuration      - Invalid port configuration.
                                 unknown                         - The interface is operationally down due to some unknown reason.
                                 no-route-distinguisher          - No route-distinguisher configured in the VRF.
                                 wlan-gateway-redundancy-standby - The interface is in standby state for WLAN-GW redundancy.
                                 wlan-gateway-group-degraded     - The interface associated WLAN-GW group is in a degraded state.
                                 ip-control-tunnel-down          - The IP tunnel associated to a control-tunnel interface is operationally down.
                                 pdn-address-mismatch            - The IP address learned from the packet data network does not match the configured primary IP address.";
                    }

                    container icmp6 {
                        description "Enter the icmp6 context";

                        container statistics {
                            description "Interface ICMPv6 statistics.";

                            leaf icmp6-in-msgs {
                                type yang:counter32;
                                description
                                    "Total number of ICMPv6 messages received by this interface.
                                                     
                                     This includes all those counted by icmp6-in-errors. Note that this
                                     interface is the interface to which the ICMPv6 messages were
                                     addressed which may not be necessarily the input interface
                                     for the messages.";
                            }

                            leaf icmp6-in-errors {
                                type yang:counter32;
                                description
                                    "Number of ICMPv6 errored messages received by this interface.
                                                     
                                     This implies ICMPv6 messages determined as having specific
                                     ICMPv6 errors (bad ICMP checksums, bad length, etc.).";
                            }

                            leaf icmp6-in-dest-unreachables {
                                type yang:counter32;
                                description "Nmber of ICMPv6 destination unreachable messages received by this interface.";
                            }

                            leaf icmp6-in-admin-prohibs {
                                type yang:counter32;
                                description
                                    "Number of ICMPv6 destination unreachable/communication administratively
                                     prohibited messages received by this interface.";
                            }

                            leaf icmp6-in-time-exceeds {
                                type yang:counter32;
                                description "Number of ICMPv6 time exceeded messages received by this interface.";
                            }

                            leaf icmp6-in-parm-problems {
                                type yang:counter32;
                                description "Number of ICMPv6 parameter problem messages received by this interface.";
                            }

                            leaf icmp6-in-pkt-too-bigs {
                                type yang:counter32;
                                description "Number of ICMPv6 packet too big messages received by this interface.";
                            }

                            leaf icmp6-in-echos {
                                type yang:counter32;
                                description "Number of ICMPv6 echo (request) messages received by this interface.";
                            }

                            leaf icmp6-in-echo-replies {
                                type yang:counter32;
                                description "Number of ICMPv6 echo reply messages received by this interface.";
                            }

                            leaf icmp6-in-rtr-solicits {
                                type yang:counter32;
                                description "Number of ICMPv6 router solicitation messages received by this interface.";
                            }

                            leaf icmp6-in-rtr-advertisements {
                                type yang:counter32;
                                description "Number of ICMPv6 router advertisement messages received by this interface.";
                            }

                            leaf icmp6-in-nbr-solicits {
                                type yang:counter32;
                                description "Number of ICMPv6 neighbor solicitation messages received by this interface.";
                            }

                            leaf icmp6-in-nbr-advertisements {
                                type yang:counter32;
                                description "Number of ICMPv6 neighbor advertisement messages received by this interface.";
                            }

                            leaf icmp6-in-redirects {
                                type yang:counter32;
                                description "Number of ICMPv6 redirect messages received by this interface.";
                            }

                            leaf icmp6-in-grp-memb-queries {
                                type yang:counter32;
                                description "Number of ICMPv6 group membership query messages received by this interface.";
                            }

                            leaf icmp6-in-grp-memb-repsonses {
                                type yang:counter32;
                                description "Number of ICMPv6 group membership response messages received by this interface.";
                            }

                            leaf icmp6-in-grp-memb-reductions {
                                type yang:counter32;
                                description "Number of ICMPv6 group membership reduction messages received by this interface.";
                            }

                            leaf icmp6-out-msgs {
                                type yang:counter32;
                                description
                                    "Total number of ICMPv6 messages this interface attempted to send.
                                                     
                                     This includes all those counted by icmp6-out-errors.";
                            }

                            leaf icmp6-out-errors {
                                type yang:counter32;
                                description
                                    "Number of ICMPv6 messages this interface could not be send due to problems
                                     discovered within ICMPv6 such as lack of buffers.
                                                     
                                     This value should not include errors discovered outside the ICMPv6 layer such as
                                     the inability of VRtr IPv6 to route the resultant datagram. In some implementations
                                     there may be no types of error which contribute to this counter's value.";
                            }

                            leaf icmp6-out-dest-unreachables {
                                type yang:counter32;
                                description "Number of ICMPv6 destination unreachable messages sent by this interface.";
                            }

                            leaf icmp6-out-admin-prohibs {
                                type yang:counter32;
                                description
                                    "Number of ICMPv6 destination unreachable/communication administratively prohibited
                                     messages sent by this interface.";
                            }

                            leaf icmp6-out-time-exceeds {
                                type yang:counter32;
                                description "Number of ICMPv6 time exceeded messages sent by this interface.";
                            }

                            leaf icmp6-out-parm-problems {
                                type yang:counter32;
                                description "Number of ICMPv6 parameter problem messages sent by this interface.";
                            }

                            leaf icmp6-out-pkt-too-bigs {
                                type yang:counter32;
                                description "Number of ICMPv6 packet too big messages sent by this interface.";
                            }

                            leaf icmp6-out-echos {
                                type yang:counter32;
                                description "Number of ICMPv6 echo request messages sent by this interface.";
                            }

                            leaf icmp6-out-echo-replies {
                                type yang:counter32;
                                description "Number of ICMPv6 echo reply messages sent by this interface.";
                            }

                            leaf icmp6-out-rtr-solicits {
                                type yang:counter32;
                                description "Number of ICMPv6 router solicitation messages sent by this interface.";
                            }

                            leaf icmp6-out-rtr-advertisements {
                                type yang:counter32;
                                description "Number of ICMPv6 router advertisement messages sent by this interface.";
                            }

                            leaf icmp6-out-nbr-solicits {
                                type yang:counter32;
                                description "Number of ICMPv6 neighbor solicitation messages sent by this interface.";
                            }

                            leaf icmp6-out-nbr-advertisements {
                                type yang:counter32;
                                description "Number of ICMPv6 neighbor advertisement messages sent by this interface.";
                            }

                            leaf icmp6-out-redirects {
                                type yang:counter32;
                                description "Number of ICMPv6 redirect messages sent by this interface.";
                            }

                            leaf icmp6-out-grp-memb-queries {
                                type yang:counter32;
                                description "Number of ICMPv6 group membership query messages sent by this interface.";
                            }

                            leaf icmp6-out-grp-memb-responses {
                                type yang:counter32;
                                description "Number of ICMPv6 group membership response messages sent by this interface.";
                            }

                            leaf icmp6-out-grp-memb-reductions {
                                type yang:counter32;
                                description "Number of ICMPv6 group membership reduction messages sent by this interface.";
                            }

                            leaf icmp6-out-discards {
                                type yang:counter32;
                                description "Number of discarded ICMPv6 messages on this interface.";
                            }

                        } // container statistics

                    } // container icmp6

                    container link-local-address {
                        description "Enter the link-local-address context";

                        leaf oper-address {
                            type types-sros:ipv6-address;
                            description "Indicates the link-local IPv6 address of this router interface.";
                        }

                        leaf address-state {
                            type types-sros:address-state;
                            description "Indicates the address state of the IPv6 address of the interface.";
                        }

                    } // container link-local-address

                    list address {
                        key "ipv6-address";
                        description "Enter the address list instance";

                        leaf ipv6-address {
                            type types-sros:ipv6-address;
                            description "IPv6 address assigned to the interface";
                        }

                        leaf address-state {
                            type types-sros:address-state;
                            description "Indicates the address state of the IPv6 address of the interface.";
                        }

                        leaf oper-address {
                            type types-sros:ip-address;
                            description "Indicates the operational address of this entry.";
                        }

                        leaf creation-origin {
                            type types-sros:creation-origin;
                            description "Indicates the mechanism used to create this entry.";
                        }

                        leaf primary-preferred {
                            type boolean;
                            description "Indicates whether this IP address is selected as the preferred primary address.";
                        }

                    } // list address

                    container dhcp6 {
                        description "Enter the dhcp6 context";

                        container relay {
                            description "Enter the relay context";

                            leaf oper-state {
                                type enumeration {
                                    enum "up"                           { value 1; }
                                    enum "down"                         { value 2; }
                                    enum "no-ipv6-prefix"               { value 3; }
                                    enum "no-server-configured"         { value 4; }
                                    enum "no-valid-source-address"      { value 5; }
                                }
                                description "The current operational state of the DHCP6 relay agent on this interface.";
                            }

                            leaf lease-populate {
                                type uint32;
                                description
                                    "The number of lease states currently allocated on this interface
                                     by the DHCP6 relay function.";
                            }

                            leaf server-lease-states {
                                type uint32;
                                description
                                    "The number of lease states currently allocated on this interface
                                     by the DHCP6 server function.";
                            }

                            container statistics {
                                description "DHCP relay interface statistics";

                                container dhcp-server-rx-packets {
                                    description "Rx packet statistics";

                                    leaf received {
                                        type yang:counter32;
                                        description "The total number of packets received by the DHCP relay agent.";
                                    }

                                    leaf malformed {
                                        type yang:counter32;
                                        description "The total number of malformed packets received by the DHCP relay agent.";
                                    }

                                    leaf untrusted {
                                        type yang:counter32;
                                        description "The total number of untrusted packets received by the DHCP relay agent.";
                                    }

                                } // container dhcp-server-rx-packets

                                container dhcp-server-tx-packets {
                                    description "Tx packet statistics";

                                    leaf transmitted {
                                        type yang:counter32;
                                        description "The total number of packets transmitted by the DHCP relay agent.";
                                    }

                                } // container dhcp-server-tx-packets

                                container client-dhcp-packets {
                                    description "Client packet statistics";

                                    leaf discarded {
                                        type yang:counter32;
                                        description "The total number of client packets discarded by the DHCP relay agent.";
                                    }

                                    leaf relayed {
                                        type yang:counter32;
                                        description "The total number of client packets relayed by the DHCP relay agent.";
                                    }

                                    leaf snooped {
                                        type yang:counter32;
                                        description "The total number of client packets snooped by the DHCP relay agent.";
                                    }

                                    leaf stream {
                                        type yang:counter32;
                                        description
                                            "The total number of received client packets scheduled for streaming
                                             to an external server, by the DHCP proxy function.";
                                    }

                                    container proxied {
                                        description "Proxied packet statistics";

                                        leaf radius {
                                            type yang:counter32;
                                            description
                                                "The total number of client packets proxied by the DHCP relay agent based
                                                 on data received from a RADIUS server.";
                                        }

                                        leaf lease-split {
                                            type yang:counter32;
                                            description
                                                "The total number of DHCP lease-split. Lease-split allows the DHCP relay agent to assigning a shorter lease time
                                                 than the actual lease time assigned by the DHCP server. This allows the system to remove disconnected client quickly
                                                 but ensure that client's shorter DHCP renewal are process by the relay agent and not the DHCP server.";
                                        }

                                        leaf nasreq {
                                            type yang:counter32;
                                            description
                                                "The total number of client packets proxied by the DHCP relay agent
                                                 based on data received from a Diameter NASREQ server.";
                                        }

                                        leaf user-db {
                                            type yang:counter32;
                                            description
                                                "The total number of client packets proxied by the DHCP relay agent based
                                                 on the local user database.";
                                        }

                                    } // container proxied

                                } // container client-dhcp-packets

                                container dhcp-server-packets {
                                    description "Server packet statistics";

                                    leaf discarded {
                                        type yang:counter32;
                                        description "The total number of server packets discarded by the DHCP relay agent.";
                                    }

                                    leaf relayed {
                                        type yang:counter32;
                                        description "The total number of server packets relayed by the DHCP relay agent.";
                                    }

                                    leaf snooped {
                                        type yang:counter32;
                                        description "The total number of server packets snooped by the DHCP relay agent.";
                                    }

                                } // container dhcp-server-packets

                                container auth-packets {
                                    description "Authenticate packet statistics";

                                    leaf discarded {
                                        type yang:counter32;
                                        description "The total number of packets discarded because authentication was not successful.";
                                    }

                                    leaf success {
                                        type yang:counter32;
                                        description "The total number of packets for which authentication was successful.";
                                    }

                                } // container auth-packets

                                container spoofed {
                                    description "Spoofed packet statistics";

                                    leaf release {
                                        type yang:counter32;
                                        description "The total number of DHCP RELEASE messages spoofed by the DHCP relay agent to the DHCP server.";
                                    }

                                    leaf force-renews {
                                        type yang:counter32;
                                        description
                                            "The total number of DHCP FORCERENEW messages spoofed by the DHCP relay agent
                                             to the DHCP clients.";
                                    }

                                } // container spoofed

                            } // container statistics

                        } // container relay

                        container server {
                            description "Enter the server context";

                            leaf current-server-lease-states {
                                type uint32 {
                                    range "0..8000";
                                }
                                description
                                    "Indicates the number of lease states currently allocated on this interface
                                     by the DHCP6 server function.";
                            }

                        } // container server

                    } // container dhcp6

                    container neighbor-discovery {
                        description "Enter the neighbor-discovery context";

                        list neighbor {
                            key "ipv6-address";
                            description "IPv6-to-MAC address mapping state parameters on the interface.";

                            leaf ipv6-address {
                                type types-sros:ipv6-address;
                                description "IPv6 address corresponding to the media-dependent physical address";
                            }

                            leaf state {
                                type enumeration {
                                    enum "incomplete"                   { value 0; }
                                    enum "reachable"                    { value 1; }
                                    enum "stale"                        { value 2; }
                                    enum "delay"                        { value 3; }
                                    enum "probe"                        { value 4; }
                                }
                                description
                                    "The Neighbor Unreachability Detection state for the interface
                                     when the address mapping is used.";
                            }

                            leaf is-router {
                                type boolean;
                                description "Indicates whether this entry is a router.";
                            }

                            leaf secure-nd {
                                type enumeration {
                                    enum "not-applicable"               { value 0; }
                                    enum "secure"                       { value 1; }
                                    enum "unsecure"                     { value 2; }
                                }
                                description
                                    "Indicates whether the physical address is received
                                     via Secured Neighbor Discovery messages.";
                            }

                            leaf mtu {
                                type uint32;
                                description "The MTU of the link attached to this entry.";
                            }

                            leaf mac-address {
                                type yang:mac-address;
                                description "The media-dependent physical address.";
                            }

                            leaf type {
                                type enumeration {
                                    enum "other"                        { value 0; }
                                    enum "static"                       { value 1; }
                                    enum "dynamic"                      { value 2; }
                                    enum "managed"                      { value 100; }
                                    enum "evpn"                         { value 101; }
                                }
                                description "The type of mapping.";
                            }

                            leaf timer {
                                type uint32 {
                                    range "0..65535";
                                }
                                units "seconds";
                                description
                                    "Indicates how much longer an ARP entry remains in the ARP cache.

                                     When timer has a value of zero, the entry is cleared from the cache.";
                            }

                        } // list neighbor

                    } // container neighbor-discovery

                    list vrrp {
                        key "virtual-router-id";
                        description "Enter the vrrp list instance";

                        leaf virtual-router-id {
                            type int32 {
                                range "1..255";
                            }
                            description "Virtual Router Identifier (VRID) for the VRRP virtual router instance";
                        }

                        leaf oper-state {
                            type types-sros:oper-state;
                            description "Operational state.";
                        }

                        leaf router-state {
                            type enumeration {
                                enum "initialize"                   { value 1; }
                                enum "backup"                       { value 2; }
                                enum "master"                       { value 3; }
                            }
                            description
                                "The current state of the virtual router. This object has
                                 three defined values:
                                  - `initialize', which indicates that all the
                                     virtual router is waiting for a startup event.

                                  - `backup', which indicates the virtual router is
                                     monitoring the availability of the master router.

                                  - `master', which indicates that the virtual router
                                     is forwarding packets for IP addresses that are
                                     associated with this router.

                                 Setting the `admin-state' object initiates
                                 transitions in the value of this object.";
                        }

                        leaf virtual-mac {
                            type yang:mac-address;
                            description
                                "The virtual MAC address of the virtual router. Although this
                                 object can be derived from the 'virtual-router-id' object, it is
                                 defined so that it is easily obtainable by a management
                                 application and can be included in VRRP-related SNMP traps.";
                        }

                        leaf master-ip-address {
                            type types-sros:ip-address;
                            description
                                "The master router's real (primary) IP address. This is
                                 the IP address listed as the source in VRRP advertisement
                                 last received by this virtual router.";
                        }

                        leaf primary-ip-address {
                            type types-sros:ip-address;
                            description
                                "In the case where there is more than one IP address for
                                 a given `interface', this object is used to specify the IP
                                 address that will become the `master-ip-addr', should
                                 the virtual router transition from backup to master. If
                                 this object is set to 0.0.0.0, the IP address which is
                                 numerically lowest will be selected.";
                        }

                        leaf up-time {
                            type yang:date-and-time;
                            description
                                "This is the value of the `system up time' object when this
                                 virtual router (i.e., the `oper-state') transitioned
                                 out of `initialized'.";
                        }

                        leaf in-use-priority {
                            type uint32 {
                                range "0..255";
                            }
                            description
                                "Indicates the current in-use priority
                                 associated with the VRRP VRRP.";
                        }

                        leaf master-since {
                            type yang:date-and-time;
                            description
                                "In case of a virtual router which
                                 is the current master, is the sysUpTime when operational state
                                 (oper-state) of the virtual router changed to master(3).
                                 In case of a backup virtual router, this value specifies the
                                 sysUpTime when it received the first VRRP advertisement message
                                 from the virtual router which is the current master.";
                        }

                        leaf master-priority {
                            type uint32 {
                                range "0..255";
                            }
                            description
                                "The value indicates the priority of
                                 the VRRP which is the current master";
                        }

                        leaf master-down-interval {
                            type types-sros:time-duration;
                            units "milliseconds";
                            description
                                "The value indicates the time
                                 interval for the backup router to declare the master as down.
                                 It is calculated as
                                        (3 * Advertisement_Interval) + Skew_time
                                 where Skew_Time is calculated as
                                        (256 - Priority) / 256";
                        }

                        leaf master-down-timer {
                            type types-sros:time-duration;
                            units "milliseconds";
                            description
                                "The value indicates the current
                                 value of the Master Down Timer.

                                 When a backup router receives a VRRP advertisement from a master,
                                 it resets this timer to the value of the Master Down Interval
                                 and begins to count down. If the backup router does not receive
                                 an advertisement till this timer times out, it will assume that
                                 the master is down and will declare itself to be the master.";
                        }

                        leaf in-use-advertisement-interval {
                            type int64;
                            units "milliseconds";
                            description "Indicates the operational value for the advertisement interval.";
                        }

                        leaf init-timer {
                            type types-sros:time-duration;
                            units "milliseconds";
                            description
                                "The value indicates the current value of
                                 initialization delay timer for VRRP, in milliseconds.";
                        }

                        leaf down-reason {
                            type enumeration {
                                enum "unknown"                      { value 0; }
                                enum "not-active"                   { value 1; }
                                enum "admin-down"                   { value 2; }
                                enum "if-down"                      { value 3; }
                                enum "no-link-lcl-addr-cfg"         { value 4; }
                                enum "rtr-adv-no-proper-cfg"        { value 5; }
                                enum "invalid-mac"                  { value 6; }
                            }
                            description
                                "The value indicates the reason for the
                                 operational state to be 'down'.";
                        }

                        container bfd-liveness {
                            description "Enter the bfd-liveness context";

                            leaf src-ip {
                                type types-sros:ip-address;
                                description
                                    "The value indicates the source
                                     IP address on the interface running BFD.";
                            }

                            leaf session-state {
                                type enumeration {
                                    enum "unknown"                      { value 1; }
                                    enum "connected"                    { value 2; }
                                    enum "broken"                       { value 3; }
                                    enum "peer-detects-down"            { value 4; }
                                    enum "not-configured"               { value 5; }
                                    enum "no-resources"                 { value 6; }
                                }
                                description
                                    "The value indicates the operational
                                     state of the BFD session the VRRP is relying
                                     upon for its fast triggering mechanism.";
                            }

                        } // container bfd-liveness

                        list master {
                            key "primary-ip-address";
                            description
                                "List of the master primary addresses that have been seen by the
                                 VRRP virtual router instance.";

                            leaf primary-ip-address {
                                type types-sros:ipv6-address;
                                description
                                    "This Object is set as read-only in mib. We use it to pass values to the sia-check
                                     function where it should fail.";
                            }

                            leaf last-seen {
                                type yang:date-and-time;
                                description
                                    "The value indicates the sysUpTime
                                     when the master was last seen by this VRRP. In
                                     other words it is the timestamp of the last advertisement message
                                     that was received from that master.";
                            }

                            leaf auth-sequence {
                                type int32;
                                description
                                    "The value indicates the last
                                     sequence number seen in the IP Authentication header of the
                                     advertisement messages received from the master.
                                     A negative value implies that the master was not being
                                     authenticated via IP authentication header.";
                            }

                            leaf ip-list-match {
                                type boolean;
                                description
                                    "The value indicates whether or not
                                     the IP address list in the advertisement messages received from
                                     the master matched the configured virtual router IP address list.";
                            }

                            container statistics {
                                description "Statistics for the master.";

                                leaf messages-received {
                                    type yang:counter32;
                                    description
                                        "The value indicates the total
                                         number of VRRP advertisement messages that have been received
                                         from the master.";
                                }

                            } // container statistics

                        } // list master

                        container statistics {

                            leaf discontinuity-time {
                                type yang:date-and-time;
                                description
                                    "The value of sysUpTime on the most recent occasion at
                                     which any one or more of this entry's counters suffered
                                     a discontinuity.

                                     If no such discontinuities have occurred since the last
                                     re-initialization of the local management subsystem,
                                     then this object contains a zero value.";
                            }

                            leaf refresh-rate {
                                type uint32;
                                units "milliseconds";
                                description
                                    "The minimum reasonable polling interval for this entry.
                                     This object provides an indication of the minimum
                                     Amount of time required to update the counters in this
                                     entry.";
                            }

                            leaf become-master {
                                type yang:counter32;
                                description
                                    "The total number of times that this virtual router's state
                                     has transitioned to MASTER.";
                            }

                            leaf advertisements-received {
                                type yang:counter32;
                                description
                                    "The total number of VRRP advertisements received by this
                                     virtual router.";
                            }

                            leaf advertisements-sent {
                                type yang:counter32;
                                description
                                    "The total number of VRRP advertisements sent by this virtual
                                     router.";
                            }

                            leaf advertisement-interval-errors {
                                type yang:counter32;
                                description
                                    "The total number of VRRP advertisement packets received
                                     for which the advertisement interval is different than the
                                     one configured for the local virtual router.";
                            }

                            leaf ttl-error-packets-received {
                                type yang:counter32;
                                description
                                    "The total number of VRRP packets received by the virtual
                                     router with IP TTL (Time-To-Live) not equal to 255.";
                            }

                            leaf zero-priority-packets-received {
                                type yang:counter32;
                                description
                                    "The total number of VRRP packets received by the virtual
                                     router with a priority of '0'.";
                            }

                            leaf zero-priority-packets-sent {
                                type yang:counter32;
                                description
                                    "The total number of VRRP packets sent by the virtual router
                                     with a priority of '0'.";
                            }

                            leaf invalid-type-packets-received {
                                type yang:counter32;
                                description
                                    "The number of VRRP packets received by the virtual router
                                     with an invalid value in the 'type' field.";
                            }

                            leaf address-list-error-packets-received {
                                type yang:counter32;
                                description
                                    "The total number of packets received for which the address
                                     list does not match the locally configured list for the
                                     virtual router.";
                            }

                            leaf error-length-packets-received {
                                type yang:counter32;
                                description
                                    "The total number of packets received with a packet length
                                     less than the length of the VRRP header.";
                            }

                            leaf invalid-authentication-type-packets-received {
                                type yang:counter32;
                                description
                                    "The total number of packets received with an unknown
                                     authentication type.";
                            }

                            leaf preempt-events {
                                type yang:counter32;
                                description
                                    "The value indicates the total
                                     number of times the virtual router has preempted another
                                     non-owner master with lower priority.";
                            }

                            leaf preempted-events {
                                type yang:counter32;
                                description
                                    "The value indicates the total
                                     number of times the virtual router has been preempted by another
                                     non-owner master with higher priority.";
                            }

                            leaf master-changes {
                                type yang:counter32;
                                description
                                    "The value indicates the total
                                     number of times the virtual router has seen the master virtual
                                     router change.";
                            }

                            leaf advertise-interval-discards {
                                type yang:counter32;
                                description
                                    "The total number of VRRP advertisement packets discarded
                                     because the advertisement interval in the received packet
                                     was different than the one configured for the local virtual
                                     router.";
                            }

                            leaf total-discards {
                                type yang:counter32;
                                description
                                    "The total number of VRRP advertisement packets discarded
                                     for any reason. This includes the packets discarded due to
                                     advertise interval mismatch and address list mismatch.";
                            }

                        } // container statistics

                    } // list vrrp

                    container statistics {
                        description "Interface IPv6 statistics.";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                    } // container statistics

                } // container ipv6

                container statistics {
                    description "Statistics information about vprn interface";

                    container ip {
                        description "Interface IP statistics.";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                    } // container ip

                    list mac {
                        key "mac-address";
                        description "Mac-accounting statistics";

                        leaf mac-address {
                            type yang:mac-address;
                            description "Mac-address";
                        }

                        leaf out-packets {
                            type yang:counter64;
                            description "The number of packets sent to the mac address";
                        }

                        leaf out-octets {
                            type yang:counter64;
                            description "The number of bytes sent to the mac address";
                        }

                        leaf in-packets {
                            type yang:counter64;
                            description "The number of packets received from the mac address";
                        }

                        leaf in-octets {
                            type yang:counter64;
                            description "The number of bytes received from the mac address";
                        }

                    } // list mac

                } // container statistics

            } // list interface

            list network-interface {
                key "interface-name";
                description "Enter the network-interface list instance";

                leaf interface-name {
                    type types-sros:interface-name;
                    description "The administrative name assigned to this router interface. The interface name must be unique among entries with the same vRtrID value.";
                }

                leaf if-index {
                    type int32;
                    description "The interface index.";
                }

                leaf system-if-index {
                    type int32;
                    description "The interface system index.";
                }

                leaf protocol {
                    type bits {
                        bit ospfv2                         { position 0; }
                        bit rip                            { position 1; }
                        bit isis                           { position 2; }
                        bit bgp                            { position 3; }
                        bit mpls                           { position 4; }
                        bit rsvp                           { position 5; }
                        bit ldp                            { position 6; }
                        bit igmp                           { position 7; }
                        bit pim                            { position 8; }
                        bit ospfv3                         { position 9; }
                        bit mld                            { position 10; }
                        bit ripng                          { position 11; }
                    }
                    description
                        "Indicates which protocols are configured on the interface.;
                                         
                         Values:
                             ospfv2 - Indicates if OSPFv2 is configured.
                             rip    - Indicates if RIP is configured.
                             isis   - Indicates if ISIS is configured.
                             bgp    - Indicates if BGP is configured.
                             mpls   - Indicates if MPLS is configured.
                             rsvp   - Indicates if RSVP is configured.
                             ldp    - Indicates if LDP is configured.
                             igmp   - Indicates if IGMP is configured.
                             pim    - Indicates if PIM is configured.
                             ospfv3 - Indicates if OSPFv3 is configured.
                             mld    - Indicates if MLD is configured.
                             ripng  - Indicates if RIPng is configured.";
                }

                leaf oper-ip-mtu {
                    type uint32;
                    units "bytes";
                    description "Indicates the interface operational IP MTU.";
                }

                leaf creation-origin {
                    type types-sros:creation-origin;
                    description "Indicates the mechanism used to create this entry.";
                }

                leaf if-oper-status {
                    type enumeration {
                        enum "up"                           { value 1; }
                        enum "down"                         { value 2; }
                        enum "testing"                      { value 3; }
                        enum "unknown"                      { value 4; }
                        enum "dormant"                      { value 5; }
                        enum "not-present"                  { value 6; }
                        enum "lower-layer-down"             { value 7; }
                    }
                    description
                        "The current operational state of the interface.
                         This leaf has the same semantics as ifOperStatus. 
                         in RFC 2863: The Interfaces Group MIB";
                }

                leaf last-oper-change {
                    type yang:date-and-time;
                    description "The sysUpTime when the operational state of this interface last changed.";
                }

                leaf lag-active-port {
                    type types-sros:port;
                    description
                        "LAG active port associated with this interface when lag-per-link-hash is enabled
                         on the lag or when a lag-link-map-profile is configured on this interface.";
                }

                container hold-time {
                    description "Enter the hold-time context";

                    container ipv4 {
                        description "Enter the ipv4 context";

                        leaf hold-timer {
                            type uint32;
                            units "seconds";
                            description
                                "The hold-timer indicates the time left before
                                 the interface comes up or goes down, depending on the ongoing
                                 transition state of the interface.";
                        }

                    } // container ipv4

                } // container hold-time

                container ipv4 {
                    description "Enter the ipv4 context";

                    leaf oper-state {
                        type types-sros:oper-state;
                        description "The current IPv4 operational status of this router interface.";
                    }

                    leaf down-reason {
                        type bits {
                            bit admin-disabled                 { position 0; }
                            bit service-admin-disabled         { position 1; }
                            bit port-down                      { position 2; }
                            bit address-or-parent-not-ready    { position 3; }
                            bit associated-object-not-ready    { position 4; }
                            bit rvpls-down                     { position 5; }
                            bit operational-group-down         { position 6; }
                            bit admin-destroy                  { position 7; }
                            bit no-address                     { position 8; }
                            bit no-info                        { position 9; }
                            bit hold-down-timer-running        { position 10; }
                            bit protocol-down                  { position 11; }
                            bit invalid-port-configuration     { position 12; }
                            bit unknown                        { position 13; }
                            bit no-route-distinguisher         { position 14; }
                            bit wlan-gateway-redundancy-standby { position 15; }
                            bit wlan-gateway-group-degraded    { position 16; }
                            bit ip-control-tunnel-down         { position 17; }
                            bit pdn-address-mismatch           { position 18; }
                        }
                        description
                            "Indicates the reason for why the interface is operationally down.
                                             
                             Values:
                                 admin-disabled                  - Administratively disabled.
                                 service-admin-disabled          - Assiocated service is administratively disabled.
                                 port-down                       - Associated SAP/port is operationally down.
                                 address-or-parent-not-ready     - Associated address or parent interface is not ready.
                                 associated-object-not-ready     - Associated object is not ready.
                                 rvpls-down                      - Associated R-VPLS service is operationally down.
                                 operational-group-down          - Associated operational group is operationally down.
                                 admin-destroy                   - The interface is being destroyed.
                                 no-address                      - There is no address configured.
                                 no-info                         - The interface info is not present.
                                 hold-down-timer-running         - The hold down timer is running.
                                 protocol-down                   - The protocols are operationally down.
                                 invalid-port-configuration      - Invalid port configuration.
                                 unknown                         - The interface is operationally down due to some unknown reason.
                                 no-route-distinguisher          - No route-distinguisher configured in the VRF.
                                 wlan-gateway-redundancy-standby - The interface is in standby state for WLAN-GW redundancy.
                                 wlan-gateway-group-degraded     - The interface associated WLAN-GW group is in a degraded state.
                                 ip-control-tunnel-down          - The IP tunnel associated to a control-tunnel interface is operationally down.
                                 pdn-address-mismatch            - The IP address learned from the packet data network does not match the configured primary IP address.";
                    }

                    container icmp {
                        description "Enter the icmp context";

                        container statistics {
                            description "Interface ICMPv4 statistics.";

                            leaf icmp-in-msgs {
                                type yang:counter32;
                                description
                                    "Total Number of ICMPv4 messages received by this interface.
                                                     
                                     This includes all those counted by icmp-in-errors. Note that this
                                     interface is the interface to which the ICMPv4 messages were
                                     addressed which may not be necessarily the input interface
                                     for the messages.";
                            }

                            leaf icmp-in-errors {
                                type yang:counter32;
                                description
                                    "Number of ICMPv4 errored messages received by this interface.
                                                     
                                     This implies ICMPv4 messages determined as having specific
                                     ICMPv4 errors (bad ICMPv4 checksums, bad length, etc.).";
                            }

                            leaf icmp-in-dest-unreachables {
                                type yang:counter32;
                                description "Number of ICMPv4 destination unreachable messages received by this interface.";
                            }

                            leaf icmp-in-redirects {
                                type yang:counter32;
                                description "Number of ICMPv4 redirect messages received by this interface.";
                            }

                            leaf icmp-in-echos {
                                type yang:counter32;
                                description "Number of ICMPv4 echo (request) messages received by this interface.";
                            }

                            leaf icmp-in-echo-replies {
                                type yang:counter32;
                                description "Number of ICMPv4 echo reply messages received by this interface.";
                            }

                            leaf icmp-in-time-exceeds {
                                type yang:counter32;
                                description "Number of ICMPv4 time exceeded messages received by this interface.";
                            }

                            leaf icmp-in-src-quenches {
                                type yang:counter32;
                                description "Number of ICMPv4 source quench messages received by this interface.";
                            }

                            leaf icmp-in-timestamps {
                                type yang:counter32;
                                description "Number of ICMPv4 timestamp (request) messages received by this interface.";
                            }

                            leaf icmp-in-timestamp-replies {
                                type yang:counter32;
                                description "Number of ICMPv4 timestamp reply messages received by this interface.";
                            }

                            leaf icmp-in-address-masks {
                                type yang:counter32;
                                description "Number of ICMPv4 address mask request messages received by this interface.";
                            }

                            leaf icmp-in-address-mask-replies {
                                type yang:counter32;
                                description "Number of ICMPv4 address mask reply messages received by this interface.";
                            }

                            leaf icmp-in-parm-problems {
                                type yang:counter32;
                                description "Number of ICMPv4 parameter problem messages received by this interface.";
                            }

                            leaf icmp-out-msgs {
                                type yang:counter32;
                                description
                                    "Total number of ICMPv4 messages this interface attempted to send.
                                                     
                                     This includes all those counted by icmp-out-errors.";
                            }

                            leaf icmp-out-errors {
                                type yang:counter32;
                                description
                                    "Number of ICMPv4 messages this interface could not be send due to problems
                                     discovered within ICMPv4 such as lack of buffers.
                                                     
                                     This value should not include errors discovered outside the ICMPv4 layer such as
                                     the inability of VRtr IPv4 to route the resultant datagram. In some implementations
                                     there may be no types of error which contribute to this counter's value.";
                            }

                            leaf icmp-out-dest-unreachables {
                                type yang:counter32;
                                description "Number of ICMPv4 destination unreachable messages sent by this interface.";
                            }

                            leaf icmp-out-redirects {
                                type yang:counter32;
                                description "Number of ICMPv4 redirect messages sent by this interface.";
                            }

                            leaf icmp-out-echos {
                                type yang:counter32;
                                description "Number of ICMPv4 echo request messages sent by this interface.";
                            }

                            leaf icmp-out-echo-replies {
                                type yang:counter32;
                                description "Number of ICMPv4 echo reply messages sent by this interface.";
                            }

                            leaf icmp-out-time-exceeds {
                                type yang:counter32;
                                description "Number of ICMPv4 time exceeded messages sent by this interface.";
                            }

                            leaf icmp-out-src-quenches {
                                type yang:counter32;
                                description "Number of ICMPv4 source quench messages sent by this interface.";
                            }

                            leaf icmp-out-timestamps {
                                type yang:counter32;
                                description "Number of ICMPv4 timestamp (request) messages sent by this interface.";
                            }

                            leaf icmp-out-timestamp-replies {
                                type yang:counter32;
                                description "Number of ICMPv4 timestamp reply messages sent by this interface.";
                            }

                            leaf icmp-out-address-masks {
                                type yang:counter32;
                                description "Number of ICMPv4 address mask request messages sent by this interface.";
                            }

                            leaf icmp-out-address-mask-replies {
                                type yang:counter32;
                                description "Number of ICMPv4 address mask reply messages sent by this interface.";
                            }

                            leaf icmp-out-parm-problems {
                                type yang:counter32;
                                description "Number of ICMPv4 parameter problem messages sent by this interface.";
                            }

                            leaf icmp-out-discards {
                                type yang:counter32;
                                description "Number of discarded ICMPv4 messages on this interface.";
                            }

                        } // container statistics

                    } // container icmp

                    container primary {
                        description "Enter the primary context";

                        leaf oper-address {
                            type types-sros:ip-address;
                            description "Indicates the operational address of this entry.";
                        }

                        leaf creation-origin {
                            type types-sros:creation-origin;
                            description "Indicates the mechanism used to create this entry.";
                        }

                    } // container primary

                    list secondary {
                        key "address";
                        description "Enter the secondary list instance";

                        leaf address {
                            type types-sros:ipv4-unicast-address;
                            description "Secondary IPv4 address assigned to the interface";
                        }

                        leaf oper-address {
                            type types-sros:ip-address;
                            description "Indicates the operational address of this entry.";
                        }

                        leaf creation-origin {
                            type types-sros:creation-origin;
                            description "Indicates the mechanism used to create this entry.";
                        }

                    } // list secondary

                    container neighbor-discovery {
                        description "Enter the neighbor-discovery context";

                        list neighbor {
                            key "ipv4-address";
                            description "IP-to-MAC address mapping state parameters on the interface.";

                            leaf ipv4-address {
                                type types-sros:ipv4-address;
                                description "IPv4 address corresponding to the media-dependent physical address";
                            }

                            leaf oper-state {
                                type types-sros:oper-state;
                                description "Indicates if the ARP entry is being used actively in the ARP table.";
                            }

                            leaf mac-address {
                                type yang:mac-address;
                                description "The media-dependent physical address.";
                            }

                            leaf type {
                                type enumeration {
                                    enum "other"                        { value 0; }
                                    enum "static"                       { value 1; }
                                    enum "dynamic"                      { value 2; }
                                    enum "managed"                      { value 100; }
                                    enum "evpn"                         { value 101; }
                                }
                                description "The type of mapping.";
                            }

                            leaf timer {
                                type uint32 {
                                    range "0..65535";
                                }
                                units "seconds";
                                description
                                    "Indicates how much longer an ARP entry remains in the ARP cache.

                                     When timer has a value of zero, the entry is cleared from the cache.";
                            }

                        } // list neighbor

                    } // container neighbor-discovery

                    container statistics {
                        description "Interface IPv4 statistics.";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                        leaf out-discard-dbcast-packets {
                            type yang:counter64;
                            description "The number of directed-broadcast packets dropped.";
                        }

                        leaf out-discard-dbcast-octets {
                            type yang:counter64;
                            description "The number of directed-broadcast octets dropped.";
                        }

                    } // container statistics

                } // container ipv4

            } // list network-interface

            list redundant-interface {
                key "interface-name";
                description "Enter the redundant-interface list instance";

                leaf interface-name {
                    type types-sros:interface-name;
                    description "Name of the interface";
                }

                leaf if-index {
                    type int32;
                    description "The interface index.";
                }

                leaf system-if-index {
                    type int32;
                    description "The interface system index.";
                }

                leaf oper-ip-mtu {
                    type uint32;
                    units "bytes";
                    description "Indicates the interface operational IP MTU.";
                }

                leaf creation-origin {
                    type types-sros:creation-origin;
                    description "Indicates the mechanism used to create this entry.";
                }

                leaf if-oper-status {
                    type enumeration {
                        enum "up"                           { value 1; }
                        enum "down"                         { value 2; }
                        enum "testing"                      { value 3; }
                        enum "unknown"                      { value 4; }
                        enum "dormant"                      { value 5; }
                        enum "not-present"                  { value 6; }
                        enum "lower-layer-down"             { value 7; }
                    }
                    description
                        "The current operational state of the interface.
                         This leaf has the same semantics as ifOperStatus. 
                         in RFC 2863: The Interfaces Group MIB";
                }

                leaf last-oper-change {
                    type yang:date-and-time;
                    description "The sysUpTime when the operational state of this interface last changed.";
                }

                container hold-time {
                    description "Enter the hold-time context";

                    container ipv4 {
                        description "Enter the ipv4 context";

                        leaf hold-timer {
                            type uint32;
                            units "seconds";
                            description
                                "The hold-timer indicates the time left before
                                 the interface comes up or goes down, depending on the ongoing
                                 transition state of the interface.";
                        }

                    } // container ipv4

                } // container hold-time

                list spoke-sdp {
                    key "sdp-bind-id";
                    description "Enter the spoke-sdp list instance";

                    leaf sdp-bind-id {
                        type types-services:sdp-bind-id;
                        description "SDP Binding identifier as <sdp-id>:<vc-id>. sdp-id - [1..32767] vc-id - [1..4294967295].";
                    }

                    leaf oper-state {
                        type enumeration {
                            enum "up"                           { value 1; }
                            enum "down"                         { value 5; }
                        }
                        description "Indicates the operating status of this Service-SDP binding.";
                    }

                    leaf oper-flags {
                        type bits {
                            bit sdp-bind-admin-down            { position 0; }
                            bit svc-admin-down                 { position 1; }
                            bit stitching-svc-txdown           { position 2; }
                            bit sdp-oper-down                  { position 3; }
                            bit sdp-path-mtu-too-small         { position 4; }
                            bit no-ingress-vc-label            { position 5; }
                            bit no-egress-vc-label             { position 6; }
                            bit svc-mtu-mismatch               { position 7; }
                            bit vc-type-mismatch               { position 8; }
                            bit relearn-limit-exceeded         { position 9; }
                            bit ies-if-admin-down              { position 10; }
                            bit released-ingress-vc-label      { position 11; }
                            bit labels-exhausted               { position 12; }
                            bit svc-param-mismatch             { position 13; }
                            bit insufficient-bandwidth         { position 14; }
                            bit pw-peer-fault-status-bits      { position 15; }
                            bit mesh-sdp-down                  { position 16; }
                            bit not-managed-by-mcring          { position 17; }
                            bit out-of-resource                { position 18; }
                            bit mh-standby                     { position 19; }
                            bit oam-down-mep-fault             { position 20; }
                            bit oam-up-mep-fault               { position 21; }
                            bit standby-sig-slave-tx-down      { position 22; }
                            bit oper-grp-down                  { position 23; }
                            bit withdrawn-ingress-vc-label     { position 24; }
                            bit vpls-pmsi-down                 { position 25; }
                            bit rec-prot-src-mac               { position 26; }
                            bit peer-fault-status-tx-down      { position 27; }
                            bit evpn-route-conflict            { position 28; }
                            bit admin-locked                   { position 29; }
                            bit evpn-p2mp-conflict             { position 30; }
                            bit label-stack-limit-exceeded     { position 31; }
                        }
                        description
                            "This object indicates all the conditions that affect the
                             operating status of this SDP Bind.";
                    }

                    leaf pw-peer-status-bits {
                        type bits {
                            bit pw-not-forwarding              { position 0; }
                            bit lac-ingress-fault              { position 1; }
                            bit lac-egress-fault               { position 2; }
                            bit psn-ingress-fault              { position 3; }
                            bit psn-egress-fault               { position 4; }
                            bit pw-fwding-standby              { position 5; }
                        }
                        description
                            "Indicates bits set by the LDP peer when there is a fault on its
                             side of the pseudowire";
                    }

                    leaf pw-local-status-bits {
                        type bits {
                            bit pw-not-forwarding              { position 0; }
                            bit lac-ingress-fault              { position 1; }
                            bit lac-egress-fault               { position 2; }
                            bit psn-ingress-fault              { position 3; }
                            bit psn-egress-fault               { position 4; }
                            bit pw-fwding-standby              { position 5; }
                        }
                        description "Indicates locally set bits when there is a fault.";
                    }

                    leaf peer-vccv-cv-bits {
                        type bits {
                            bit icmp-ping                      { position 0; }
                            bit lsp-ping                       { position 1; }
                            bit bfd-fault-detection            { position 2; }
                            bit bfd-fault-detection-and-signalling { position 3; }
                        }
                        description "Indicates CV type bits set by the LDP peer if it supports VCCV.";
                    }

                    leaf peer-vccv-cc-bits {
                        type bits {
                            bit pwe3-control-word              { position 0; }
                            bit mpls-router-alert-label        { position 1; }
                            bit mpls-pw-demultiplex-or-label   { position 2; }
                        }
                        description "Indicates CC type bits set by the LDP peer if it supports VCCV.";
                    }

                    leaf oper-control-word {
                        type boolean;
                        description "Status of control word.";
                    }

                    leaf pw-fault-ip-address {
                        type types-sros:ip-address;
                        description "Faulty IP address sent by peer.";
                    }

                    leaf class-forwarding-oper-state {
                        type types-sros:oper-state;
                        description "Operational state of forwarding-class based forwarding on this SDP bind.";
                    }

                    leaf creation-origin {
                        type types-sros:creation-origin;
                        description "Creation origin of the service.";
                    }

                    leaf oper-hash-label {
                        type boolean;
                        description "Indicates the negotiated value of hash lavel that is used on this SDP binding.";
                    }

                    leaf min-required-sdp-oper-mtu {
                        type int32;
                        description "Minimum required SDP MTU size used with this SDP binding.";
                    }

                    container ingress {
                        description "Enter the ingress context";

                        leaf oper-label {
                            type uint32;
                            description "MPLS service label used by the far-end device to send packets to the local PEs sdp-bind.";
                        }

                        container statistics {
                            description "Ingress side statistics";

                            leaf forwarded-packets {
                                type yang:counter64;
                                description "Forwarded packets";
                            }

                            leaf forwarded-octets {
                                type yang:counter64;
                                description "Forwarded octets";
                            }

                            leaf dropped-packets {
                                type yang:counter64;
                                description "Dropped packets";
                            }

                            leaf dropped-octets {
                                type yang:counter64;
                                description "Dropped octets";
                            }

                        } // container statistics

                    } // container ingress

                    container egress {
                        description "Enter the egress context";

                        leaf oper-label {
                            type uint32;
                            description "MPLS service label used to send packets to the far-end device via this sdp-bind.";
                        }

                        container statistics {
                            description "Egress side statistics";

                            leaf forwarded-packets {
                                type yang:counter64;
                                description "Forwarded packets";
                            }

                            leaf forwarded-octets {
                                type yang:counter64;
                                description "Forwarded octets";
                            }

                        } // container statistics

                    } // container egress

                } // list spoke-sdp

                container ipv4 {
                    description "Enter the ipv4 context";

                    leaf oper-state {
                        type types-sros:oper-state;
                        description "The current IPv4 operational status of this router interface.";
                    }

                    leaf down-reason {
                        type bits {
                            bit admin-disabled                 { position 0; }
                            bit service-admin-disabled         { position 1; }
                            bit port-down                      { position 2; }
                            bit address-or-parent-not-ready    { position 3; }
                            bit associated-object-not-ready    { position 4; }
                            bit rvpls-down                     { position 5; }
                            bit operational-group-down         { position 6; }
                            bit admin-destroy                  { position 7; }
                            bit no-address                     { position 8; }
                            bit no-info                        { position 9; }
                            bit hold-down-timer-running        { position 10; }
                            bit protocol-down                  { position 11; }
                            bit invalid-port-configuration     { position 12; }
                            bit unknown                        { position 13; }
                            bit no-route-distinguisher         { position 14; }
                            bit wlan-gateway-redundancy-standby { position 15; }
                            bit wlan-gateway-group-degraded    { position 16; }
                            bit ip-control-tunnel-down         { position 17; }
                            bit pdn-address-mismatch           { position 18; }
                        }
                        description
                            "Indicates the reason for why the interface is operationally down.
                                             
                             Values:
                                 admin-disabled                  - Administratively disabled.
                                 service-admin-disabled          - Assiocated service is administratively disabled.
                                 port-down                       - Associated SAP/port is operationally down.
                                 address-or-parent-not-ready     - Associated address or parent interface is not ready.
                                 associated-object-not-ready     - Associated object is not ready.
                                 rvpls-down                      - Associated R-VPLS service is operationally down.
                                 operational-group-down          - Associated operational group is operationally down.
                                 admin-destroy                   - The interface is being destroyed.
                                 no-address                      - There is no address configured.
                                 no-info                         - The interface info is not present.
                                 hold-down-timer-running         - The hold down timer is running.
                                 protocol-down                   - The protocols are operationally down.
                                 invalid-port-configuration      - Invalid port configuration.
                                 unknown                         - The interface is operationally down due to some unknown reason.
                                 no-route-distinguisher          - No route-distinguisher configured in the VRF.
                                 wlan-gateway-redundancy-standby - The interface is in standby state for WLAN-GW redundancy.
                                 wlan-gateway-group-degraded     - The interface associated WLAN-GW group is in a degraded state.
                                 ip-control-tunnel-down          - The IP tunnel associated to a control-tunnel interface is operationally down.
                                 pdn-address-mismatch            - The IP address learned from the packet data network does not match the configured primary IP address.";
                    }

                    container statistics {
                        description "Interface IPv4 statistics.";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                        leaf out-discard-dbcast-packets {
                            type yang:counter64;
                            description "The number of directed-broadcast packets dropped.";
                        }

                        leaf out-discard-dbcast-octets {
                            type yang:counter64;
                            description "The number of directed-broadcast octets dropped.";
                        }

                    } // container statistics

                    container primary {
                        description "Enter the primary context";

                        leaf oper-address {
                            type types-sros:ip-address;
                            description "Indicates the operational address of this entry.";
                        }

                        leaf creation-origin {
                            type types-sros:creation-origin;
                            description "Indicates the mechanism used to create this entry.";
                        }

                    } // container primary

                } // container ipv4

                container ipv6 {
                    description "IPv6 related objects for an interface";

                    container statistics {
                        description "Interface IPv6 statistics.";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                    } // container statistics

                } // container ipv6

                container statistics {
                    description "Statistics information about vprn redundant-interface";

                    container ip {
                        description "Interface IP statistics.";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                    } // container ip

                    list mac {
                        key "mac-address";
                        description "Mac-accounting statistics";

                        leaf mac-address {
                            type yang:mac-address;
                            description "Mac-address";
                        }

                        leaf out-packets {
                            type yang:counter64;
                            description "The number of packets sent to the mac address";
                        }

                        leaf out-octets {
                            type yang:counter64;
                            description "The number of bytes sent to the mac address";
                        }

                        leaf in-packets {
                            type yang:counter64;
                            description "The number of packets received from the mac address";
                        }

                        leaf in-octets {
                            type yang:counter64;
                            description "The number of bytes received from the mac address";
                        }

                    } // list mac

                } // container statistics

            } // list redundant-interface

            list ip-mirror-interface {
                key "interface-name";
                description "Enter the ip-mirror-interface list instance";

                leaf interface-name {
                    type types-sros:interface-name;
                    description "Name of the interface";
                }

                leaf if-index {
                    type int32;
                    description "The interface index.";
                }

                leaf system-if-index {
                    type int32;
                    description "The interface system index.";
                }

                container ipv4 {
                    description "IPv4 related objects for an interface";

                    container statistics {
                        description "Interface IPv4 statistics.";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                        leaf out-discard-dbcast-packets {
                            type yang:counter64;
                            description "The number of directed-broadcast packets dropped.";
                        }

                        leaf out-discard-dbcast-octets {
                            type yang:counter64;
                            description "The number of directed-broadcast octets dropped.";
                        }

                    } // container statistics

                } // container ipv4

                container ipv6 {
                    description "IPv6 related objects for an interface";

                    container statistics {
                        description "Interface IPv6 statistics.";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                    } // container statistics

                } // container ipv6

                container statistics {
                    description "Statistics information about vprn ip-mirror-interface";

                    container ip {
                        description "Interface IP statistics.";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                    } // container ip

                    list mac {
                        key "mac-address";
                        description "Mac-accounting statistics";

                        leaf mac-address {
                            type yang:mac-address;
                            description "Mac-address";
                        }

                        leaf out-packets {
                            type yang:counter64;
                            description "The number of packets sent to the mac address";
                        }

                        leaf out-octets {
                            type yang:counter64;
                            description "The number of bytes sent to the mac address";
                        }

                        leaf in-packets {
                            type yang:counter64;
                            description "The number of packets received from the mac address";
                        }

                        leaf in-octets {
                            type yang:counter64;
                            description "The number of bytes received from the mac address";
                        }

                    } // list mac

                } // container statistics

            } // list ip-mirror-interface

            container ipv4 {
                description "Router instance IPv4 parameters.";

                container icmp {
                    description "Router instance ICMPv4 parameters.";

                    container statistics {
                        description "Router instance ICMPv4 statistics.";

                        leaf icmp-in-msgs {
                            type yang:counter32;
                            description
                                "Number of ICMPv4 messages received by this router instance.

                                 This includes all those counted by icmp-in-errors.";
                        }

                        leaf icmp-in-errors {
                            type yang:counter32;
                            description
                                "Number of ICMPv4 errored messages received by this router instance.
                                                 
                                 This implies ICMPv4 messages determined as having specific
                                 ICMPv4 errors (bad ICMPv4 checksums, bad length, etc.).";
                        }

                        leaf icmp-in-dest-unreachables {
                            type yang:counter32;
                            description "Number of ICMPv4 destination unreachable messages received by this router instance.";
                        }

                        leaf icmp-in-redirects {
                            type yang:counter32;
                            description "Number of ICMPv4 redirect messages received by this router instance.";
                        }

                        leaf icmp-in-echos {
                            type yang:counter32;
                            description "Number of ICMPv4 echo (request) messages received by this router instance.";
                        }

                        leaf icmp-in-echo-replies {
                            type yang:counter32;
                            description "Number of ICMPv4 echo reply messages received by this router instance.";
                        }

                        leaf icmp-in-time-exceeds {
                            type yang:counter32;
                            description "Number of ICMPv4 time exceeded messages received by this router instance.";
                        }

                        leaf icmp-in-src-quenches {
                            type yang:counter32;
                            description "Number of ICMPv4 source quench messages received by this router instance.";
                        }

                        leaf icmp-in-timestamps {
                            type yang:counter32;
                            description "Number of ICMPv4 timestamp (request) messages received by this router instance.";
                        }

                        leaf icmp-in-timestamp-replies {
                            type yang:counter32;
                            description "Number of ICMPv4 timestamp reply messages received by this router instance.";
                        }

                        leaf icmp-in-address-masks {
                            type yang:counter32;
                            description "Number of ICMPv4 address mask request messages received by this router instance.";
                        }

                        leaf icmp-in-address-mask-replies {
                            type yang:counter32;
                            description "Number of ICMPv4 address mask reply messages received by this router instance.";
                        }

                        leaf icmp-in-parm-problems {
                            type yang:counter32;
                            description "Number of ICMPv4 parameter problem messages received by this router instance.";
                        }

                        leaf icmp-out-msgs {
                            type yang:counter32;
                            description
                                "Total number of ICMPv4 messages this router instance attempted to send.
                                                 
                                 This includes all those counted by icmp-out-errors.";
                        }

                        leaf icmp-out-errors {
                            type yang:counter32;
                            description
                                "Number of ICMPv4 messages that could not be send due to problems discovered within ICMPv4
                                 such as lack of buffers.
                                                 
                                 This value should not include errors discovered outside the ICMPv4 layer such as
                                 the inability of VRtr IPv4 to route the resultant datagram. In some implementations
                                 there may be no types of error which contribute to this counter's value.";
                        }

                        leaf icmp-out-dest-unreachables {
                            type yang:counter32;
                            description "Number of ICMPv4 destination unreachable messages sent by this router instance.";
                        }

                        leaf icmp-out-redirects {
                            type yang:counter32;
                            description "Number of ICMPv4 redirect messages sent by this router instance.";
                        }

                        leaf icmp-out-echos {
                            type yang:counter32;
                            description "Number of ICMPv4 echo request messages sent by this router instance.";
                        }

                        leaf icmp-out-echo-replies {
                            type yang:counter32;
                            description "Number of ICMPv4 echo reply messages sent by this router instance.";
                        }

                        leaf icmp-out-time-exceeds {
                            type yang:counter32;
                            description "Number of ICMPv4 time exceeded messages sent by this router instance.";
                        }

                        leaf icmp-out-src-quenches {
                            type yang:counter32;
                            description "Number of ICMPv4 source quench messages sent by this router instance.";
                        }

                        leaf icmp-out-timestamps {
                            type yang:counter32;
                            description "Number of ICMPv4 timestamp (request) messages sent by this router instance.";
                        }

                        leaf icmp-out-timestamp-replies {
                            type yang:counter32;
                            description "Number of ICMPv4 timestamp reply messages sent by this router instance.";
                        }

                        leaf icmp-out-address-masks {
                            type yang:counter32;
                            description "Number of ICMPv4 address mask request messages sent by this router instance.";
                        }

                        leaf icmp-out-address-mask-replies {
                            type yang:counter32;
                            description "Number of ICMPv4 address mask reply messages sent by this router instance.";
                        }

                        leaf icmp-out-parm-problems {
                            type yang:counter32;
                            description "Number of ICMPv4 parameter problem messages sent by this router instance.";
                        }

                        leaf icmp-out-discards {
                            type yang:counter32;
                            description "Number of discarded ICMPv4 messages on this router instance.";
                        }

                    } // container statistics

                } // container icmp

            } // container ipv4

            container ipv6 {
                description "Enter the ipv6 context";

                container icmp6 {
                    description "Router instance ICMPv6 parameters.";

                    container statistics {
                        description "Router instance ICMPv6 statistics.";

                        leaf icmp6-in-msgs {
                            type yang:counter32;
                            description
                                "Total number of ICMPv6 messages received by this router instance.
                                                 
                                 This includes all those counted by icmp6-in-errors.";
                        }

                        leaf icmp6-in-errors {
                            type yang:counter32;
                            description
                                "Number of ICMPv6 errored messages received by this router instance.

                                 This implies ICMPv6 messages determined as having specific
                                 ICMPv6 errors (bad ICMP checksums, bad length, etc.).";
                        }

                        leaf icmp6-in-dest-unreachables {
                            type yang:counter32;
                            description "Number of ICMPv6 destination unreachable messages received by this router instance.";
                        }

                        leaf icmp6-in-admin-prohibs {
                            type yang:counter32;
                            description
                                "Number of ICMPv6 destination unreachable/communication administratively
                                 prohibited messages received by this router instance.";
                        }

                        leaf icmp6-in-time-exceeds {
                            type yang:counter32;
                            description "Number of ICMPv6 time exceeded messages received by this router instance.";
                        }

                        leaf icmp6-in-parm-problems {
                            type yang:counter32;
                            description "Number of ICMPv6 parameter problem messages received by this router instance.";
                        }

                        leaf icmp6-in-pkt-too-bigs {
                            type yang:counter32;
                            description "Number of ICMPv6 packet too big messages received by this router instance.";
                        }

                        leaf icmp6-in-echos {
                            type yang:counter32;
                            description "Number of ICMPv6 echo (request) messages received by this router instance.";
                        }

                        leaf icmp6-in-echo-replies {
                            type yang:counter32;
                            description "Number of ICMPv6 echo reply messages received by this router instance.";
                        }

                        leaf icmp6-in-rtr-solicits {
                            type yang:counter32;
                            description "Number of ICMPv6 router solicitation messages received by this router instance.";
                        }

                        leaf icmp6-in-rtr-advertisements {
                            type yang:counter32;
                            description "Number of ICMPv6 router advertisement messages received by this router instance.";
                        }

                        leaf icmp6-in-nbr-solicits {
                            type yang:counter32;
                            description "Number of ICMPv6 neighbor solicitation messages received by this router instance.";
                        }

                        leaf icmp6-in-nbr-advertisements {
                            type yang:counter32;
                            description "Number of ICMPv6 neighbor advertisement messages received by this router instance.";
                        }

                        leaf icmp6-in-redirects {
                            type yang:counter32;
                            description "Number of ICMPv6 redirect messages received by this router instance.";
                        }

                        leaf icmp6-in-grp-memb-queries {
                            type yang:counter32;
                            description "Number of ICMPv6 group membership query messages received by this router instance.";
                        }

                        leaf icmp6-in-grp-memb-repsonses {
                            type yang:counter32;
                            description "Number of ICMPv6 group membership response messages received by this router instance.";
                        }

                        leaf icmp6-in-grp-memb-reductions {
                            type yang:counter32;
                            description "Number of ICMPv6 group membership reduction messages received by this router instance.";
                        }

                        leaf icmp6-out-msgs {
                            type yang:counter32;
                            description
                                "Total number of ICMPv6 messages this router instance attempted to send.
                                                 
                                 This includes all those counted by icmp6-out-errors.";
                        }

                        leaf icmp6-out-errors {
                            type yang:counter32;
                            description
                                "Number of ICMPv6 messages this router instance could not be send due to problems
                                 discovered within ICMPv6 such as lack of buffers.
                                                 
                                 This value should not include errors discovered outside the ICMPv6 layer such as
                                 the inability of VRtr IPv6 to route the resultant datagram. In some implementations
                                 there may be no types of error which contribute to this counter's value.";
                        }

                        leaf icmp6-out-dest-unreachables {
                            type yang:counter32;
                            description "Number of ICMPv6 destination unreachable messages sent by this router instance.";
                        }

                        leaf icmp6-out-admin-prohibs {
                            type yang:counter32;
                            description
                                "Number of ICMPv6 destination unreachable/communication administratively
                                 prohibited messages sent by this router instance.";
                        }

                        leaf icmp6-out-time-exceeds {
                            type yang:counter32;
                            description "Number of ICMPv6 time exceeded messages sent by this router instance.";
                        }

                        leaf icmp6-out-parm-problems {
                            type yang:counter32;
                            description "Number of ICMPv6 parameter problem messages sent by this router instance.";
                        }

                        leaf icmp6-out-pkt-too-bigs {
                            type yang:counter32;
                            description "Number of ICMPv6 packet too big messages sent by this router instance.";
                        }

                        leaf icmp6-out-echos {
                            type yang:counter32;
                            description "Number of ICMPv6 echo request messages sent by this router instance.";
                        }

                        leaf icmp6-out-echo-replies {
                            type yang:counter32;
                            description "Number of ICMPv6 echo reply messages sent by this router instance.";
                        }

                        leaf icmp6-out-rtr-solicits {
                            type yang:counter32;
                            description "Number of ICMPv6 router solicitation messages sent by this router instance.";
                        }

                        leaf icmp6-out-rtr-advertisements {
                            type yang:counter32;
                            description "Number of ICMPv6 router advertisement messages sent by this router instance.";
                        }

                        leaf icmp6-out-nbr-solicits {
                            type yang:counter32;
                            description "Number of ICMPv6 neighbor solicitation messages sent by this router instance.";
                        }

                        leaf icmp6-out-nbr-advertisements {
                            type yang:counter32;
                            description "Number of ICMPv6 neighbor advertisement messages sent by this router instance.";
                        }

                        leaf icmp6-out-redirects {
                            type yang:counter32;
                            description "Number of ICMPv6 redirect messages sent by this router instance.";
                        }

                        leaf icmp6-out-grp-memb-queries {
                            type yang:counter32;
                            description "Number of ICMPv6 group membership query messages sent by this router instance.";
                        }

                        leaf icmp6-out-grp-memb-responses {
                            type yang:counter32;
                            description "Number of ICMPv6 group membership response messages sent by this router instance.";
                        }

                        leaf icmp6-out-grp-memb-reductions {
                            type yang:counter32;
                            description "Number of ICMPv6 group membership reduction messages sent by this router instance.";
                        }

                        leaf icmp6-out-discards {
                            type yang:counter32;
                            description "Number of discarded ICMPv6 messages on this router instance.";
                        }

                    } // container statistics

                } // container icmp6

                container router-advertisement {
                    description "Enter the router-advertisement context";

                    list interface {
                        key "ip-int-name";
                        description "Enter the interface list instance";

                        leaf ip-int-name {
                            type leafref {
                                path "../../../../interface/interface-name";
                            }
                            description "VPRN interface name";
                        }

                        leaf creation-origin {
                            type types-sros:creation-origin;
                            description "Indicates the mechanism which created this router advertisement.";
                        }

                    } // list interface

                } // container router-advertisement

            } // container ipv6

            list spoke-sdp {
                key "sdp-bind-id";
                description "Enter the spoke-sdp list instance";

                leaf sdp-bind-id {
                    type types-services:sdp-bind-id;
                    description "SDP Binding identifier as <sdp-id>:<vc-id>. sdp-id - [1..32767] vc-id - [1..4294967295].";
                }

                leaf oper-state {
                    type enumeration {
                        enum "up"                           { value 1; }
                        enum "down"                         { value 5; }
                    }
                    description "Indicates the operating status of this Service-SDP binding.";
                }

                leaf oper-flags {
                    type bits {
                        bit sdp-bind-admin-down            { position 0; }
                        bit svc-admin-down                 { position 1; }
                        bit stitching-svc-txdown           { position 2; }
                        bit sdp-oper-down                  { position 3; }
                        bit sdp-path-mtu-too-small         { position 4; }
                        bit no-ingress-vc-label            { position 5; }
                        bit no-egress-vc-label             { position 6; }
                        bit svc-mtu-mismatch               { position 7; }
                        bit vc-type-mismatch               { position 8; }
                        bit relearn-limit-exceeded         { position 9; }
                        bit ies-if-admin-down              { position 10; }
                        bit released-ingress-vc-label      { position 11; }
                        bit labels-exhausted               { position 12; }
                        bit svc-param-mismatch             { position 13; }
                        bit insufficient-bandwidth         { position 14; }
                        bit pw-peer-fault-status-bits      { position 15; }
                        bit mesh-sdp-down                  { position 16; }
                        bit not-managed-by-mcring          { position 17; }
                        bit out-of-resource                { position 18; }
                        bit mh-standby                     { position 19; }
                        bit oam-down-mep-fault             { position 20; }
                        bit oam-up-mep-fault               { position 21; }
                        bit standby-sig-slave-tx-down      { position 22; }
                        bit oper-grp-down                  { position 23; }
                        bit withdrawn-ingress-vc-label     { position 24; }
                        bit vpls-pmsi-down                 { position 25; }
                        bit rec-prot-src-mac               { position 26; }
                        bit peer-fault-status-tx-down      { position 27; }
                        bit evpn-route-conflict            { position 28; }
                        bit admin-locked                   { position 29; }
                        bit evpn-p2mp-conflict             { position 30; }
                        bit label-stack-limit-exceeded     { position 31; }
                    }
                    description
                        "This object indicates all the conditions that affect the
                         operating status of this SDP Bind.";
                }

                leaf pw-peer-status-bits {
                    type bits {
                        bit pw-not-forwarding              { position 0; }
                        bit lac-ingress-fault              { position 1; }
                        bit lac-egress-fault               { position 2; }
                        bit psn-ingress-fault              { position 3; }
                        bit psn-egress-fault               { position 4; }
                        bit pw-fwding-standby              { position 5; }
                    }
                    description
                        "Indicates bits set by the LDP peer when there is a fault on its
                         side of the pseudowire";
                }

                leaf pw-local-status-bits {
                    type bits {
                        bit pw-not-forwarding              { position 0; }
                        bit lac-ingress-fault              { position 1; }
                        bit lac-egress-fault               { position 2; }
                        bit psn-ingress-fault              { position 3; }
                        bit psn-egress-fault               { position 4; }
                        bit pw-fwding-standby              { position 5; }
                    }
                    description "Indicates locally set bits when there is a fault.";
                }

                leaf peer-vccv-cv-bits {
                    type bits {
                        bit icmp-ping                      { position 0; }
                        bit lsp-ping                       { position 1; }
                        bit bfd-fault-detection            { position 2; }
                        bit bfd-fault-detection-and-signalling { position 3; }
                    }
                    description "Indicates CV type bits set by the LDP peer if it supports VCCV.";
                }

                leaf peer-vccv-cc-bits {
                    type bits {
                        bit pwe3-control-word              { position 0; }
                        bit mpls-router-alert-label        { position 1; }
                        bit mpls-pw-demultiplex-or-label   { position 2; }
                    }
                    description "Indicates CC type bits set by the LDP peer if it supports VCCV.";
                }

                leaf oper-control-word {
                    type boolean;
                    description "Status of control word.";
                }

                leaf pw-fault-ip-address {
                    type types-sros:ip-address;
                    description "Faulty IP address sent by peer.";
                }

                leaf class-forwarding-oper-state {
                    type types-sros:oper-state;
                    description "Operational state of forwarding-class based forwarding on this SDP bind.";
                }

                leaf creation-origin {
                    type types-sros:creation-origin;
                    description "Creation origin of the service.";
                }

                leaf oper-hash-label {
                    type boolean;
                    description "Indicates the negotiated value of hash lavel that is used on this SDP binding.";
                }

                leaf min-required-sdp-oper-mtu {
                    type int32;
                    description "Minimum required SDP MTU size used with this SDP binding.";
                }

                container ingress {
                    description "Ingress information";

                    leaf oper-label {
                        type uint32;
                        description "MPLS service label used by the far-end device to send packets to the local PEs sdp-bind.";
                    }

                } // container ingress

                container egress {
                    description "Egress information";

                    leaf oper-label {
                        type uint32;
                        description "MPLS service label used to send packets to the far-end device via this sdp-bind.";
                    }

                } // container egress

            } // list spoke-sdp

            container source-address {
                description "Enter the source-address context";

                list ipv4 {
                    key "application";
                    description "Enter the ipv4 list instance";

                    leaf application {
                        type enumeration {
                            enum "telnet"                       { value 1; }
                            enum "ssh"                          { value 3; }
                            enum "ping"                         { value 8; }
                            enum "traceroute"                   { value 9; }
                            enum "ntp"                          { value 12; }
                            enum "cflowd"                       { value 13; }
                            enum "ptp"                          { value 23; }
                            enum "icmp-error"                   { value 29; }
                        }
                        description "Source IP address for the application";
                    }

                    leaf oper-status {
                        type types-system:server-oper-status;
                        description "Indicates the operational status of the source IP entry.";
                    }

                } // list ipv4

                list ipv6 {
                    key "application";
                    description "Enter the ipv6 list instance";

                    leaf application {
                        type enumeration {
                            enum "telnet"                       { value 14; }
                            enum "ping"                         { value 20; }
                            enum "traceroute"                   { value 21; }
                            enum "cflowd"                       { value 25; }
                            enum "ntp"                          { value 26; }
                            enum "icmp6-error"                  { value 30; }
                        }
                        description "Source IPv6 address for the application";
                    }

                    leaf oper-status {
                        type types-system:server-oper-status;
                        description "Indicates the operational status of the soure IPv6 entry.";
                    }

                } // list ipv6

            } // container source-address

            container static-routes {
                description "Enter the static-routes context";

                list route {
                    key "ip-prefix route-type";
                    description "Enter the route list instance";

                    leaf ip-prefix {
                        type types-sros:ip-prefix;
                        description "IP prefix and prefix length for the static routes";
                    }

                    leaf route-type {
                        type types-router:unicast-multicast;
                        description "Indicates the type of that static-route being configured, either for unicast routing or for use with multicast rpf.";
                    }

                    leaf creation-origin {
                        type types-sros:creation-origin;
                        description "Indicates the mechanism used to create this entry.";
                    }

                    leaf next-hops-count {
                        type yang:counter32;
                        description "The number of next-hops configured under this prefix row entry.";
                    }

                    container blackhole {
                        description "Enter the blackhole context";

                        leaf last-enabled-time {
                            type types-sros:date-time;
                            description
                                "Indicates the time when 'status' was last set to active
                                 to allow IP forwarding on this static route entry.";
                        }

                        leaf status {
                            type enumeration {
                                enum "active"                       { value 1; }
                                enum "inactive"                     { value 2; }
                            }
                            description "Indicates whether or not this route entry is active in the system.";
                        }

                        leaf egress-interface-index {
                            type int32 {
                                range "0..max";
                            }
                            description
                                "Indicates the outgoing interface index for this route as computed by the
                                 static-route module.";
                        }

                        leaf creation-origin {
                            type types-sros:creation-origin;
                            description "Indicates the mechanism used to create this entry.";
                        }

                        leaf dynamic-bgp-next-hop {
                            type types-sros:ip-address;
                            description
                                "This is the next-hop of the BGP prefix that matches the static-route prefix in
                                 a blackhole static-route. The static-route is programmed in the route-table
                                 with this next-hop, if present.";
                        }

                        leaf hold-time-left {
                            type uint32;
                            description
                                "If a static-route hold timer is configured and this is non-zero, it indicates
                                 the static-route is being held from becoming active and is the remaining time
                                 in seconds for static route to become active.";
                        }

                    } // container blackhole

                    container grt {
                        description "Enter the grt context";

                        leaf last-enabled-time {
                            type types-sros:date-time;
                            description
                                "Indicates the time when 'status' was last set to active
                                 to allow IP forwarding on this static route entry.";
                        }

                        leaf status {
                            type enumeration {
                                enum "active"                       { value 1; }
                                enum "inactive"                     { value 2; }
                            }
                            description "Indicates whether or not this route entry is active in the system.";
                        }

                        leaf egress-interface-index {
                            type int32 {
                                range "0..max";
                            }
                            description
                                "Indicates the outgoing interface index for this route as computed by the
                                 static-route module.";
                        }

                        leaf creation-origin {
                            type types-sros:creation-origin;
                            description "Indicates the mechanism used to create this entry.";
                        }

                        leaf dynamic-bgp-next-hop {
                            type types-sros:ip-address;
                            description
                                "This is the next-hop of the BGP prefix that matches the static-route prefix in
                                 a blackhole static-route. The static-route is programmed in the route-table
                                 with this next-hop, if present.";
                        }

                        leaf hold-time-left {
                            type uint32;
                            description
                                "If a static-route hold timer is configured and this is non-zero, it indicates
                                 the static-route is being held from becoming active and is the remaining time
                                 in seconds for static route to become active.";
                        }

                    } // container grt

                    list indirect {
                        key "ip-address";
                        description "Enter the indirect list instance";

                        leaf ip-address {
                            type types-sros:ip-address;
                            description "Indirect next hop for static routes";
                        }

                        leaf last-enabled-time {
                            type types-sros:date-time;
                            description
                                "Indicates the time when 'status' was last set to active
                                 to allow IP forwarding on this static route entry.";
                        }

                        leaf status {
                            type enumeration {
                                enum "active"                       { value 1; }
                                enum "inactive"                     { value 2; }
                            }
                            description "Indicates whether or not this route entry is active in the system.";
                        }

                        leaf egress-interface-index {
                            type int32 {
                                range "0..max";
                            }
                            description
                                "Indicates the outgoing interface index for this route as computed by the
                                 static-route module.";
                        }

                        leaf creation-origin {
                            type types-sros:creation-origin;
                            description "Indicates the mechanism used to create this entry.";
                        }

                        leaf dynamic-bgp-next-hop {
                            type types-sros:ip-address;
                            description
                                "This is the next-hop of the BGP prefix that matches the static-route prefix in
                                 a blackhole static-route. The static-route is programmed in the route-table
                                 with this next-hop, if present.";
                        }

                        leaf hold-time-left {
                            type uint32;
                            description
                                "If a static-route hold timer is configured and this is non-zero, it indicates
                                 the static-route is being held from becoming active and is the remaining time
                                 in seconds for static route to become active.";
                        }

                        list cpe-check {
                            key "address";
                            description "Enter the cpe-check list instance";

                            leaf address {
                                type types-sros:ip-address;
                                description "IP address of the target CPE device.";
                            }

                            leaf up-time {
                                type yang:timeticks;
                                description
                                    "Indicates how long (in centiseconds) the CPE has been
                                     available.";
                            }

                            leaf in-packet-count {
                                type yang:counter32;
                                description "Indicates the number of echo-reply packets received.";
                            }

                            leaf out-packet-count {
                                type yang:counter32;
                                description "Indicates the number of echo-request packets sent.";
                            }

                            leaf down-transition {
                                type yang:gauge32;
                                description
                                    "Indicates the number of times the CPE has transitioned
                                     to the unavailable state.";
                            }

                            leaf up-transition {
                                type yang:gauge32;
                                description
                                    "Indicates the number of times the CPE has transitioned
                                     to the available state.";
                            }

                            leaf ttl {
                                type uint32;
                                units "seconds";
                                description "Indicates the time, in seconds, before the CPE will be declared down.";
                            }

                        } // list cpe-check

                    } // list indirect

                    list interface {
                        key "interface-name";
                        description "Enter the interface list instance";

                        leaf interface-name {
                            type types-sros:interface-name;
                            description "Router interface name.";
                        }

                        leaf last-enabled-time {
                            type types-sros:date-time;
                            description
                                "Indicates the time when 'status' was last set to active
                                 to allow IP forwarding on this static route entry.";
                        }

                        leaf status {
                            type enumeration {
                                enum "active"                       { value 1; }
                                enum "inactive"                     { value 2; }
                            }
                            description "Indicates whether or not this route entry is active in the system.";
                        }

                        leaf egress-interface-index {
                            type int32 {
                                range "0..max";
                            }
                            description
                                "Indicates the outgoing interface index for this route as computed by the
                                 static-route module.";
                        }

                        leaf creation-origin {
                            type types-sros:creation-origin;
                            description "Indicates the mechanism used to create this entry.";
                        }

                        leaf dynamic-bgp-next-hop {
                            type types-sros:ip-address;
                            description
                                "This is the next-hop of the BGP prefix that matches the static-route prefix in
                                 a blackhole static-route. The static-route is programmed in the route-table
                                 with this next-hop, if present.";
                        }

                        leaf hold-time-left {
                            type uint32;
                            description
                                "If a static-route hold timer is configured and this is non-zero, it indicates
                                 the static-route is being held from becoming active and is the remaining time
                                 in seconds for static route to become active.";
                        }

                        list cpe-check {
                            key "address";
                            description "Enter the cpe-check list instance";

                            leaf address {
                                type types-sros:ip-address;
                                description "IP address of the target CPE device.";
                            }

                            leaf up-time {
                                type yang:timeticks;
                                description
                                    "Indicates how long (in centiseconds) the CPE has been
                                     available.";
                            }

                            leaf in-packet-count {
                                type yang:counter32;
                                description "Indicates the number of echo-reply packets received.";
                            }

                            leaf out-packet-count {
                                type yang:counter32;
                                description "Indicates the number of echo-request packets sent.";
                            }

                            leaf down-transition {
                                type yang:gauge32;
                                description
                                    "Indicates the number of times the CPE has transitioned
                                     to the unavailable state.";
                            }

                            leaf up-transition {
                                type yang:gauge32;
                                description
                                    "Indicates the number of times the CPE has transitioned
                                     to the available state.";
                            }

                            leaf ttl {
                                type uint32;
                                units "seconds";
                                description "Indicates the time, in seconds, before the CPE will be declared down.";
                            }

                        } // list cpe-check

                    } // list interface

                    list ipsec-tunnel {
                        key "ipsec-tunnel-name";
                        description "Enter the ipsec-tunnel list instance";

                        leaf ipsec-tunnel-name {
                            type types-sros:named-item;
                            description "Ipsec tunnel name.";
                        }

                        leaf last-enabled-time {
                            type types-sros:date-time;
                            description
                                "Indicates the time when 'status' was last set to active
                                 to allow IP forwarding on this static route entry.";
                        }

                        leaf status {
                            type enumeration {
                                enum "active"                       { value 1; }
                                enum "inactive"                     { value 2; }
                            }
                            description "Indicates whether or not this route entry is active in the system.";
                        }

                        leaf egress-interface-index {
                            type int32 {
                                range "0..max";
                            }
                            description
                                "Indicates the outgoing interface index for this route as computed by the
                                 static-route module.";
                        }

                        leaf creation-origin {
                            type types-sros:creation-origin;
                            description "Indicates the mechanism used to create this entry.";
                        }

                        leaf dynamic-bgp-next-hop {
                            type types-sros:ip-address;
                            description
                                "This is the next-hop of the BGP prefix that matches the static-route prefix in
                                 a blackhole static-route. The static-route is programmed in the route-table
                                 with this next-hop, if present.";
                        }

                        leaf hold-time-left {
                            type uint32;
                            description
                                "If a static-route hold timer is configured and this is non-zero, it indicates
                                 the static-route is being held from becoming active and is the remaining time
                                 in seconds for static route to become active.";
                        }

                    } // list ipsec-tunnel

                    list next-hop {
                        key "ip-address";
                        description "Enter the next-hop list instance";

                        leaf ip-address {
                            type types-sros:ip-address-with-zone;
                            description "IP address of the next-hop.";
                        }

                        leaf last-enabled-time {
                            type types-sros:date-time;
                            description
                                "Indicates the time when 'status' was last set to active
                                 to allow IP forwarding on this static route entry.";
                        }

                        leaf status {
                            type enumeration {
                                enum "active"                       { value 1; }
                                enum "inactive"                     { value 2; }
                            }
                            description "Indicates whether or not this route entry is active in the system.";
                        }

                        leaf egress-interface-index {
                            type int32 {
                                range "0..max";
                            }
                            description
                                "Indicates the outgoing interface index for this route as computed by the
                                 static-route module.";
                        }

                        leaf creation-origin {
                            type types-sros:creation-origin;
                            description "Indicates the mechanism used to create this entry.";
                        }

                        leaf dynamic-bgp-next-hop {
                            type types-sros:ip-address;
                            description
                                "This is the next-hop of the BGP prefix that matches the static-route prefix in
                                 a blackhole static-route. The static-route is programmed in the route-table
                                 with this next-hop, if present.";
                        }

                        leaf hold-time-left {
                            type uint32;
                            description
                                "If a static-route hold timer is configured and this is non-zero, it indicates
                                 the static-route is being held from becoming active and is the remaining time
                                 in seconds for static route to become active.";
                        }

                        list cpe-check {
                            key "address";
                            description "Enter the cpe-check list instance";

                            leaf address {
                                type types-sros:ip-address;
                                description "IP address of the target CPE device.";
                            }

                            leaf up-time {
                                type yang:timeticks;
                                description
                                    "Indicates how long (in centiseconds) the CPE has been
                                     available.";
                            }

                            leaf in-packet-count {
                                type yang:counter32;
                                description "Indicates the number of echo-reply packets received.";
                            }

                            leaf out-packet-count {
                                type yang:counter32;
                                description "Indicates the number of echo-request packets sent.";
                            }

                            leaf down-transition {
                                type yang:gauge32;
                                description
                                    "Indicates the number of times the CPE has transitioned
                                     to the unavailable state.";
                            }

                            leaf up-transition {
                                type yang:gauge32;
                                description
                                    "Indicates the number of times the CPE has transitioned
                                     to the available state.";
                            }

                            leaf ttl {
                                type uint32;
                                units "seconds";
                                description "Indicates the time, in seconds, before the CPE will be declared down.";
                            }

                        } // list cpe-check

                    } // list next-hop

                } // list route

            } // container static-routes

            container log {
                description "Enter the log context";

                list filter {
                    key "filter-id";
                    description "Enter the filter list instance";

                    leaf filter-id {
                        type uint32 {
                            range "1..1500";
                        }
                        description "Identification number for an event log filter";
                    }

                    leaf applied {
                        type boolean;
                        description
                            "If 'true', this filter is attached to a log file configuration.
                             The same entry can be attached to more than one log file.";
                    }

                } // list filter

                list log-id {
                    key "id";
                    description "Enter the log-id list instance";

                    leaf id {
                        type int32 {
                            range "1..100";
                        }
                        description "The value of id uniquely identifies an event stream log.";
                    }

                    leaf oper-state {
                        type types-sros:oper-state;
                        description "Operational state.";
                    }

                    leaf wrapped {
                        type boolean;
                        description "The sequence-number for this log has wrapped.";
                    }

                    leaf next-event {
                        type yang:counter64;
                        description
                            "The value of the this object is the count of the number
                             of events that have been forwarded to this logs's destination.";
                    }

                    container statistics {
                        description "Log-id statistics.";

                        leaf logged-events {
                            type yang:counter64;
                            description
                                "The value of the this object is the count of the number
                                 of events that have been forwarded to this logs's destination.";
                        }

                        leaf dropped-events {
                            type yang:counter64;
                            description
                                "The value of the this object is the count of the number
                                 of events that have been sent to this logs source(s) and
                                 that have not been forwarded to the log destination because
                                 they were filtered out by the log filter.";
                        }

                    } // container statistics

                    list event {
                        key "sequence-number";
                        description
                            "Generated on any event that is generated in the system
                             that is not modeled by a more specific event.";

                        leaf sequence-number {
                            type uint64;
                            description
                                "A sequence number to indicate the ordering of log events in the log-id.
                                 If the event is replayed, the sequence number is replayed as well.";
                        }

                        leaf time {
                            type yang:date-and-time;
                            description "Time when the event was generated.";
                        }

                        leaf severity {
                            type types-log:severity-level;
                            description "The severity level of the log event.";
                        }

                        leaf application {
                            type types-log:application;
                            description "The name of the application that reports the log event.";
                        }

                        leaf event-id {
                            type uint32 {
                                range "1..max";
                            }
                            description
                                "The id the event that was generated.
                                 Each log event type has a unique identifying number.  This number is
                                 unique within a particular software application, such as IP, MPLS,
                                 OSPF, etc. but it is not necessarily unique across different software
                                 applications.  That is MPLS event #1001 may be different from OSPF
                                 event #1001.";
                        }

                        leaf event-name {
                            type types-sros:named-item;
                            description "The name of the log event that was generated.";
                        }

                        leaf vrtr-name {
                            type types-log:vrtr-name;
                            description "The router context name that generated the log event.";
                        }

                        leaf subject {
                            type string {
                                length "0..32";
                            }
                            description
                                "The router context name that generated the log event.
                                 The subject is the entity that originated the event, such as the Port ID.";
                        }

                        leaf message {
                            type string {
                                length "1..4100";
                            }
                            description "The log event message.";
                        }

                    } // list event

                } // list log-id

                list snmp-trap-group {
                    key "log-id";
                    description "Enter the snmp-trap-group list instance";

                    leaf log-id {
                        type int32 {
                            range "1..100";
                        }
                        description "SNMP notification group associated with the event log";
                    }

                    list trap-target {
                        key "name";
                        description "Enter the trap-target list instance";

                        leaf name {
                            type string {
                                length "1..28";
                            }
                            description "Name for an SNMP notification destination within the SNMP notification group";
                        }

                        leaf replay-start-id {
                            type uint32;
                            description
                                "Indicates the SNMP notification request ID of the first event
                                 that could not be generated because there is no route to this
                                  notification target address.";
                        }

                        leaf last-replay-time {
                            type yang:date-and-time;
                            description
                                "Indicates the time when missed events were last replayed
                                 to this SNMP notification target address.";
                        }

                    } // list trap-target

                } // list snmp-trap-group

                list syslog {
                    key "syslog-id";
                    description "Enter the syslog list instance";

                    leaf syslog-id {
                        type int32 {
                            range "1..30";
                        }
                        description "Unique arbitrary identifier for this SYSLOG collector target";
                    }

                    leaf below-severity-drops {
                        type yang:counter32;
                        description
                            "Identifies the count of messages not sent to this syslog collector
                             target because the severity level of the message was above the configured level.";
                    }

                } // list syslog

            } // container log

            container pcp {
                description "Enter the pcp context";

                list server {
                    key "name";
                    description "Enter the server list instance";

                    leaf name {
                        type types-sros:named-item;
                        description "PCP server name";
                    }

                    leaf oper-state {
                        type types-sros:oper-state;
                        description "Operational state of PCP server";
                    }

                    leaf oper-state-reason {
                        type string;
                        description "Description of the state of the PCP server";
                    }

                    leaf epoch {
                        type uint32;
                        description "PCP server epoch";
                    }

                    list interface {
                        key "name";
                        description "Add a list entry for interface";

                        leaf name {
                            type leafref {
                                path "../../../../interface/interface-name";
                            }
                            description "Interface name";
                        }

                        container statistics {
                            description "PCP server interface statistics";

                            container received {
                                description "PCP server interface ingress statistics";

                                container opcode {
                                    description "PCP server interface received opcodes";

                                    leaf announce {
                                        type yang:counter64;
                                        description "Received announce requests";
                                    }

                                    leaf map {
                                        type yang:counter64;
                                        description "Received map requests";
                                    }

                                    leaf peer {
                                        type yang:counter64;
                                        description "Received peer requests";
                                    }

                                    leaf get {
                                        type yang:counter64;
                                        description "Received get requests";
                                    }

                                    leaf unknown {
                                        type yang:counter64;
                                        description "Received requests with an unknown or unsupported opcodes";
                                    }

                                } // container opcode

                                container option {
                                    description "PCP server interface received options";

                                    leaf description {
                                        type yang:counter64;
                                        description "Received requests containing the description option";
                                    }

                                    leaf filter {
                                        type yang:counter64;
                                        description "Received requests containing the filter option";
                                    }

                                    leaf next {
                                        type yang:counter64;
                                        description "Received requests containing the next option";
                                    }

                                    leaf port-reservation {
                                        type yang:counter64;
                                        description "Received PCP requests containing the port-reservation option";
                                    }

                                    leaf prefer-failure {
                                        type yang:counter64;
                                        description "Received requests containing the prefer-failure option";
                                    }

                                    leaf third-party {
                                        type yang:counter64;
                                        description "Received requests containing a third-party option";
                                    }

                                    leaf unknown {
                                        type yang:counter64;
                                        description "Received requests containing unknown or unsupported options";
                                    }

                                } // container option

                                container dropped {
                                    description "PCP server interface dropped requests";

                                    leaf packet-too-short {
                                        type yang:counter64;
                                        description "Dropped requests due to the packet being too short";
                                    }

                                    leaf wrong-r-bit {
                                        type yang:counter64;
                                        description "Dropped requests due to the wrong r bit";
                                    }

                                    leaf invalid-source-address {
                                        type yang:counter64;
                                        description "Dropped requests due to the use of an invalid source address";
                                    }

                                    leaf oper-down {
                                        type yang:counter64;
                                        description "Dropped requests due to the PCP server being operationally down";
                                    }

                                } // container dropped

                            } // container received

                            container transmitted {
                                description "PCP server interface egress statistics";

                                leaf v4 {
                                    type yang:counter64;
                                    description "Replies sent via IPv4";
                                }

                                leaf v6 {
                                    type yang:counter64;
                                    description "Replies sent via IPv6";
                                }

                                container result {
                                    description "PCP server interface transmitted results";

                                    leaf address-mismatch {
                                        type yang:counter64;
                                        description "Replies sent with result address mismatch";
                                    }

                                    leaf ambiguous {
                                        type yang:counter64;
                                        description "Replies sent with result ambiguous";
                                    }

                                    leaf cannot-provide-external {
                                        type yang:counter64;
                                        description "Replies sent with result cannot-provide-external";
                                    }

                                    leaf malformed-option {
                                        type yang:counter64;
                                        description "Replies sent with result malformed-option";
                                    }

                                    leaf malformed-request {
                                        type yang:counter64;
                                        description "Replies sent with result malformed-request";
                                    }

                                    leaf network-failure {
                                        type yang:counter64;
                                        description "Replies sent with result network-failure";
                                    }

                                    leaf no-more-mappings {
                                        type yang:counter64;
                                        description "Replies sent with result no-more-mappings";
                                    }

                                    leaf no-resources {
                                        type yang:counter64;
                                        description "Replies sent with result no-resources";
                                    }

                                    leaf not-authorized {
                                        type yang:counter64;
                                        description "Replies sent with result not-authorized";
                                    }

                                    leaf success {
                                        type yang:counter64;
                                        description "Replies sent with result success";
                                    }

                                    leaf unsupported-opcode {
                                        type yang:counter64;
                                        description "Replies sent with result unsupported-opcode";
                                    }

                                    leaf unsupported-option {
                                        type yang:counter64;
                                        description "Replies sent with result unsupported-option";
                                    }

                                    leaf unsupported-protocol {
                                        type yang:counter64;
                                        description "Replies sent with result unsupported-protocol";
                                    }

                                    leaf unsupported-version {
                                        type yang:counter64;
                                        description "Replies sent with result unsupported-version";
                                    }

                                    leaf user-exceeded-quota {
                                        type yang:counter64;
                                        description "Replies sent with result user-exceeded-quota";
                                    }

                                } // container result

                            } // container transmitted

                            container dropped {
                                description "PCP server interface dropped replies statistics";

                                leaf tx-error {
                                    type yang:counter64;
                                    description "Replies that could not be sent due to transmission errors";
                                }

                            } // container dropped

                        } // container statistics

                    } // list interface

                } // list server

            } // container pcp

            container route-table {

                container unicast {
                    description "This is the unicast routing FIB.";

                    container ipv4 {

                        container statistics {

                            container aggregate {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container aggregate

                            container arp-nd {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container arp-nd

                            container bgp {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp

                            container bgp-backup {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp-backup

                            container bgp-evpn {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp-evpn

                            container bgp-label {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp-label

                            container bgp-vpn {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp-vpn

                            container bgp-vpn-backup {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp-vpn-backup

                            container direct {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container direct

                            container host {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container host

                            container ipsec {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ipsec

                            container isis {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container isis

                            container isis-lfa {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container isis-lfa

                            container managed {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container managed

                            container nat {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container nat

                            container ospf {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ospf

                            container ospf-lfa {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ospf-lfa

                            container ospfv3 {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ospfv3

                            container ospfv3-lfa {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ospfv3-lfa

                            container periodic {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container periodic

                            container rip {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container rip

                            container static {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container static

                            container sub-mgmt {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container sub-mgmt

                            container vpn-leak {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container vpn-leak

                        } // container statistics

                        list route {
                            key "ipv4-prefix";
                            description "This is the IPv4 unicast routing FIB.";

                            leaf ipv4-prefix {
                                type types-sros:ipv4-prefix;
                                description "Indicates the IPv4 prefix for this route table entry.";
                            }

                            leaf age {
                                type uint32 {
                                    range "0..4294967295";
                                }
                                description "The number of seconds since this route was last updated.";
                            }

                            leaf instance {
                                type uint8;
                                description "The protocol instance the route belongs to.";
                            }

                            leaf flags {
                                type bits {
                                    bit sticky-flag                    { position 0; }
                                }
                                description
                                    "Bit flags that indicate different properties of this route.

                                     If the 'stickyFlag' bit is set, it indicates the ECMP
                                     sticky flag is set on this route.";
                            }

                            leaf preference {
                                type uint8;
                                description
                                    "Indicates the priority of this route versus the routes
                                     from different sources such as BGP or OSPF etc.";
                            }

                            leaf protocol {
                                type types-router:protocol-type;
                                description "Identifies the routing protocol.";
                            }

                            list nexthop {
                                key "nexthop-index";
                                description
                                    "This is the set of next-hops used by the
                                     route.";

                                leaf nexthop-index {
                                    type uint32;
                                    description "Index of ECMP next-hop or backup next-hop.";
                                }

                                leaf flags {
                                    type bits {
                                        bit nh-is-indirect                 { position 0; }
                                        bit nh-is-tunneled                 { position 1; }
                                        bit nh-is-lfa                      { position 2; }
                                        bit nh-is-backup                   { position 3; }
                                        bit nh-is-unnumbered               { position 4; }
                                    }
                                    description
                                        "Bit flags that indicate different properties of this next-hop.

                                         If the 'nh-is-indirect' bit is set, it indicates the next-hop is
                                         an indirect next-hop IP. An additional lookup will have to be
                                         made to map the indirect IP address to the resolving IP
                                         address(es) The 'if-index' leaf will be 0 in this case.

                                         If the 'nh-is-tunneled' bit is set, it indicates the next-hop is
                                         a tunnel destination (the 'nexthop-ip' leaf is a far-end tunnel
                                         destination). The 'if-index' leaf will be 0 in this case.

                                         If the 'nh-is-lfa' bit is set, it indicates the next-hop is a
                                         loop-free alternate (LFA) of the next-hop immediately preceding
                                         this next-hop.

                                         If the 'nh-is-backup' bit is set, it indicates the next-hop is
                                         a BGP backup next-hop.

                                         If the 'nh-is-unnumbered' bit is set, it indicates the next-hop is
                                         unnumbered.";
                                }

                                leaf if-index {
                                    type uint32;
                                    description
                                        "This is the index of the egress interface where the
                                         next-hop resides.";
                                }

                                leaf if-vrtr-id {
                                    type uint32;
                                    description
                                        "Indicates the virtual router instance of the egress interface
                                         defined by 'if-index'.";
                                }

                                leaf metric {
                                    type uint32;
                                    description "Indicates the routing metric for the next-hop.";
                                }

                                leaf nexthop-ip {
                                    type types-sros:ip-address;
                                    description
                                        "Indicates the next-hop IP address of the route entry.

                                         The nexthop-ip is a tunnel far-end IP if the 'flags' leaf
                                         has the 'nh-is-tunneled' bit set.

                                         The nexthop-ip is an indirect IP if the 'flags' leaf has
                                         the 'nh-is-indirect' bit set.";
                                }

                                leaf nexthop-tunnel-id {
                                    type uint32;
                                    description
                                        "This indicates the next-hop tunnel ID when there are
                                         multiple tunnels to a destination or SDP ID.";
                                }

                                leaf nexthop-tunnel-type {
                                    type types-router:tunnel-type;
                                    description
                                        "This indicates the next-hop tunnel type if the
                                         'flags' leaf has the 'nh-is-tunneled' bit set.";
                                }

                                leaf nexthop-tunnel-type-instance {
                                    type uint8;
                                    description
                                        "This indicates the next-hop tunnel type instance if
                                         the 'flags' leaf has the 'nh-is-tunneled' bit set.";
                                }

                                leaf nexthop-label {
                                    type uint32 {
                                        range "0..1048575";
                                    }
                                    description "This is a VPRN or route label associated with the route entry.";
                                }

                                leaf forwarding-class {
                                    type types-sros:fc-name;
                                    description "This is the forwarding class associated with the next-hop.";
                                }

                                leaf priority {
                                    type types-router:nexthop-priority;
                                    description "This is the priority associated with packets to the next-hop.";
                                }

                                leaf source-class-index {
                                    type uint8 {
                                        range "1..255";
                                    }
                                    description "This is the source class index associated with the next-hop.";
                                }

                                leaf dest-class-index {
                                    type uint8 {
                                        range "1..255";
                                    }
                                    description "This is the destination class index associated with the next-hop.";
                                }

                                leaf weight {
                                    type types-router:ip-ecmp;
                                    description
                                        "The value of this leaf indicates the weight given to traffic using this
                                         particular next-hop among the ECMP set of next-hops.";
                                }

                                list resolving-nexthop {
                                    key "resolving-nexthop-index";
                                    description "This is the set of ECMP resolving hops of an indirect next-hop";

                                    leaf resolving-nexthop-index {
                                        type uint32;
                                        description "Index of ECMP resolving next-hop or LFA next-hop.";
                                    }

                                    leaf flags {
                                        type bits {
                                            bit nh-is-indirect                 { position 0; }
                                            bit nh-is-tunneled                 { position 1; }
                                            bit nh-is-lfa                      { position 2; }
                                            bit nh-is-backup                   { position 3; }
                                            bit nh-is-unnumbered               { position 4; }
                                        }
                                        description
                                            "Bit flags that indicate different properties of this next-hop.

                                             If the 'nh-is-indirect' bit is set, it indicates the next-hop is
                                             an indirect next-hop IP. An additional lookup will have to be
                                             made to map the indirect IP address to the resolving IP
                                             address(es) The 'if-index' leaf will be 0 in this case.

                                             If the 'nh-is-tunneled' bit is set, it indicates the next-hop is
                                             a tunnel destination (the 'nexthop-ip' leaf is a far-end tunnel
                                             destination). The 'if-index' leaf will be 0 in this case.

                                             If the 'nh-is-lfa' bit is set, it indicates the next-hop is a
                                             loop-free alternate (LFA) of the next-hop immediately preceding
                                             this next-hop.

                                             If the 'nh-is-backup' bit is set, it indicates the next-hop is
                                             a BGP backup next-hop.

                                             If the 'nh-is-unnumbered' bit is set, it indicates the next-hop is
                                             unnumbered.";
                                    }

                                    leaf if-index {
                                        type uint32;
                                        description
                                            "This is the index of the egress interface where the
                                             next-hop resides.";
                                    }

                                    leaf if-vrtr-id {
                                        type uint32;
                                        description
                                            "Indicates the virtual router instance of the egress interface
                                             defined by 'if-index'.";
                                    }

                                    leaf metric {
                                        type uint32;
                                        description "Indicates the routing metric for the next-hop.";
                                    }

                                    leaf nexthop-ip {
                                        type types-sros:ip-address;
                                        description
                                            "Indicates the next-hop IP address of the route entry.

                                             The nexthop-ip is a tunnel far-end IP if the 'flags' leaf
                                             has the 'nh-is-tunneled' bit set.

                                             The nexthop-ip is an indirect IP if the 'flags' leaf has
                                             the 'nh-is-indirect' bit set.";
                                    }

                                    leaf nexthop-tunnel-id {
                                        type uint32;
                                        description
                                            "This indicates the next-hop tunnel ID when there are
                                             multiple tunnels to a destination or SDP ID.";
                                    }

                                    leaf nexthop-tunnel-type {
                                        type types-router:tunnel-type;
                                        description
                                            "This indicates the next-hop tunnel type if the
                                             'flags' leaf has the 'nh-is-tunneled' bit set.";
                                    }

                                    leaf nexthop-tunnel-type-instance {
                                        type uint8;
                                        description
                                            "This indicates the next-hop tunnel type instance if
                                             the 'flags' leaf has the 'nh-is-tunneled' bit set.";
                                    }

                                    leaf nexthop-label {
                                        type uint32 {
                                            range "0..1048575";
                                        }
                                        description "This is a VPRN or route label associated with the route entry.";
                                    }

                                    leaf forwarding-class {
                                        type types-sros:fc-name;
                                        description "This is the forwarding class associated with the next-hop.";
                                    }

                                    leaf priority {
                                        type types-router:nexthop-priority;
                                        description "This is the priority associated with packets to the next-hop.";
                                    }

                                    leaf source-class-index {
                                        type uint8 {
                                            range "1..255";
                                        }
                                        description "This is the source class index associated with the next-hop.";
                                    }

                                    leaf dest-class-index {
                                        type uint8 {
                                            range "1..255";
                                        }
                                        description "This is the destination class index associated with the next-hop.";
                                    }

                                    leaf weight {
                                        type types-router:ip-ecmp;
                                        description
                                            "The value of this leaf indicates the weight given to traffic using this
                                             particular next-hop among the ECMP set of next-hops.";
                                    }

                                } // list resolving-nexthop

                            } // list nexthop

                        } // list route

                    } // container ipv4

                    container ipv6 {

                        container statistics {

                            container aggregate {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container aggregate

                            container arp-nd {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container arp-nd

                            container bgp {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp

                            container bgp-backup {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp-backup

                            container bgp-evpn {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp-evpn

                            container bgp-label {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp-label

                            container bgp-vpn {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp-vpn

                            container bgp-vpn-backup {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp-vpn-backup

                            container dhcpv6-bh {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container dhcpv6-bh

                            container dhcpv6-na {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container dhcpv6-na

                            container dhcpv6-pd {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container dhcpv6-pd

                            container dhcpv6-ta {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container dhcpv6-ta

                            container direct {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container direct

                            container host {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container host

                            container ipsec {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ipsec

                            container isis {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container isis

                            container isis-lfa {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container isis-lfa

                            container managed {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container managed

                            container nat {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container nat

                            container ospfv3 {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ospfv3

                            container ospfv3-lfa {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ospfv3-lfa

                            container periodic {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container periodic

                            container rip {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container rip

                            container static {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container static

                            container sub-mgmt {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container sub-mgmt

                            container vpn-leak {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container vpn-leak

                        } // container statistics

                        list route {
                            key "ipv6-prefix";
                            description "This is the IPv6 unicast routing FIB.";

                            leaf ipv6-prefix {
                                type types-sros:ipv6-prefix;
                                description "Indicates the IPv6 prefix for this route table entry.";
                            }

                            leaf age {
                                type uint32 {
                                    range "0..4294967295";
                                }
                                description "The number of seconds since this route was last updated.";
                            }

                            leaf instance {
                                type uint8;
                                description "The protocol instance the route belongs to.";
                            }

                            leaf flags {
                                type bits {
                                    bit sticky-flag                    { position 0; }
                                }
                                description
                                    "Bit flags that indicate different properties of this route.

                                     If the 'stickyFlag' bit is set, it indicates the ECMP
                                     sticky flag is set on this route.";
                            }

                            leaf preference {
                                type uint8;
                                description
                                    "Indicates the priority of this route versus the routes
                                     from different sources such as BGP or OSPF etc.";
                            }

                            leaf protocol {
                                type types-router:protocol-type;
                                description "Identifies the routing protocol.";
                            }

                            list nexthop {
                                key "nexthop-index";
                                description
                                    "This is the set of ECMP next-hops used by the
                                     route.";

                                leaf nexthop-index {
                                    type uint32;
                                    description "Index of ECMP next-hop or backup next-hop.";
                                }

                                leaf flags {
                                    type bits {
                                        bit nh-is-indirect                 { position 0; }
                                        bit nh-is-tunneled                 { position 1; }
                                        bit nh-is-lfa                      { position 2; }
                                        bit nh-is-backup                   { position 3; }
                                        bit nh-is-unnumbered               { position 4; }
                                    }
                                    description
                                        "Bit flags that indicate different properties of this next-hop.

                                         If the 'nh-is-indirect' bit is set, it indicates the next-hop is
                                         an indirect next-hop IP. An additional lookup will have to be
                                         made to map the indirect IP address to the resolving IP
                                         address(es) The 'if-index' leaf will be 0 in this case.

                                         If the 'nh-is-tunneled' bit is set, it indicates the next-hop is
                                         a tunnel destination (the 'nexthop-ip' leaf is a far-end tunnel
                                         destination). The 'if-index' leaf will be 0 in this case.

                                         If the 'nh-is-lfa' bit is set, it indicates the next-hop is a
                                         loop-free alternate (LFA) of the next-hop immediately preceding
                                         this next-hop.

                                         If the 'nh-is-backup' bit is set, it indicates the next-hop is
                                         a BGP backup next-hop.

                                         If the 'nh-is-unnumbered' bit is set, it indicates the next-hop is
                                         unnumbered.";
                                }

                                leaf if-index {
                                    type uint32;
                                    description
                                        "This is the index of the egress interface where the
                                         next-hop resides.";
                                }

                                leaf if-vrtr-id {
                                    type uint32;
                                    description
                                        "Indicates the virtual router instance of the egress interface
                                         defined by 'if-index'.";
                                }

                                leaf metric {
                                    type uint32;
                                    description "Indicates the routing metric for the next-hop.";
                                }

                                leaf nexthop-ip {
                                    type types-sros:ip-address;
                                    description
                                        "Indicates the next-hop IP address of the route entry.

                                         The nexthop-ip is a tunnel far-end IP if the 'flags' leaf
                                         has the 'nh-is-tunneled' bit set.

                                         The nexthop-ip is an indirect IP if the 'flags' leaf has
                                         the 'nh-is-indirect' bit set.";
                                }

                                leaf nexthop-tunnel-id {
                                    type uint32;
                                    description
                                        "This indicates the next-hop tunnel ID when there are
                                         multiple tunnels to a destination or SDP ID.";
                                }

                                leaf nexthop-tunnel-type {
                                    type types-router:tunnel-type;
                                    description
                                        "This indicates the next-hop tunnel type if the
                                         'flags' leaf has the 'nh-is-tunneled' bit set.";
                                }

                                leaf nexthop-tunnel-type-instance {
                                    type uint8;
                                    description
                                        "This indicates the next-hop tunnel type instance if
                                         the 'flags' leaf has the 'nh-is-tunneled' bit set.";
                                }

                                leaf nexthop-label {
                                    type uint32 {
                                        range "0..1048575";
                                    }
                                    description "This is a VPRN or route label associated with the route entry.";
                                }

                                leaf forwarding-class {
                                    type types-sros:fc-name;
                                    description "This is the forwarding class associated with the next-hop.";
                                }

                                leaf priority {
                                    type types-router:nexthop-priority;
                                    description "This is the priority associated with packets to the next-hop.";
                                }

                                leaf source-class-index {
                                    type uint8 {
                                        range "1..255";
                                    }
                                    description "This is the source class index associated with the next-hop.";
                                }

                                leaf dest-class-index {
                                    type uint8 {
                                        range "1..255";
                                    }
                                    description "This is the destination class index associated with the next-hop.";
                                }

                                leaf weight {
                                    type types-router:ip-ecmp;
                                    description
                                        "The value of this leaf indicates the weight given to traffic using this
                                         particular next-hop among the ECMP set of next-hops.";
                                }

                                list resolving-nexthop {
                                    key "resolving-nexthop-index";
                                    description "This is the set of ECMP resolving hops of an indirect next-hop";

                                    leaf resolving-nexthop-index {
                                        type uint32;
                                        description "Index of ECMP resolving next-hop or LFA next-hop.";
                                    }

                                    leaf flags {
                                        type bits {
                                            bit nh-is-indirect                 { position 0; }
                                            bit nh-is-tunneled                 { position 1; }
                                            bit nh-is-lfa                      { position 2; }
                                            bit nh-is-backup                   { position 3; }
                                            bit nh-is-unnumbered               { position 4; }
                                        }
                                        description
                                            "Bit flags that indicate different properties of this next-hop.

                                             If the 'nh-is-indirect' bit is set, it indicates the next-hop is
                                             an indirect next-hop IP. An additional lookup will have to be
                                             made to map the indirect IP address to the resolving IP
                                             address(es) The 'if-index' leaf will be 0 in this case.

                                             If the 'nh-is-tunneled' bit is set, it indicates the next-hop is
                                             a tunnel destination (the 'nexthop-ip' leaf is a far-end tunnel
                                             destination). The 'if-index' leaf will be 0 in this case.

                                             If the 'nh-is-lfa' bit is set, it indicates the next-hop is a
                                             loop-free alternate (LFA) of the next-hop immediately preceding
                                             this next-hop.

                                             If the 'nh-is-backup' bit is set, it indicates the next-hop is
                                             a BGP backup next-hop.

                                             If the 'nh-is-unnumbered' bit is set, it indicates the next-hop is
                                             unnumbered.";
                                    }

                                    leaf if-index {
                                        type uint32;
                                        description
                                            "This is the index of the egress interface where the
                                             next-hop resides.";
                                    }

                                    leaf if-vrtr-id {
                                        type uint32;
                                        description
                                            "Indicates the virtual router instance of the egress interface
                                             defined by 'if-index'.";
                                    }

                                    leaf metric {
                                        type uint32;
                                        description "Indicates the routing metric for the next-hop.";
                                    }

                                    leaf nexthop-ip {
                                        type types-sros:ip-address;
                                        description
                                            "Indicates the next-hop IP address of the route entry.

                                             The nexthop-ip is a tunnel far-end IP if the 'flags' leaf
                                             has the 'nh-is-tunneled' bit set.

                                             The nexthop-ip is an indirect IP if the 'flags' leaf has
                                             the 'nh-is-indirect' bit set.";
                                    }

                                    leaf nexthop-tunnel-id {
                                        type uint32;
                                        description
                                            "This indicates the next-hop tunnel ID when there are
                                             multiple tunnels to a destination or SDP ID.";
                                    }

                                    leaf nexthop-tunnel-type {
                                        type types-router:tunnel-type;
                                        description
                                            "This indicates the next-hop tunnel type if the
                                             'flags' leaf has the 'nh-is-tunneled' bit set.";
                                    }

                                    leaf nexthop-tunnel-type-instance {
                                        type uint8;
                                        description
                                            "This indicates the next-hop tunnel type instance if
                                             the 'flags' leaf has the 'nh-is-tunneled' bit set.";
                                    }

                                    leaf nexthop-label {
                                        type uint32 {
                                            range "0..1048575";
                                        }
                                        description "This is a VPRN or route label associated with the route entry.";
                                    }

                                    leaf forwarding-class {
                                        type types-sros:fc-name;
                                        description "This is the forwarding class associated with the next-hop.";
                                    }

                                    leaf priority {
                                        type types-router:nexthop-priority;
                                        description "This is the priority associated with packets to the next-hop.";
                                    }

                                    leaf source-class-index {
                                        type uint8 {
                                            range "1..255";
                                        }
                                        description "This is the source class index associated with the next-hop.";
                                    }

                                    leaf dest-class-index {
                                        type uint8 {
                                            range "1..255";
                                        }
                                        description "This is the destination class index associated with the next-hop.";
                                    }

                                    leaf weight {
                                        type types-router:ip-ecmp;
                                        description
                                            "The value of this leaf indicates the weight given to traffic using this
                                             particular next-hop among the ECMP set of next-hops.";
                                    }

                                } // list resolving-nexthop

                            } // list nexthop

                        } // list route

                    } // container ipv6

                } // container unicast

                container multicast {

                    container ipv4 {

                        container statistics {

                            container bgp {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp

                            container bgp-vpn {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp-vpn

                            container direct {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container direct

                            container host {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container host

                            container isis {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container isis

                            container ospf {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ospf

                            container ospfv3 {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ospfv3

                            container static {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container static

                        } // container statistics

                        list route {
                            key "ipv4-prefix";
                            description "This is the IPv4 multicast RPF table.";

                            leaf ipv4-prefix {
                                type types-sros:ipv4-prefix;
                                description "Indicates the IPv4 prefix for this route table entry.";
                            }

                            leaf age {
                                type uint32 {
                                    range "0..4294967295";
                                }
                                description "The number of seconds since this route was last updated.";
                            }

                            leaf instance {
                                type uint8;
                                description "The protocol instance the route belongs to.";
                            }

                            leaf flags {
                                type bits {
                                    bit sticky-flag                    { position 0; }
                                }
                                description
                                    "Bit flags that indicate different properties of this route.

                                     If the 'stickyFlag' bit is set, it indicates the ECMP
                                     sticky flag is set on this route.";
                            }

                            leaf preference {
                                type uint8;
                                description
                                    "Indicates the priority of this route versus the routes
                                     from different sources such as BGP or OSPF etc.";
                            }

                            leaf protocol {
                                type types-router:protocol-type;
                                description "Identifies the routing protocol.";
                            }

                            list nexthop {
                                key "nexthop-index";
                                description
                                    "This is the set of ECMP next-hops used by the
                                     route.";

                                leaf nexthop-index {
                                    type uint32;
                                    description "Index of ECMP next-hop or backup next-hop.";
                                }

                                leaf flags {
                                    type bits {
                                        bit nh-is-indirect                 { position 0; }
                                        bit nh-is-tunneled                 { position 1; }
                                        bit nh-is-lfa                      { position 2; }
                                        bit nh-is-backup                   { position 3; }
                                        bit nh-is-unnumbered               { position 4; }
                                    }
                                    description
                                        "Bit flags that indicate different properties of this next-hop.

                                         If the 'nh-is-indirect' bit is set, it indicates the next-hop is
                                         an indirect next-hop IP. An additional lookup will have to be
                                         made to map the indirect IP address to the resolving IP
                                         address(es) The 'if-index' leaf will be 0 in this case.

                                         If the 'nh-is-tunneled' bit is set, it indicates the next-hop is
                                         a tunnel destination (the 'nexthop-ip' leaf is a far-end tunnel
                                         destination). The 'if-index' leaf will be 0 in this case.

                                         If the 'nh-is-lfa' bit is set, it indicates the next-hop is a
                                         loop-free alternate (LFA) of the next-hop immediately preceding
                                         this next-hop.

                                         If the 'nh-is-backup' bit is set, it indicates the next-hop is
                                         a BGP backup next-hop.

                                         If the 'nh-is-unnumbered' bit is set, it indicates the next-hop is
                                         unnumbered.";
                                }

                                leaf if-index {
                                    type uint32;
                                    description
                                        "This is the index of the egress interface where the
                                         next-hop resides.";
                                }

                                leaf if-vrtr-id {
                                    type uint32;
                                    description
                                        "Indicates the virtual router instance of the egress interface
                                         defined by 'if-index'.";
                                }

                                leaf metric {
                                    type uint32;
                                    description "Indicates the routing metric for the next-hop.";
                                }

                                leaf nexthop-ip {
                                    type types-sros:ip-address;
                                    description
                                        "Indicates the next-hop IP address of the route entry.

                                         The nexthop-ip is a tunnel far-end IP if the 'flags' leaf
                                         has the 'nh-is-tunneled' bit set.

                                         The nexthop-ip is an indirect IP if the 'flags' leaf has
                                         the 'nh-is-indirect' bit set.";
                                }

                                leaf nexthop-tunnel-id {
                                    type uint32;
                                    description
                                        "This indicates the next-hop tunnel ID when there are
                                         multiple tunnels to a destination or SDP ID.";
                                }

                                leaf nexthop-tunnel-type {
                                    type types-router:tunnel-type;
                                    description
                                        "This indicates the next-hop tunnel type if the
                                         'flags' leaf has the 'nh-is-tunneled' bit set.";
                                }

                                leaf nexthop-tunnel-type-instance {
                                    type uint8;
                                    description
                                        "This indicates the next-hop tunnel type instance if
                                         the 'flags' leaf has the 'nh-is-tunneled' bit set.";
                                }

                                leaf nexthop-label {
                                    type uint32 {
                                        range "0..1048575";
                                    }
                                    description "This is a VPRN or route label associated with the route entry.";
                                }

                                leaf forwarding-class {
                                    type types-sros:fc-name;
                                    description "This is the forwarding class associated with the next-hop.";
                                }

                                leaf priority {
                                    type types-router:nexthop-priority;
                                    description "This is the priority associated with packets to the next-hop.";
                                }

                                leaf source-class-index {
                                    type uint8 {
                                        range "1..255";
                                    }
                                    description "This is the source class index associated with the next-hop.";
                                }

                                leaf dest-class-index {
                                    type uint8 {
                                        range "1..255";
                                    }
                                    description "This is the destination class index associated with the next-hop.";
                                }

                                leaf weight {
                                    type types-router:ip-ecmp;
                                    description
                                        "The value of this leaf indicates the weight given to traffic using this
                                         particular next-hop among the ECMP set of next-hops.";
                                }

                                list resolving-nexthop {
                                    key "resolving-nexthop-index";
                                    description "This is the set of ECMP resolving hops of an indirect next-hop";

                                    leaf resolving-nexthop-index {
                                        type uint32;
                                        description "Index of ECMP resolving next-hop or LFA next-hop.";
                                    }

                                    leaf flags {
                                        type bits {
                                            bit nh-is-indirect                 { position 0; }
                                            bit nh-is-tunneled                 { position 1; }
                                            bit nh-is-lfa                      { position 2; }
                                            bit nh-is-backup                   { position 3; }
                                            bit nh-is-unnumbered               { position 4; }
                                        }
                                        description
                                            "Bit flags that indicate different properties of this next-hop.

                                             If the 'nh-is-indirect' bit is set, it indicates the next-hop is
                                             an indirect next-hop IP. An additional lookup will have to be
                                             made to map the indirect IP address to the resolving IP
                                             address(es) The 'if-index' leaf will be 0 in this case.

                                             If the 'nh-is-tunneled' bit is set, it indicates the next-hop is
                                             a tunnel destination (the 'nexthop-ip' leaf is a far-end tunnel
                                             destination). The 'if-index' leaf will be 0 in this case.

                                             If the 'nh-is-lfa' bit is set, it indicates the next-hop is a
                                             loop-free alternate (LFA) of the next-hop immediately preceding
                                             this next-hop.

                                             If the 'nh-is-backup' bit is set, it indicates the next-hop is
                                             a BGP backup next-hop.

                                             If the 'nh-is-unnumbered' bit is set, it indicates the next-hop is
                                             unnumbered.";
                                    }

                                    leaf if-index {
                                        type uint32;
                                        description
                                            "This is the index of the egress interface where the
                                             next-hop resides.";
                                    }

                                    leaf if-vrtr-id {
                                        type uint32;
                                        description
                                            "Indicates the virtual router instance of the egress interface
                                             defined by 'if-index'.";
                                    }

                                    leaf metric {
                                        type uint32;
                                        description "Indicates the routing metric for the next-hop.";
                                    }

                                    leaf nexthop-ip {
                                        type types-sros:ip-address;
                                        description
                                            "Indicates the next-hop IP address of the route entry.

                                             The nexthop-ip is a tunnel far-end IP if the 'flags' leaf
                                             has the 'nh-is-tunneled' bit set.

                                             The nexthop-ip is an indirect IP if the 'flags' leaf has
                                             the 'nh-is-indirect' bit set.";
                                    }

                                    leaf nexthop-tunnel-id {
                                        type uint32;
                                        description
                                            "This indicates the next-hop tunnel ID when there are
                                             multiple tunnels to a destination or SDP ID.";
                                    }

                                    leaf nexthop-tunnel-type {
                                        type types-router:tunnel-type;
                                        description
                                            "This indicates the next-hop tunnel type if the
                                             'flags' leaf has the 'nh-is-tunneled' bit set.";
                                    }

                                    leaf nexthop-tunnel-type-instance {
                                        type uint8;
                                        description
                                            "This indicates the next-hop tunnel type instance if
                                             the 'flags' leaf has the 'nh-is-tunneled' bit set.";
                                    }

                                    leaf nexthop-label {
                                        type uint32 {
                                            range "0..1048575";
                                        }
                                        description "This is a VPRN or route label associated with the route entry.";
                                    }

                                    leaf forwarding-class {
                                        type types-sros:fc-name;
                                        description "This is the forwarding class associated with the next-hop.";
                                    }

                                    leaf priority {
                                        type types-router:nexthop-priority;
                                        description "This is the priority associated with packets to the next-hop.";
                                    }

                                    leaf source-class-index {
                                        type uint8 {
                                            range "1..255";
                                        }
                                        description "This is the source class index associated with the next-hop.";
                                    }

                                    leaf dest-class-index {
                                        type uint8 {
                                            range "1..255";
                                        }
                                        description "This is the destination class index associated with the next-hop.";
                                    }

                                    leaf weight {
                                        type types-router:ip-ecmp;
                                        description
                                            "The value of this leaf indicates the weight given to traffic using this
                                             particular next-hop among the ECMP set of next-hops.";
                                    }

                                } // list resolving-nexthop

                            } // list nexthop

                        } // list route

                    } // container ipv4

                    container ipv6 {

                        container statistics {

                            container bgp {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp

                            container bgp-vpn {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp-vpn

                            container direct {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container direct

                            container host {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container host

                            container isis {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container isis

                            container ospfv3 {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ospfv3

                            container static {

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container static

                        } // container statistics

                        list route {
                            key "ipv6-prefix";
                            description "This is the IPv6 multicast RPF table.";

                            leaf ipv6-prefix {
                                type types-sros:ipv6-prefix;
                                description "Indicates the IPv6 prefix for this route table entry.";
                            }

                            leaf age {
                                type uint32 {
                                    range "0..4294967295";
                                }
                                description "The number of seconds since this route was last updated.";
                            }

                            leaf instance {
                                type uint8;
                                description "The protocol instance the route belongs to.";
                            }

                            leaf flags {
                                type bits {
                                    bit sticky-flag                    { position 0; }
                                }
                                description
                                    "Bit flags that indicate different properties of this route.

                                     If the 'stickyFlag' bit is set, it indicates the ECMP
                                     sticky flag is set on this route.";
                            }

                            leaf preference {
                                type uint8;
                                description
                                    "Indicates the priority of this route versus the routes
                                     from different sources such as BGP or OSPF etc.";
                            }

                            leaf protocol {
                                type types-router:protocol-type;
                                description "Identifies the routing protocol.";
                            }

                            list nexthop {
                                key "nexthop-index";
                                description
                                    "This is the set of ECMP next-hops used by the
                                     route.";

                                leaf nexthop-index {
                                    type uint32;
                                    description "Index of ECMP next-hop or backup next-hop.";
                                }

                                leaf flags {
                                    type bits {
                                        bit nh-is-indirect                 { position 0; }
                                        bit nh-is-tunneled                 { position 1; }
                                        bit nh-is-lfa                      { position 2; }
                                        bit nh-is-backup                   { position 3; }
                                        bit nh-is-unnumbered               { position 4; }
                                    }
                                    description
                                        "Bit flags that indicate different properties of this next-hop.

                                         If the 'nh-is-indirect' bit is set, it indicates the next-hop is
                                         an indirect next-hop IP. An additional lookup will have to be
                                         made to map the indirect IP address to the resolving IP
                                         address(es) The 'if-index' leaf will be 0 in this case.

                                         If the 'nh-is-tunneled' bit is set, it indicates the next-hop is
                                         a tunnel destination (the 'nexthop-ip' leaf is a far-end tunnel
                                         destination). The 'if-index' leaf will be 0 in this case.

                                         If the 'nh-is-lfa' bit is set, it indicates the next-hop is a
                                         loop-free alternate (LFA) of the next-hop immediately preceding
                                         this next-hop.

                                         If the 'nh-is-backup' bit is set, it indicates the next-hop is
                                         a BGP backup next-hop.

                                         If the 'nh-is-unnumbered' bit is set, it indicates the next-hop is
                                         unnumbered.";
                                }

                                leaf if-index {
                                    type uint32;
                                    description
                                        "This is the index of the egress interface where the
                                         next-hop resides.";
                                }

                                leaf if-vrtr-id {
                                    type uint32;
                                    description
                                        "Indicates the virtual router instance of the egress interface
                                         defined by 'if-index'.";
                                }

                                leaf metric {
                                    type uint32;
                                    description "Indicates the routing metric for the next-hop.";
                                }

                                leaf nexthop-ip {
                                    type types-sros:ip-address;
                                    description
                                        "Indicates the next-hop IP address of the route entry.

                                         The nexthop-ip is a tunnel far-end IP if the 'flags' leaf
                                         has the 'nh-is-tunneled' bit set.

                                         The nexthop-ip is an indirect IP if the 'flags' leaf has
                                         the 'nh-is-indirect' bit set.";
                                }

                                leaf nexthop-tunnel-id {
                                    type uint32;
                                    description
                                        "This indicates the next-hop tunnel ID when there are
                                         multiple tunnels to a destination or SDP ID.";
                                }

                                leaf nexthop-tunnel-type {
                                    type types-router:tunnel-type;
                                    description
                                        "This indicates the next-hop tunnel type if the
                                         'flags' leaf has the 'nh-is-tunneled' bit set.";
                                }

                                leaf nexthop-tunnel-type-instance {
                                    type uint8;
                                    description
                                        "This indicates the next-hop tunnel type instance if
                                         the 'flags' leaf has the 'nh-is-tunneled' bit set.";
                                }

                                leaf nexthop-label {
                                    type uint32 {
                                        range "0..1048575";
                                    }
                                    description "This is a VPRN or route label associated with the route entry.";
                                }

                                leaf forwarding-class {
                                    type types-sros:fc-name;
                                    description "This is the forwarding class associated with the next-hop.";
                                }

                                leaf priority {
                                    type types-router:nexthop-priority;
                                    description "This is the priority associated with packets to the next-hop.";
                                }

                                leaf source-class-index {
                                    type uint8 {
                                        range "1..255";
                                    }
                                    description "This is the source class index associated with the next-hop.";
                                }

                                leaf dest-class-index {
                                    type uint8 {
                                        range "1..255";
                                    }
                                    description "This is the destination class index associated with the next-hop.";
                                }

                                leaf weight {
                                    type types-router:ip-ecmp;
                                    description
                                        "The value of this leaf indicates the weight given to traffic using this
                                         particular next-hop among the ECMP set of next-hops.";
                                }

                                list resolving-nexthop {
                                    key "resolving-nexthop-index";
                                    description "This is the set of ECMP resolving hops of an indirect next-hop";

                                    leaf resolving-nexthop-index {
                                        type uint32;
                                        description "Index of ECMP resolving next-hop or LFA next-hop.";
                                    }

                                    leaf flags {
                                        type bits {
                                            bit nh-is-indirect                 { position 0; }
                                            bit nh-is-tunneled                 { position 1; }
                                            bit nh-is-lfa                      { position 2; }
                                            bit nh-is-backup                   { position 3; }
                                            bit nh-is-unnumbered               { position 4; }
                                        }
                                        description
                                            "Bit flags that indicate different properties of this next-hop.

                                             If the 'nh-is-indirect' bit is set, it indicates the next-hop is
                                             an indirect next-hop IP. An additional lookup will have to be
                                             made to map the indirect IP address to the resolving IP
                                             address(es) The 'if-index' leaf will be 0 in this case.

                                             If the 'nh-is-tunneled' bit is set, it indicates the next-hop is
                                             a tunnel destination (the 'nexthop-ip' leaf is a far-end tunnel
                                             destination). The 'if-index' leaf will be 0 in this case.

                                             If the 'nh-is-lfa' bit is set, it indicates the next-hop is a
                                             loop-free alternate (LFA) of the next-hop immediately preceding
                                             this next-hop.

                                             If the 'nh-is-backup' bit is set, it indicates the next-hop is
                                             a BGP backup next-hop.

                                             If the 'nh-is-unnumbered' bit is set, it indicates the next-hop is
                                             unnumbered.";
                                    }

                                    leaf if-index {
                                        type uint32;
                                        description
                                            "This is the index of the egress interface where the
                                             next-hop resides.";
                                    }

                                    leaf if-vrtr-id {
                                        type uint32;
                                        description
                                            "Indicates the virtual router instance of the egress interface
                                             defined by 'if-index'.";
                                    }

                                    leaf metric {
                                        type uint32;
                                        description "Indicates the routing metric for the next-hop.";
                                    }

                                    leaf nexthop-ip {
                                        type types-sros:ip-address;
                                        description
                                            "Indicates the next-hop IP address of the route entry.

                                             The nexthop-ip is a tunnel far-end IP if the 'flags' leaf
                                             has the 'nh-is-tunneled' bit set.

                                             The nexthop-ip is an indirect IP if the 'flags' leaf has
                                             the 'nh-is-indirect' bit set.";
                                    }

                                    leaf nexthop-tunnel-id {
                                        type uint32;
                                        description
                                            "This indicates the next-hop tunnel ID when there are
                                             multiple tunnels to a destination or SDP ID.";
                                    }

                                    leaf nexthop-tunnel-type {
                                        type types-router:tunnel-type;
                                        description
                                            "This indicates the next-hop tunnel type if the
                                             'flags' leaf has the 'nh-is-tunneled' bit set.";
                                    }

                                    leaf nexthop-tunnel-type-instance {
                                        type uint8;
                                        description
                                            "This indicates the next-hop tunnel type instance if
                                             the 'flags' leaf has the 'nh-is-tunneled' bit set.";
                                    }

                                    leaf nexthop-label {
                                        type uint32 {
                                            range "0..1048575";
                                        }
                                        description "This is a VPRN or route label associated with the route entry.";
                                    }

                                    leaf forwarding-class {
                                        type types-sros:fc-name;
                                        description "This is the forwarding class associated with the next-hop.";
                                    }

                                    leaf priority {
                                        type types-router:nexthop-priority;
                                        description "This is the priority associated with packets to the next-hop.";
                                    }

                                    leaf source-class-index {
                                        type uint8 {
                                            range "1..255";
                                        }
                                        description "This is the source class index associated with the next-hop.";
                                    }

                                    leaf dest-class-index {
                                        type uint8 {
                                            range "1..255";
                                        }
                                        description "This is the destination class index associated with the next-hop.";
                                    }

                                    leaf weight {
                                        type types-router:ip-ecmp;
                                        description
                                            "The value of this leaf indicates the weight given to traffic using this
                                             particular next-hop among the ECMP set of next-hops.";
                                    }

                                } // list resolving-nexthop

                            } // list nexthop

                        } // list route

                    } // container ipv6

                } // container multicast

            } // container route-table

            container dhcp6 {
                description "DHCP6 statistics";

                container statistics {
                    description "DHCPv6 statistics";

                    list message {
                        key "type";
                        description "Counters for DHCPv6 messages per message type";

                        leaf type {
                            type enumeration {
                                enum "solicit"                      { value 1; }
                                enum "advertise"                    { value 2; }
                                enum "request"                      { value 3; }
                                enum "confirm"                      { value 4; }
                                enum "renew"                        { value 5; }
                                enum "rebind"                       { value 6; }
                                enum "reply"                        { value 7; }
                                enum "release"                      { value 8; }
                                enum "decline"                      { value 9; }
                                enum "reconfigure"                  { value 10; }
                                enum "info-request"                 { value 11; }
                                enum "relay-forward"                { value 12; }
                                enum "relay-reply"                  { value 13; }
                                enum "lease-query"                  { value 14; }
                                enum "lease-query-reply"            { value 15; }
                            }
                        }

                        leaf received {
                            type yang:counter32;
                            description "Number of packets received";
                        }

                        leaf transmitted {
                            type yang:counter32;
                            description "Number of packets transmitted";
                        }

                        leaf dropped {
                            type yang:counter32;
                            description "Number of packets dropped";
                        }

                        leaf last-cleared {
                            type yang:date-and-time;
                            description "Date and time when this drop reason counter was last reset";
                        }

                    } // list message

                    container dropped {
                        description "Counters for DHCPv6 messages per drop reason";

                        container none {
                            description "No DHCP6 drop reason given";

                            leaf counter {
                                type yang:counter32;
                                description "Number of packets dropped";
                            }

                            leaf last-cleared {
                                type yang:date-and-time;
                                description "Date and time when this drop reason counter was last reset";
                            }

                        } // container none

                        container source-operational-down {
                            description "DHCP6 operational state is not up on source interface";

                            leaf counter {
                                type yang:counter32;
                                description "Number of packets dropped";
                            }

                            leaf last-cleared {
                                type yang:date-and-time;
                                description "Date and time when this drop reason counter was last reset";
                            }

                        } // container source-operational-down

                        container destination-operational-down {
                            description "DHCP6 operational state is not up on destination interface";

                            leaf counter {
                                type yang:counter32;
                                description "Number of packets dropped";
                            }

                            leaf last-cleared {
                                type yang:date-and-time;
                                description "Date and time when this drop reason counter was last reset";
                            }

                        } // container destination-operational-down

                        container relay-reply-on-client-interface {
                            description "Relay reply message on client interface";

                            leaf counter {
                                type yang:counter32;
                                description "Number of packets dropped";
                            }

                            leaf last-cleared {
                                type yang:date-and-time;
                                description "Date and time when this drop reason counter was last reset";
                            }

                        } // container relay-reply-on-client-interface

                        container hop-count {
                            description "Hop Count limit reached";

                            leaf counter {
                                type yang:counter32;
                                description "Number of packets dropped";
                            }

                            leaf last-cleared {
                                type yang:date-and-time;
                                description "Date and time when this drop reason counter was last reset";
                            }

                        } // container hop-count

                        container bad-relayed-message {
                            description "Missing relay message option, or illegal message type";

                            leaf counter {
                                type yang:counter32;
                                description "Number of packets dropped";
                            }

                            leaf last-cleared {
                                type yang:date-and-time;
                                description "Date and time when this drop reason counter was last reset";
                            }

                        } // container bad-relayed-message

                        container client-interface-not-found {
                            description "Unable to determine destination client interface";

                            leaf counter {
                                type yang:counter32;
                                description "Number of packets dropped";
                            }

                            leaf last-cleared {
                                type yang:date-and-time;
                                description "Date and time when this drop reason counter was last reset";
                            }

                        } // container client-interface-not-found

                        container no-memory {
                            description "Out of memory";

                            leaf counter {
                                type yang:counter32;
                                description "Number of packets dropped";
                            }

                            leaf last-cleared {
                                type yang:date-and-time;
                                description "Date and time when this drop reason counter was last reset";
                            }

                        } // container no-memory

                        container no-global-prefix {
                            description "No global prefix on client interface";

                            leaf counter {
                                type yang:counter32;
                                description "Number of packets dropped";
                            }

                            leaf last-cleared {
                                type yang:date-and-time;
                                description "Date and time when this drop reason counter was last reset";
                            }

                        } // container no-global-prefix

                        container no-source-ip {
                            description "Unable to determine source IP address";

                            leaf counter {
                                type yang:counter32;
                                description "Number of packets dropped";
                            }

                            leaf last-cleared {
                                type yang:date-and-time;
                                description "Date and time when this drop reason counter was last reset";
                            }

                        } // container no-source-ip

                        container no-route-to-server {
                            description "No route to server";

                            leaf counter {
                                type yang:counter32;
                                description "Number of packets dropped";
                            }

                            leaf last-cleared {
                                type yang:date-and-time;
                                description "Date and time when this drop reason counter was last reset";
                            }

                        } // container no-route-to-server

                        container update-failed {
                            description "Updating the subscriber management backend failed, e.g. due to overload conditions";

                            leaf counter {
                                type yang:counter32;
                                description "Number of packets dropped";
                            }

                            leaf last-cleared {
                                type yang:date-and-time;
                                description "Date and time when this drop reason counter was last reset";
                            }

                        } // container update-failed

                        container rx-relay-forward-message {
                            description "Received relay forward message";

                            leaf counter {
                                type yang:counter32;
                                description "Number of packets dropped";
                            }

                            leaf last-cleared {
                                type yang:date-and-time;
                                description "Date and time when this drop reason counter was last reset";
                            }

                        } // container rx-relay-forward-message

                        container message-too-small {
                            description "Packet too small to contain valid DHCP6 message";

                            leaf counter {
                                type yang:counter32;
                                description "Number of packets dropped";
                            }

                            leaf last-cleared {
                                type yang:date-and-time;
                                description "Date and time when this drop reason counter was last reset";
                            }

                        } // container message-too-small

                        container message-not-for-server {
                            description "Server cannot respond to this message";

                            leaf counter {
                                type yang:counter32;
                                description "Number of packets dropped";
                            }

                            leaf last-cleared {
                                type yang:date-and-time;
                                description "Date and time when this drop reason counter was last reset";
                            }

                        } // container message-not-for-server

                        container no-server-id {
                            description "No server ID option in message from server";

                            leaf counter {
                                type yang:counter32;
                                description "Number of packets dropped";
                            }

                            leaf last-cleared {
                                type yang:date-and-time;
                                description "Date and time when this drop reason counter was last reset";
                            }

                        } // container no-server-id

                        container no-client-id {
                            description "No client ID option in message from client";

                            leaf counter {
                                type yang:counter32;
                                description "Number of packets dropped";
                            }

                            leaf last-cleared {
                                type yang:date-and-time;
                                description "Date and time when this drop reason counter was last reset";
                            }

                        } // container no-client-id

                        container server-id-in-client-message {
                            description "Server ID option in client message";

                            leaf counter {
                                type yang:counter32;
                                description "Number of packets dropped";
                            }

                            leaf last-cleared {
                                type yang:date-and-time;
                                description "Date and time when this drop reason counter was last reset";
                            }

                        } // container server-id-in-client-message

                        container wrong-server-id {
                            description "Server DUID in client message does not match ours";

                            leaf counter {
                                type yang:counter32;
                                description "Number of packets dropped";
                            }

                            leaf last-cleared {
                                type yang:date-and-time;
                                description "Date and time when this drop reason counter was last reset";
                            }

                        } // container wrong-server-id

                        container unicast {
                            description "Client sent message to unicast while not allowed";

                            leaf counter {
                                type yang:counter32;
                                description "Number of packets dropped";
                            }

                            leaf last-cleared {
                                type yang:date-and-time;
                                description "Date and time when this drop reason counter was last reset";
                            }

                        } // container unicast

                        container invalid-source-address {
                            description "Client sent message with illegal source IP, e.g. client uses a source IP from a prefix that is not configured on the interface";

                            leaf counter {
                                type yang:counter32;
                                description "Number of packets dropped";
                            }

                            leaf last-cleared {
                                type yang:date-and-time;
                                description "Date and time when this drop reason counter was last reset";
                            }

                        } // container invalid-source-address

                        container prefix-delegation-message-not-supported {
                            description "Client message type not supported in prefix delegation";

                            leaf counter {
                                type yang:counter32;
                                description "Number of packets dropped";
                            }

                            leaf last-cleared {
                                type yang:date-and-time;
                                description "Date and time when this drop reason counter was last reset";
                            }

                        } // container prefix-delegation-message-not-supported

                        container number-of-addresses-exceeded {
                            description "Number of addresses or prefixes exceeds allowed maximum in message";

                            leaf counter {
                                type yang:counter32;
                                description "Number of packets dropped";
                            }

                            leaf last-cleared {
                                type yang:date-and-time;
                                description "Date and time when this drop reason counter was last reset";
                            }

                        } // container number-of-addresses-exceeded

                        container client-mac-not-resolved {
                            description "Unable to resolve client's mac address";

                            leaf counter {
                                type yang:counter32;
                                description "Number of packets dropped";
                            }

                            leaf last-cleared {
                                type yang:date-and-time;
                                description "Date and time when this drop reason counter was last reset";
                            }

                        } // container client-mac-not-resolved

                        container invalid-assigned-address {
                            description "The client was assigned an illegal address, e.g. the address is not routable or conflicts with other addresses";

                            leaf counter {
                                type yang:counter32;
                                description "Number of packets dropped";
                            }

                            leaf last-cleared {
                                type yang:date-and-time;
                                description "Date and time when this drop reason counter was last reset";
                            }

                        } // container invalid-assigned-address

                        container illegal-message-encoding {
                            description "The message encoding is incorrect";

                            leaf counter {
                                type yang:counter32;
                                description "Number of packets dropped";
                            }

                            leaf last-cleared {
                                type yang:date-and-time;
                                description "Date and time when this drop reason counter was last reset";
                            }

                        } // container illegal-message-encoding

                        container routed-central-office-message-not-supported {
                            description "Client message type not supported on rco (routed central office) interfaces";

                            leaf counter {
                                type yang:counter32;
                                description "Number of packets dropped";
                            }

                            leaf last-cleared {
                                type yang:date-and-time;
                                description "Date and time when this drop reason counter was last reset";
                            }

                        } // container routed-central-office-message-not-supported

                        container ia-in-info-request {
                            description "Info request holds IA options";

                            leaf counter {
                                type yang:counter32;
                                description "Number of packets dropped";
                            }

                            leaf last-cleared {
                                type yang:date-and-time;
                                description "Date and time when this drop reason counter was last reset";
                            }

                        } // container ia-in-info-request

                        container no-ia-in-client-message {
                            description "Client message holds no IA options";

                            leaf counter {
                                type yang:counter32;
                                description "Number of packets dropped";
                            }

                            leaf last-cleared {
                                type yang:date-and-time;
                                description "Date and time when this drop reason counter was last reset";
                            }

                        } // container no-ia-in-client-message

                        container no-address-in-confirm-message {
                            description "No addresses in client confirm message";

                            leaf counter {
                                type yang:counter32;
                                description "Number of packets dropped";
                            }

                            leaf last-cleared {
                                type yang:date-and-time;
                                description "Date and time when this drop reason counter was last reset";
                            }

                        } // container no-address-in-confirm-message

                        container no-relay-servers {
                            description "No relay servers configured";

                            leaf counter {
                                type yang:counter32;
                                description "Number of packets dropped";
                            }

                            leaf last-cleared {
                                type yang:date-and-time;
                                description "Date and time when this drop reason counter was last reset";
                            }

                        } // container no-relay-servers

                        container host-lockout {
                            description "Blocked by host lockout";

                            leaf counter {
                                type yang:counter32;
                                description "Number of packets dropped";
                            }

                            leaf last-cleared {
                                type yang:date-and-time;
                                description "Date and time when this drop reason counter was last reset";
                            }

                        } // container host-lockout

                        container no-link-address {
                            description "No link address available";

                            leaf counter {
                                type yang:counter32;
                                description "Number of packets dropped";
                            }

                            leaf last-cleared {
                                type yang:date-and-time;
                                description "Date and time when this drop reason counter was last reset";
                            }

                        } // container no-link-address

                        container dropped-by-python {
                            description "Either explicit or because of a Python failure";

                            leaf counter {
                                type yang:counter32;
                                description "Number of packets dropped";
                            }

                            leaf last-cleared {
                                type yang:date-and-time;
                                description "Date and time when this drop reason counter was last reset";
                            }

                        } // container dropped-by-python

                        container invalid-forced-server {
                            description "The forced server configured in the local-user-database is not configured on the interface";

                            leaf counter {
                                type yang:counter32;
                                description "Number of packets dropped";
                            }

                            leaf last-cleared {
                                type yang:date-and-time;
                                description "Date and time when this drop reason counter was last reset";
                            }

                        } // container invalid-forced-server

                        container rx-on-srrp-backup-interface {
                            description "Packet ignored on SRRP backup interface";

                            leaf counter {
                                type yang:counter32;
                                description "Number of packets dropped";
                            }

                            leaf last-cleared {
                                type yang:date-and-time;
                                description "Date and time when this drop reason counter was last reset";
                            }

                        } // container rx-on-srrp-backup-interface

                        container dhcp-transaction-not-found {
                            description "A DHCP transaction is not found";

                            leaf counter {
                                type yang:counter32;
                                description "Number of packets dropped";
                            }

                            leaf last-cleared {
                                type yang:date-and-time;
                                description "Date and time when this drop reason counter was last reset";
                            }

                        } // container dhcp-transaction-not-found

                        container retail-interface-not-found {
                            description "Retail interface is not found";

                            leaf counter {
                                type yang:counter32;
                                description "Number of packets dropped";
                            }

                            leaf last-cleared {
                                type yang:date-and-time;
                                description "Date and time when this drop reason counter was last reset";
                            }

                        } // container retail-interface-not-found

                        container dropped-by-dhcp-filter {
                            description "Packet dropped by DHCP filter";

                            leaf counter {
                                type yang:counter32;
                                description "Number of packets dropped";
                            }

                            leaf last-cleared {
                                type yang:date-and-time;
                                description "Date and time when this drop reason counter was last reset";
                            }

                        } // container dropped-by-dhcp-filter

                        container authentication-failed {
                            description "The packet was rejected by authentication";

                            leaf counter {
                                type yang:counter32;
                                description "Number of packets dropped";
                            }

                            leaf last-cleared {
                                type yang:date-and-time;
                                description "Date and time when this drop reason counter was last reset";
                            }

                        } // container authentication-failed

                        container invalid-forced-source-address {
                            description "Forced source address not configured on this vrf";

                            leaf counter {
                                type yang:counter32;
                                description "Number of packets dropped";
                            }

                            leaf last-cleared {
                                type yang:date-and-time;
                                description "Date and time when this drop reason counter was last reset";
                            }

                        } // container invalid-forced-source-address

                    } // container dropped

                } // container statistics

            } // container dhcp6

            uses state-svc-vprn-dhcp-server;
            uses state-svc-vprn-isis;
            uses state-svc-vprn-msdp;
            uses state-svc-vprn-ospf;
            uses state-svc-vprn-ospf3;
            uses state-svc-vprn-radius;
            uses state-svc-vprn-rip;
            uses state-svc-vprn-ripng;
            uses state-svc-vprn-sub-if-subscriber-interface;
            uses state-svc-vprn-twamp-light;
            uses state-svc-vprn-vdo-if-video-interface;
        } // list vprn

    } // grouping state-svc-vprn

}
