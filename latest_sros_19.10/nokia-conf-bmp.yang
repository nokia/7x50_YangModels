submodule nokia-conf-bmp {

    yang-version "1.1";

    belongs-to nokia-conf { prefix "conf"; }

    import nokia-sros-yang-extensions     { prefix "sros-ext"; }
    import nokia-types-sros               { prefix "types-sros"; }

    include nokia-conf-system;
    include nokia-conf-system-security;

    sros-ext:sros-major-release "rel19";

    organization "Nokia";

    contact
        "Nokia SR OS Support
         Web: <http://www.nokia.com>";

    description
        "Nokia YANG Data model to configure BGP Monitoring Protocol on SR OS based routers.

         Copyright 2016 Nokia. All rights reserved. Reproduction of this document
         is authorized on the condition that the foregoing copyright notice is included.

         This nokia-conf-bmp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-05-13";

    grouping conf-bmp {
        container bmp {
            description "Enter the bmp context";

            leaf admin-state {
                type types-sros:admin-state;
                default "disable";
                description "Administrative state of the BMP operation";
            }

            container collector {
                description "Enter the collector context";

                leaf admin-state {
                    type types-sros:admin-state;
                    sros-ext:auto-restart-to-modify;
                    default "disable";
                    description "Administrative state of the BMP collector.";
                }

                container connection {
                    sros-ext:auto-restart-to-modify;
                    description "Enter the connection context";

                    container ipv4 {
                        sros-ext:auto-restart-to-modify;
                        description "Enter the ipv4 context";

                        leaf address {
                            type types-sros:ipv4-unicast-address;
                            sros-ext:auto-restart-to-modify;
                            description "IPv4 address.";
                        }

                        leaf port {
                            type types-sros:tcp-udp-port-non-zero;
                            sros-ext:auto-restart-to-modify;
                            default "4210";
                            description "IPv4 TCP port.";
                        }

                    } // container ipv4

                    container ipv6 {
                        sros-ext:auto-restart-to-modify;
                        description "Enter the ipv6 context";

                        leaf address {
                            type types-sros:ipv6-unicast-address;
                            sros-ext:auto-restart-to-modify;
                            description "IPv6 address.";
                        }

                        leaf port {
                            type types-sros:tcp-udp-port-non-zero;
                            sros-ext:auto-restart-to-modify;
                            default "4210";
                            description "IPv6 TCP port.";
                        }

                    } // container ipv6

                } // container connection

            } // container collector

            list station {
                key "name";
                max-elements 8;
                description "Enter the station list instance";

                leaf name {
                    type types-sros:named-item;
                    description "BMP monitoring station name";
                }

                leaf description {
                    type types-sros:description;
                    description "Text description";
                }

                leaf admin-state {
                    type types-sros:admin-state;
                    default "disable";
                    description "Administrative state of the BMP monitoring station";
                }

                leaf initiation-message {
                    type string {
                        length "1..255";
                    }
                    description "Free form initiation message for a type 0 TLV to be sent to the BMP monitoring station";
                }

                leaf stats-report-interval {
                    type types-sros:time-duration {
                        range "15..65535";
                    }
                    units "seconds";
                    description "Frequency of statistics reporting messages sent to the BMP monitoring station";
                }

                leaf report-local-routes {
                    type boolean;
                    default "false";
                    description "Allow local route reporting to the BMP monitoring station";
                }

                container connection {
                    description "Enter the connection context";

                    leaf connect-retry {
                        type types-sros:time-duration {
                            range "1..65535";
                        }
                        units "seconds";
                        default "120";
                        description "Maximum time between connection attempts";
                    }

                    leaf local-address {
                        type types-sros:ip-unicast-address;
                        description "Local IP address to communicate with the BMP monitoring station";
                    }

                    leaf router-instance {
                        type string;
                        default "Base";
                        description "Router instance used to reach the BMP station";
                    }

                    container station-address {
                        description "Enter the station-address context";

                        leaf ip-address {
                            type types-sros:ip-unicast-address;
                            description "IP address of the BMP monitoring station";
                        }

                        leaf port {
                            type types-sros:tcp-udp-port-non-zero;
                            description "Port of the BMP monitoring station";
                        }

                    } // container station-address

                    container tcp-keepalive {
                        description "Enter the tcp-keepalive context";

                        leaf admin-state {
                            type types-sros:admin-state;
                            default "disable";
                            description "Administrative state of TCP keepalive";
                        }

                        leaf keep-idle {
                            type types-sros:time-duration {
                                range "1..100000";
                            }
                            units "seconds";
                            default "600";
                            description "Time until the first TCP keepalive probe is sent.";
                        }

                        leaf keep-interval {
                            type types-sros:time-duration {
                                range "1..100000";
                            }
                            units "seconds";
                            default "15";
                            description "Time between two TCP keepalive probes";
                        }

                        leaf keep-count {
                            type uint32 {
                                range "3..100";
                            }
                            default "4";
                            description "Number of missed keepalives before the TCP connection is declared down";
                        }

                    } // container tcp-keepalive

                } // container connection

                container family {
                    description "Enter the family context";

                    leaf ipv4 {
                        type boolean;
                        default "true";
                        description "Support IPv4 address family";
                    }

                    leaf ipv6 {
                        type boolean;
                        default "false";
                        description "Support IPv6 address family";
                    }

                    leaf label-ipv4 {
                        type boolean;
                        default "false";
                        description "Support labeled IPv4 address family";
                    }

                    leaf label-ipv6 {
                        type boolean;
                        default "false";
                        description "Support labeled IPv6 address family";
                    }

                    leaf mcast-ipv4 {
                        type boolean;
                        default "false";
                        description "Support IPv4 multicast address family";
                    }

                    leaf mcast-ipv6 {
                        type boolean;
                        default "false";
                        description "Support IPv6 multicast address family";
                    }

                    leaf vpn-ipv4 {
                        type boolean;
                        default "false";
                        description "Support VPN IPv4 address family";
                    }

                    leaf vpn-ipv6 {
                        type boolean;
                        default "false";
                        description "Support VPN IPv6 address family";
                    }

                    leaf mcast-vpn-ipv4 {
                        type boolean;
                        default "false";
                        description "Support IPv4 VPN multicast address family";
                    }

                    leaf mcast-vpn-ipv6 {
                        type boolean;
                        default "false";
                        description "Support IPv6 VPN multicast address family";
                    }

                    leaf evpn {
                        type boolean;
                        default "false";
                        description "Support EVPN address family";
                    }

                    leaf l2-vpn {
                        type boolean;
                        default "false";
                        description "Support L2 VPN address family";
                    }

                } // container family

            } // list station

        } // container bmp

    } // grouping conf-bmp

}
