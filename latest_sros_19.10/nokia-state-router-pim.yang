submodule nokia-state-router-pim {

    yang-version "1.1";

    belongs-to nokia-state { prefix "state"; }

    import ietf-yang-types                { prefix "yang"; }
    import nokia-sros-yang-extensions     { prefix "sros-ext"; }
    import nokia-types-pim                { prefix "types-pim"; }
    import nokia-types-services           { prefix "types-services"; }
    import nokia-types-sros               { prefix "types-sros"; }


    sros-ext:sros-major-release "rel19";

    organization "Nokia";

    contact
        "Nokia SR OS Support
         Web: <http://www.nokia.com>";

    description
        "Nokia YANG Data model with operational state for Base router PIM protocol on SR OS based routers.

         Copyright 2016 Nokia. All rights reserved. Reproduction of this document
         is authorized on the condition that the foregoing copyright notice is included.

         This nokia-state-router-pim YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-04-20";

    grouping state-router-pim {
        container pim {
            description "Enter the pim context";

            leaf maximum-mdts {
                type int32;
                description
                    "Maximum number of Multicast Distribution Trees (MDTs) that can
                     be configured on the system.";
            }

            leaf multistream-spmsi {
                type boolean;
                description
                    "The value of this object specifies whether multistream SPMSI is
                     configured on this router.";
            }

            leaf oper-state {
                type types-sros:oper-state;
                description
                    "The value of this object indicates the operational
                     state of the PIM protocol.";
            }

            leaf mc-ecmp-last-rebalance-time {
                type types-sros:date-time;
                description
                    "The value of this object indicates the time when the last re-balancing
                     occurred if the value of mc-ecmp-rebalance-inprogress is 'false'.";
            }

            leaf mc-ecmp-next-balance-time {
                type uint32;
                units "seconds";
                description
                    "The value of this object indicates how much time is remaining until
                     the next rebalance would occur.";
            }

            leaf mc-ecmp-rebalance-inprogress {
                type boolean;
                description "Whether or not multicast ECMP re-balancing is currently in progress.";
            }

            leaf mc-ecmp-rebalance-type {
                type enumeration {
                    enum "triggered"                    { value 1; }
                    enum "operator-forced"              { value 2; }
                }
                description "The value of this object indicates the type of ECMP rebalance.";
            }

            container ipv4 {
                description "Enter the ipv4 context";

                list sg {
                    key "group-address source-address";
                    description
                        "Each entry represents a source address from which receivers are
                         interested or not interested in receiving multicast traffic.";

                    leaf group-address {
                        type types-sros:ipv4-multicast-address;
                        description
                            "The IP multicast group address for which this entry contains information.
                             If the source-type is 'starStarRP', the value of this object will
                             be zero and source-address will contain the address of the RP.";
                    }

                    leaf source-address {
                        type types-sros:ipv4-address;
                        description
                            "The source address for which this entry contains information.
                             If source-type is 'starG', the value of this object will be zero.
                             If source-type is 'starstarRP', the value of this object will be address of the RP.";
                    }

                    leaf source-type {
                        type enumeration {
                            enum "star-star-rp"                 { value 0; }
                            enum "star-g"                       { value 1; }
                            enum "sg"                           { value 2; }
                        }
                        description "The type of this entry.";
                    }

                    leaf sg-state {
                        type enumeration {
                            enum "none"                         { value 0; }
                            enum "active"                       { value 1; }
                            enum "standby"                      { value 2; }
                        }
                        description "The current state of the (S,G).";
                    }

                    leaf rp-address {
                        type types-sros:ip-address;
                        description "The address of the Rendezvous Point(RP).";
                    }

                    leaf advertising-router {
                        type types-sros:ip-address;
                        description "The router address that advertised the route to the source indicated by source-address.";
                    }

                    leaf downstream-rpfv-neighbor {
                        type types-sros:ip-address;
                        description "The address of the downstream RPF vector neighbor.";
                    }

                    leaf downstream-rpfv-type {
                        type types-pim:rpfv-type;
                        description "The downstream RPF vector type.";
                    }

                    leaf downstream-rpfv-rd {
                        type types-services:state-vpn-rd;
                        description "The downstream RPF vector Route Distinguisher.";
                    }

                    leaf downstream-rpfv-proxy {
                        type types-sros:ip-address;
                        description "The address of the downstream RPF vector proxy.";
                    }

                    leaf upstream-rpfv-neighbor {
                        type types-sros:ip-address;
                        description "The address of the upstream RPF vector neighbor.";
                    }

                    leaf rpfv-flags {
                        type bits {
                            bit upstream-neighbor-no-join-attribute { position 0; }
                        }
                        description
                            "The state of the rpf-vectors.

                             When the bit 'upstream-neighbor-no-join-attribute' is set, it
                             indicates that the upstream neighbor towards the rpf-vector
                             proxy does not support join-attributes.";
                    }

                    leaf upstream-rpfv-type {
                        type types-pim:rpfv-type;
                        description "The upstream RPF vector type.";
                    }

                    leaf upstream-rpfv-rd {
                        type types-services:state-vpn-rd;
                        description "The upstream RPF vector Route Distinguisher.";
                    }

                    leaf upstream-rpfv-proxy {
                        type types-sros:ip-address;
                        description "The address of the upstream RPF vector proxy.";
                    }

                    leaf source-flags {
                        type bits {
                            bit spt-bit                        { position 0; }
                            bit rpt-prune-desired              { position 1; }
                        }
                        description
                            "The information about the state of the entry

                             This object is applicable only for (S,G) entries,i.e., when
                             source-type is 'sg'.

                             The (S,G) 'spt-bit' is used to distinguish whether to forward on
                             (*,*,RP) or (*,G) or on (S,G) state. It is updated when the (S,G)
                             data comes on the RPF interface towards the source.
                             'rpt-prune-desired' is set according to the PruneDesired(S,G,rpt)
                             algorithm.";
                    }

                    leaf mode {
                        type enumeration {
                            enum "none"                         { value 0; }
                            enum "sparse"                       { value 1; }
                            enum "dense"                        { value 2; }
                        }
                        description "The mode of operation for the (S,G).";
                    }

                    leaf mrib-nh-address {
                        type types-sros:ip-address-with-zone;
                        description "The next hop address towards the RP.";
                    }

                    leaf standby-rpf-neighbor-address {
                        type types-sros:ip-address;
                        description
                            "The address of the secondary RPF neighbor

                             The value of this object is applicable only when the value of the
                             object 'configure service vprn mvpn umh-selection' is set to 'tunnel-status'
                             indicating that the MVPN is configured with source redundancy.

                             When MVPN is configured with source redundancy, MVPN is capable of
                             receiving traffic from two different PE's for the same source.";
                    }

                    leaf mrib-source-flags {
                        type types-pim:mrib-source-flags;
                        description
                            "The MRIB information about the source. If the entry is of type 'starG'
                             or 'starStarRP', it will contain information about the RP for this group.";
                    }

                    leaf standby-mrib-source-flags {
                        type types-pim:mrib-source-flags;
                        description
                            "The MRIB information about the source reachable through the standby RPF
                             interface.

                             This object is applicable only for (S,G) entries,i.e., when
                             source-type is 'sg'.";
                    }

                    leaf keepalive-timer {
                        type uint32;
                        units "seconds";
                        description
                            "Is applicable only for (S,G) entries. The (S,G) Keepalive Timer is updated by
                             data being forwarded using this (S,G) forwarding state. It is used to keep (S,G)
                             state alive in the absence of explicit (S,G) Joins.";
                    }

                    leaf prune-limit-timer {
                        type uint32;
                        units "seconds";
                        description "The time until which no prunes will be sent upstream.";
                    }

                    leaf graft-retry-timer {
                        type uint32;
                        units "seconds";
                        description
                            "The time interval between which two grafts are sent upstream and no ack is
                             received from the upstream router.";
                    }

                    leaf up-time {
                        type uint32;
                        units "seconds";
                        description "The time since this source group entry got created.";
                    }

                    leaf resolved-by {
                        type enumeration {
                            enum "none"                         { value 0; }
                            enum "multicast-route-table"        { value 1; }
                            enum "unicast-route-table"          { value 2; }
                        }
                        description
                            "Which unicast routing table was used to resolve this source group entry.

                             The value of this object will be 'multicastRouteTable' if the
                             source or Rendezvous Point (RP) is resolved by the multicast-unicast
                             route table. The value of this object will be 'unicastRouteTable' if
                             the source or Rendezvous Point (RP) is resolved by the unicast
                             route table. The value will be 'none' if the source or RP is
                             unresolved.";
                    }

                    leaf upstream-jp-state {
                        type enumeration {
                            enum "not-joined"                   { value 0; }
                            enum "joined"                       { value 1; }
                            enum "pruned"                       { value 2; }
                            enum "forwarding"                   { value 3; }
                            enum "ack-pending"                  { value 4; }
                        }
                        description
                            "The upstream Join-Prune state. This is a result of sending PIM Join-Prune
                             messages towards the source or the RP.";
                    }

                    leaf upstream-jp-timer {
                        type uint32;
                        units "seconds";
                        description
                            "The time remaining before the router sends another Join message to it's
                             upstream neighbor.";
                    }

                    leaf upstream-rpt-jp-state {
                        type enumeration {
                            enum "not-joined-star-g"            { value 0; }
                            enum "not-pruned"                   { value 1; }
                            enum "pruned"                       { value 2; }
                        }
                        description
                            "The upstream RPT Join-Prune state. (S,G,rpt) Joins and Prunes are (S,G) Joins or
                             Prunes sent on the RP tree with the RPT bit set, either to modify the results of
                             (*,G) Joins, or to override the behavior of other upstream LAN peers.";
                    }

                    leaf upstream-rpt-override-timer {
                        type uint32;
                        units "seconds";
                        description
                            "The delay to triggered Join(S,G,rpt) messages to prevent implosions of triggered
                             messages.

                             If non-zero, it means that the router was in 'not-pruned' state and it saw a
                             Prune(S,G,rpt) message being sent to RPF'(S,G,rpt).

                             If the router sees a Join(S,G,rpt) override message being sent by
                             some other router on the LAN while the timer is still non-zero,
                             it simply cancels the override timer. If it does not see a
                             Join(S,G,rpt) message, then on expiry of the override timer, it
                             sends it's own Join(S,G,rpt) message to RPF'(S,G,rpt). A similar
                             scenario exists when RPF'(S,G,rpt) changes to become equal to
                             RPF'(*,G).";
                    }

                    leaf standby-upstream-jp-state {
                        type enumeration {
                            enum "not-joined"                   { value 0; }
                            enum "joined"                       { value 1; }
                        }
                        description
                            "The standby RPF Join-Prune state.

                             This object is applicable only for (S,G) entries,i.e., when
                             source-type is 'sg'.";
                    }

                    leaf standby-upstream-jp-timer {
                        type uint32;
                        units "seconds";
                        description
                            "The time remaining before the router sends another Join message to it's
                             upstream neighbor reachable through the standby RPF interface.

                             This object is applicable only for (S,G) entries,i.e., when
                             source-type is 'sg'.";
                    }

                    leaf register-state {
                        type enumeration {
                            enum "no-info"                      { value 0; }
                            enum "join"                         { value 1; }
                            enum "join-pending"                 { value 2; }
                            enum "prune"                        { value 3; }
                            enum "null-join"                    { value 4; }
                        }
                        description
                            "The register state. The register state is kept at the source DR. When the host
                             starts sending multicast packets and if there are no entries
                             programmed for that group, the source DR sends a Register packet
                             to the RP(G). Register state transition happen based on the register
                             stop timer and the response received from the RP.";
                    }

                    leaf register-stop-timer {
                        type uint32;
                        units "seconds";
                        description
                            "The time remaining before the register-state might transition
                             to a different state. This timer has a non-zero value when the
                             value of register-state is not 'noInfo'.";
                    }

                    leaf register-from-anycast-rp {
                        type boolean;
                        description
                            "Whether a register message for this source  group combination
                             was received from the anycast RP and not from the designated
                             router connected to the source. It  is not applicable when the value of
                             source-type is starStarRP or starG.";
                    }

                    leaf rpf-neighbor-address {
                        type types-sros:ip-address;
                        description "The address of the RPF neighbor.";
                    }

                    leaf rpf-neighbor-interface-name {
                        type string;
                        description "The router's interface index on which the RPF neighbor exists.";
                    }

                    leaf standby-rpf-neighbor-interface-name {
                        type string;
                        description
                            "The router's interface index on which the secondary RPF neighbor exists.

                             The value of this object is applicable only when the value of the
                             object 'configure service vprn mvpn umh-selection' is set to 'tunnel-status'
                             indicating that the MVPN is configured with source redundancy.";
                    }

                    leaf spmsi-rpf-neighbor-interface-name {
                        type string;
                        description
                            "In an MVPN scenario: The router's SPMSI interface index, if any, on which the RPF
                             neighbor exists.";
                    }

                    leaf inherited-outgoing-interface-count {
                        type yang:gauge32;
                        description
                            "The number of interfaces in the inherited outgoing interface list. An 'inherited'
                             list inherits state from other types.";
                    }

                    leaf s-g-rpt-prune-interface-count {
                        type yang:gauge32;
                        description "The number of interfaces on which the router received (S,G,Rpt) prunes.";
                    }

                    leaf spt-switchover-threshold {
                        type uint32;
                        units "kilobps";
                        description
                            "The configured threshold in kilobits per second(kbps) for the group to which
                             this (S,G) belongs.  For a group G configured with a threshold,
                             switchover to SPT for an (S,G) is attempted only if the (S,G)'s rate
                             exceeds this configured threshold.";
                    }

                    leaf ecmp-optional-threshold {
                        type uint32 {
                            range "0..7";
                        }
                        description "The optional threshold value for ECMP balancing.";
                    }

                    leaf administrative-bandwidth {
                        type yang:gauge32 {
                            range "0..40000000";
                        }
                        units "kilobps";
                        description
                            "The administrative bandwidth in kilobits per second(kbps) for the group to which
                             this (S,G) belongs.";
                    }

                    leaf rpt-rpf-neighbor-address {
                        type types-sros:ip-address;
                        description "The address of the RPF neighbor on the RPT.";
                    }

                    leaf immediate-outgoing-interface-count {
                        type yang:gauge32;
                        description
                            "The number of interfaces in the immediate outgoing interface list. An outgoing
                             list can be 'immediate' if it is built directly from the state of
                             the relevant type as indicated by source-type.";
                    }

                    leaf inherited-rpt-outgoing-interface-count {
                        type yang:gauge32;
                        description "The number of interfaces in the inherited outgoing interface list for (S,G,Rpt).";
                    }

                    leaf local-rx-include-interface-count {
                        type yang:gauge32;
                        description
                            "The number of interfaces in the local membership include interface list. Local
                             membership is the result of the local membership mechanism (MLD)
                             running on a interface. Include list contains interfaces which are
                             interested in receiving multicast traffic for this source group entry.";
                    }

                    leaf local-rx-exclude-interface-count {
                        type yang:gauge32;
                        description
                            "The number of interfaces in the local membership exclude interface list. Local
                             membership is the result of the local membership mechanism (MLD)
                             running on the interface. Exclude list contains interfaces which are
                             not interested in receiving multicast traffic for this source group
                             entry.";
                    }

                    leaf join-or-prune-interface-count {
                        type yang:gauge32;
                        description
                            "The number of interfaces on which the router received a Join or Prune message for
                             this source group combination.";
                    }

                    leaf lost-assert-interface-count {
                        type yang:gauge32;
                        description
                            "The number of interfaces on which the router lost assert for this source group
                             combination.";
                    }

                    leaf current-forwarding-rate {
                        type yang:counter64;
                        units "bps";
                        description
                            "The current forwarding rate being used by a source group(S,G) entry or
                             (*,G) entry, where * means any source entry, for the traffic in bits
                             per second(bps). This forwarding rate is calculated before ingress
                             QoS policing or shaping is applied.";
                    }

                    list group-interface {
                        key "sap forwarding-service group-interface-name";
                        description "List of the PIM enabled group-interfaces for an entry in the sg list.";

                        leaf sap {
                            type types-sros:sap;
                            description "SAP identifier.";
                        }

                        leaf forwarding-service {
                            type types-services:service-name;
                            description
                                "Specifies the forwarding service ID for a group-interface in a retailer
                                 context.";
                        }

                        leaf group-interface-name {
                            type types-sros:interface-name;
                            description
                                "The unique value which identifies this group-interface of this virtual
                                 router in the system. This field provides an identifier for
                                 virtual router interfaces similar to the ifIndex values used in the
                                 mib-2 interfaces table for physical interfaces.

                                 The values can be reused for different virtual routers, but are unique within
                                 those entries with the same vrtr-id.

                                 The value for each virtual interface must remain constant at least from
                                 one re-initialization of the system management processor to the next.";
                        }

                        leaf list-flags {
                            type types-pim:sg-flags;
                            description "The different lists that this group-interface belongs to.";
                        }

                    } // list group-interface

                    list host {
                        key "host-address";
                        description "List of PIM enabled hosts and their states for each entry in the sg list.";

                        leaf host-address {
                            type types-sros:ipv4-unicast-address;
                            description
                                "The IP multicast host address for which this entry contains information.
                                 If the ../type is 'star-star-rp', the value of this object will
                                 be zero and host-address will contain the address of the RP.";
                        }

                        leaf host-flags {
                            type types-pim:sg-flags;
                            description "The different lists that this host belongs to.";
                        }

                    } // list host

                    list interface {
                        key "interface-name";
                        description "List of the PIM enabled interfaces for an entry in sg list.";

                        leaf interface-name {
                            type types-sros:interface-name;
                            description "Router interface name.";
                        }

                        leaf interface-flags {
                            type types-pim:sg-flags;
                            description "Set of lists to which this interface belongs";
                        }

                        leaf spmsi-interface-name {
                            type string;
                            description
                                "In an MVPN scenario: The router's SPMSI interface index, if any, corresponding to
                                 the outgoing IPMSI interface.";
                        }

                    } // list interface

                    container statistics {
                        description
                            "Statistics for the entries in the sg list. These statistics are
                             collected by the forwarding engine.";

                        leaf forwarded-packets {
                            type yang:counter64;
                            description
                                "The number of multicast packets that were forwarded to the interfaces in the
                                 outgoing interface list. 'display router/(service vprn) pim ipv4/6 sg interface' lists all the
                                 interfaces in the outgoing interface list.";
                        }

                        leaf discarded-packets {
                            type yang:counter64;
                            description
                                "The number of multicast packets that matched this source group entry but were
                                 discarded. For (S,G) entries, if the traffic is getting forwarded on
                                 the SPT, the packets arriving from the RPT will be discarded.";
                        }

                        leaf rpf-mismatches {
                            type yang:counter64;
                            description
                                "The number of multicast packets that matched this source group entry
                                 but they did not arrive on the interface indicated by
                                 'display router/(service vprn) pim ipv4/6 sg rpf-neighbor-interface-name'.";
                        }

                        leaf forwarded-octets {
                            type yang:counter64;
                            description
                                "The number of multicast octets that were forwarded to the interfaces in the
                                 outgoing interface list. 'display router/(service vprn) pim ipv4/6 sg interface' lists all the
                                 interfaces in the outgoing interface list.";
                        }

                    } // container statistics

                    list multicast-management-operational-data {
                        key "chassis-number slot-number fp-number";
                        description "operational data.";

                        leaf chassis-number {
                            type uint32;
                            description "The unique index identifying this physical chassis.";
                        }

                        leaf slot-number {
                            type uint32;
                            description
                                "The unique value which identifies the IOM slot within a
                                 chassis in the system.";
                        }

                        leaf fp-number {
                            type uint32;
                            description "Forwarding plane within a specific IOM card";
                        }

                        leaf bandwith {
                            type yang:gauge32;
                            units "kilobps";
                            description "Current bandwidth";
                        }

                        leaf current-path {
                            type enumeration {
                                enum "none"                         { value 0; }
                                enum "primary"                      { value 1; }
                                enum "secondary"                    { value 2; }
                                enum "ancillary"                    { value 3; }
                                enum "blackhole"                    { value 4; }
                            }
                            description "Explicit sf path.";
                        }

                        leaf explicit-path {
                            type boolean;
                            description "???";
                        }

                        leaf admin-bw {
                            type yang:gauge32;
                            description "Admin bandwidth.";
                        }

                        leaf preference {
                            type yang:gauge32;
                            description "Preference level.";
                        }

                        leaf blackholed {
                            type boolean;
                            description "In black-hole state";
                        }

                        leaf blackhole-rate {
                            type yang:gauge32;
                            description "The current rate at which this channel will be placed in black-hole state";
                        }

                        leaf highest-bw {
                            type yang:gauge32;
                            description "The highest multicast bandwidth that has been accounted.";
                        }

                        leaf second-highest-bw {
                            type yang:gauge32;
                            description "The second highest multicast bandwidth that has been accounted.";
                        }

                        leaf expiry-time {
                            type uint32;
                            units "seconds";
                            description "Remaining time before the bandwidth update timer on the FP expires";
                        }

                        leaf plane {
                            type uint32;
                            description "Forwarding plane";
                        }

                    } // list multicast-management-operational-data

                } // list sg

                container statistics {
                    description "PIM statistics for a particular PIM instance.";

                    leaf tx-registers {
                        type yang:counter32;
                        description "The number of PIM Register messages transmitted by this instance.";
                    }

                    leaf tx-register-errors {
                        type yang:counter32;
                        description
                            "The number of the times there was an error while transmitting PIM
                             Register messages by this instance.";
                    }

                    leaf tx-null-registers {
                        type yang:counter32;
                        description "The number of PIM Null Register messages transmitted by this instance.";
                    }

                    leaf rx-candidate-rp-advertisements {
                        type yang:counter32;
                        description "The number of PIM Candidate-RP Advertisements (C-RP-Adv) received by this instance.";
                    }

                    leaf tx-candidate-rp-advertisements {
                        type yang:counter32;
                        description
                            "The number of PIM Candidate-RP Advertisements (C-RP-Adv) transmitted by this router
                             instance.";
                    }

                    leaf rx-candidate-rp-advertisement-drops {
                        type yang:counter32;
                        description
                            "The number of PIM Candidate-RP Advertisements (C-RP-Adv) received by this instance,
                             but were dropped.";
                    }

                    leaf tx-candidate-rp-advertisement-errors {
                        type yang:counter32;
                        description "The number of errors while transmitting PIM Candidate-RP Advertisements (C-RP-Adv).";
                    }

                    leaf forwarded-candidate-rp-advertisements {
                        type yang:counter32;
                        description
                            "The number of Candidate-RP Advertisements(C-RP-Adv) that were forwarded by the
                             router. C-RP-Adv's are forwarded when the received advertisement
                             has a router alert set and the destination address is not the
                             router's local address.";
                    }

                    leaf forwarded-candidate-rp-advertisement-drops {
                        type yang:counter32;
                        description
                            "The number of times the Candidate-RP Advertisements(C-RP-Adv) could not be forwarded
                             by the router.";
                    }

                    leaf tx-mdt-join-tlvs {
                        type yang:counter32;
                        description "The number of times MDT Join TLV were transmitted.";
                    }

                    leaf rx-mdt-join-tlvs {
                        type yang:counter32;
                        description "The number of times MDT Join TLV were received.";
                    }

                    leaf tx-mdt-join-tlv-errors {
                        type yang:counter32;
                        description "The number of times MDT Join TLV could not be transmitted.";
                    }

                    leaf rx-mdt-join-tlv-errors {
                        type yang:counter32;
                        description
                            "The number of times MDT Join TLVs were dropped due to errors in the
                             received TLV.";
                    }

                    leaf tx-spmsi-limit-hits {
                        type yang:counter32;
                        description
                            "The number of times the switch from ipmsi to S-PMSI is failed because of reaching the
                             maximum S-PMSI limit configured in
                             TIMETRA-VRTR-MIB::vRtrMvpnSpmsiMaxLimit.";
                    }

                    leaf p2mp-pmsi-create-fails {
                        type yang:counter32;
                        description "The number of times a P2MP PMSI tunnel creation has failed.";
                    }

                    leaf p2mp-pmsi-request-fails {
                        type yang:counter32;
                        description "The number of times a P2MP PMSI tunnel request has failed.";
                    }

                    leaf rx-control-pdu-interface-drops {
                        type yang:counter32;
                        description
                            "The number of control PDU drops on an interface which is operationally down or on an
                             interface on which PIM is not enabled.";
                    }

                    leaf active-tx-s-pmsis {
                        type yang:gauge32;
                        description
                            "The number of active MDTs on which the PE is forwarding packets. This object is
                             applicable to VPRNs only.";
                    }

                    leaf active-tx-receiver-threshold-s-pmsis {
                        type yang:counter32;
                        description
                            "The number of active MDTs on which the PE is forwarding packets. This S-PMSI is
                             threshold controlled.";
                    }

                    leaf active-rx-s-pmsis {
                        type yang:gauge32;
                        description
                            "The number of active Mdts on which the PE is receiving packets.  This object is applicable
                             to VPRNs only.";
                    }

                    leaf active-rx-pseudo-s-pmsis {
                        type yang:counter32;
                        description
                            "The number of active Mdts on which the pseudo PE is receiving packets. This object
                             is applicable to VPRNs only.";
                    }

                    leaf total-tx-s-pmsis {
                        type yang:counter32;
                        description
                            "The number of MDTs created by the PE for forwarding packets. This object is applicable to
                             VPRNs only.";
                    }

                    leaf total-rx-s-pmsis {
                        type yang:counter32;
                        description
                            "The number of MDTs created by the PE for receiving packets. This object is applicable to
                             VPRNs only.";
                    }

                    leaf sg-count {
                        type yang:gauge32;
                        description
                            "The number of entries in 'display router/(service vprn) pim ipv4/6 sg'
                             for which 'type' is 'sg'.";
                    }

                    leaf star-g-count {
                        type yang:gauge32;
                        description
                            "The number of entries in 'display router/(service vprn) pim ipv4/6 sg'
                             for which 'type' is 'starG'.";
                    }

                    leaf star-star-rp-count {
                        type yang:gauge32;
                        description
                            "The number of entries in 'display router/(service vprn) pim ipv4/6 sg'
                             for which 'type' is 'starStarRP'.";
                    }

                    leaf tx-register-ttl-drops {
                        type yang:counter32;
                        description
                            "The number of multicast data packets which could not be encapsulated in Register
                             messages because the Time To Live (TTL) was zero.";
                    }

                    leaf rx-intra-as-ad {
                        type yang:counter32;
                        description "The number of Intra AS AD routes received on this interface.";
                    }

                    leaf tx-intra-as-ad {
                        type yang:counter32;
                        description "The number of Intra AS AD routes transmitted on this interface.";
                    }

                    leaf rx-intra-as-ad-errors {
                        type yang:counter32;
                        description
                            "The number of errors while processing Intra AS AD routes received on this
                             interface.";
                    }

                    leaf tx-inter-as-ad {
                        type yang:counter32;
                        description
                            "The number
                             of Inter AS AD routes transmitted on this interface.";
                    }

                    leaf rx-inter-as-ad {
                        type yang:counter32;
                        description
                            "The number
                             of Inter AS AD routes received on this interface.";
                    }

                    leaf rx-inter-as-ad-errors {
                        type yang:counter32;
                        description
                            "The number of errors while processing Inter AS AD routes received on this
                             interface.";
                    }

                    leaf rx-mdt-safi {
                        type yang:counter32;
                        description
                            "The number
                             of MDT-SAFI AD routes received on this interface.";
                    }

                    leaf tx-mdt-safi {
                        type yang:counter32;
                        description
                            "The number
                             of MDT-SAFI AD routes transmitted on this interface.";
                    }

                    leaf rx-mdt-safi-errors {
                        type yang:counter32;
                        description
                            "The number of errors while processing MDT-SAFI AD routes received on this
                             interface.";
                    }

                    leaf rx-spmsi-ad {
                        type yang:counter32;
                        description "The number of S-PMSI AD routes received on this interface.";
                    }

                    leaf tx-spmsi-ad {
                        type yang:counter32;
                        description "The number of S-PMSI AD routes transmitted on this interface.";
                    }

                    leaf rx-spmsi-ad-errors {
                        type yang:counter32;
                        description
                            "The number of errors while processing S-PMSI AD routes received on
                             this interface.";
                    }

                    leaf rx-leaf-ad {
                        type yang:counter32;
                        description "The number of Leaf AD routes received on this interface.";
                    }

                    leaf tx-leaf-ad {
                        type yang:counter32;
                        description "The number of Leaf AD routes transmitted on this interface.";
                    }

                    leaf rx-leaf-ad-errors {
                        type yang:counter32;
                        description
                            "The number of errors while processing Leaf AD routes received on
                             this interface.";
                    }

                    leaf rx-source-active-ad {
                        type yang:counter32;
                        description "The number of Source Active AD routes received on this interface.";
                    }

                    leaf tx-source-active-ad {
                        type yang:counter32;
                        description "The number of Source Active AD routes transmitted on this interface.";
                    }

                    leaf tx-source-active-ad-errors {
                        type yang:counter32;
                        description
                            "The number of errors while processing Source Active AD routes received
                             on this interface.";
                    }

                    leaf rx-shared-tree-join {
                        type yang:counter32;
                        description "The number of Shared Tree Joins received on this interface.";
                    }

                    leaf tx-shared-tree-join {
                        type yang:counter32;
                        description "The number of Shared Tree Joins transmitted on this interface.";
                    }

                    leaf rx-shared-tree-join-errors {
                        type yang:counter32;
                        description
                            "The number of errors while processing Shared Tree Joins received
                             on this interface.";
                    }

                    leaf rx-source-tree-join {
                        type yang:counter32;
                        description "The number of Source Tree Joins received on this interface.";
                    }

                    leaf tx-source-tree-join {
                        type yang:counter32;
                        description "The number of Source Tree Joins transmitted on this interface.";
                    }

                    leaf rx-source-tree-join-errors {
                        type yang:counter32;
                        description
                            "The number of errors while processing Source Tree Joins received on
                             this interface.";
                    }

                    leaf rx-bgp-packets {
                        type yang:counter32;
                        description
                            "The number
                             of BGP Packets received on this interface.";
                    }

                    leaf tx-bgp-packets {
                        type yang:counter32;
                        description
                            "The number
                             of BGP Packets transmitted on this interface.";
                    }

                } // container statistics

                container s-pmsi {
                    description "IPv4 selective provider-network multicast service interface (S-PMSI) configuration";

                    list rsvp {
                        key "extended-tunnel-address tunnel-id p2mp-id";
                        description
                            "The list of the RSVP Provider-Network Multicast Service (PMSI) interfaces.

                             A PMSI can be thought of as a connector between a set of PE routers
                             forming a Multicast Domain. From the perspective of a VPN-specific
                             PIM instance, a PMSI is a single multi-access interface.

                             A PMSI interface is created whenever the threshold of a (C-S,C-G)
                             exceeds the configured threshold value specified by Multicast Data Tunnel thresholds.
                             If the data-threshold goes below the value specified by
                             Multicast Data Tunnel thresholds, the PMSI interface is automatically deleted.";

                        leaf extended-tunnel-address {
                            type types-sros:ipv4-unicast-address;
                            description "The extended Tunnel address for a PMSI.";
                        }

                        leaf tunnel-id {
                            type uint32;
                            description "The Source RSVP Tunnel Identifier for a PMSI.";
                        }

                        leaf p2mp-id {
                            type uint32;
                            description "The P2MP Identifier for a PMSI.";
                        }

                        leaf interface-name {
                            type string;
                            description
                                "The interface name of the PMSI.

                                 This value is specific to the router.";
                        }

                        leaf interface-type {
                            type types-pim:pmsi-interface-type;
                            description "Whether this PMSI interface is of type transmitter or receiver.";
                        }

                        leaf vpn-cscg-count {
                            type uint32;
                            description "The number of (C-S,C-G)'s mapped to this PMSI.";
                        }

                        leaf up-time {
                            type uint32;
                            units "seconds";
                            description "The time since this PMSI entry was created.";
                        }

                        leaf multistream-id {
                            type uint32;
                            description "The stream Id of this multi stream SPMSI.";
                        }

                        leaf multistream-oper-state {
                            type types-sros:up-down-status;
                            description "The current operational state of this multi stream SPMSI.";
                        }

                        list cscg {
                            key "vpn-group-address vpn-source-address";
                            description
                                "The list of the (C-S,C-G) mapped to the Data Multicast Tunnel(MT).

                                 An entry in this table is created whenever a (C-S,C-G) is mapped to a MT interface.
                                 An entry will be deleted automatically when the mapping between (C-S,C-G) and
                                 Data MT is removed.";

                            leaf vpn-group-address {
                                type types-sros:ip-multicast-address;
                                description "The IP address of the multicast traffic destination address in the VPN (C-group address).";
                            }

                            leaf vpn-source-address {
                                type types-sros:ip-unicast-address;
                                description "The IP address of the traffic source in the VPN (C-source address).";
                            }

                            leaf cscg-state {
                                type types-pim:cscg-state;
                                description
                                    "The state of this PMSI (S,G).

                                     If the S-PMSI is bound to a (C-S,C-G) on the ingress PE and if the PE
                                     is allocating a PMSI, the state will be 'tx-join-pending'. The
                                     state will change to 'tx-joined' when the (C-S,C-G) traffic is switched
                                     over to the new S-PMSI.

                                     If the S-PMSI is not bound to a (C-S,C-G) on the egress PE, the state
                                     will be 'rx-not-joined'. The state will be 'rx-joined' if the (C-S,C-G)
                                     has bound to the S-PMSI.

                                     Egress PE state will be 'rx-joined-tracking' if it receives SPMSI-AD
                                     with no tunnel information.";
                            }

                            leaf mdt-threshold {
                                type uint32;
                                units "kilobps";
                                description
                                    "The threshold in kilobits per second (kbps) for the group to which
                                     this (C-S,C-G) belongs.

                                     For a group C-G configured with a threshold, a (C-S,C-G) is mapped to
                                     a PMSI only if the (C-S,C-G)'s rate exceeds this configured threshold.";
                            }

                            leaf join-timer {
                                type uint32;
                                units "seconds";
                                description
                                    "The time interval before the Provider Edge (PE) router connected to the
                                     source switches to the S-PMSI group.

                                     After providing sufficient time for all PE's to join the S-PMSI, the
                                     transmitting PE switches the given multicast stream to the S-PMSI.
                                     The PE router connected to the source then starts encapsulating
                                     traffic using the S-PMSI group.";
                            }

                            leaf holddown-timer {
                                type uint32;
                                units "seconds";
                                description
                                    "The time interval before which the PE router will switch back to the
                                     Default S-PMSI after it started encapsulating packets using the S-PMSI
                                     group.

                                     This is used to avoid oscillation when traffic is bursty.";
                            }

                            leaf expiry-timer {
                                type uint32;
                                units "seconds";
                                description
                                    "The time interval after which the Provider Edge (PE) router connected to
                                     the receivers time out S-PMSI Join Tag Length Value (TLV) received and
                                     leave the S-PMSI group.

                                     This value must be consistent among PE routers.";
                            }

                            leaf receiver-threshold {
                                type boolean;
                                description "Whether receiver threshold is enabled for this S-PMSI.";
                            }

                            leaf receiver-count {
                                type uint32;
                                description
                                    "The current receiver count for this S-PMSI.

                                     The value of this object is applicable only when the value of
                                     'receiver-threshold' is 'true'.";
                            }

                            leaf interface-name {
                                type types-sros:interface-name;
                                description
                                    "The interface name of this S-PMSI.

                                     This value will be non-zero integer value specific to the router.";
                            }

                            leaf up-time {
                                type uint32;
                                units "seconds";
                                description "The time since this entry was created.";
                            }

                        } // list cscg

                    } // list rsvp

                } // container s-pmsi

            } // container ipv4

            container ipv6 {
                description "Enter the ipv6 context";

                list sg {
                    key "group-address source-address";
                    description
                        "Each entry represents a source address from which receivers are
                         interested or not interested in receiving multicast traffic.";

                    leaf group-address {
                        type types-sros:ipv6-multicast-address;
                        description
                            "The IP multicast group address for which this entry contains information.
                             If the source-type is 'starStarRP', the value of this object will
                             be zero and source-address will contain the address of the RP.";
                    }

                    leaf source-address {
                        type types-sros:ipv6-address;
                        description
                            "The source address for which this entry contains information.
                             If source-type is 'starG', the value of this object will be zero.
                             If source-type is 'starstarRP', the value of this object will be address of the RP.";
                    }

                    leaf source-type {
                        type enumeration {
                            enum "star-star-rp"                 { value 0; }
                            enum "star-g"                       { value 1; }
                            enum "sg"                           { value 2; }
                        }
                        description "The type of this entry.";
                    }

                    leaf sg-state {
                        type enumeration {
                            enum "none"                         { value 0; }
                            enum "active"                       { value 1; }
                            enum "standby"                      { value 2; }
                        }
                        description "The current state of the (S,G).";
                    }

                    leaf rp-address {
                        type types-sros:ip-address;
                        description "The address of the Rendezvous Point(RP).";
                    }

                    leaf advertising-router {
                        type types-sros:ip-address;
                        description "The router address that advertised the route to the source indicated by source-address.";
                    }

                    leaf downstream-rpfv-neighbor {
                        type types-sros:ip-address;
                        description "The address of the downstream RPF vector neighbor.";
                    }

                    leaf downstream-rpfv-type {
                        type types-pim:rpfv-type;
                        description "The downstream RPF vector type.";
                    }

                    leaf downstream-rpfv-rd {
                        type types-services:state-vpn-rd;
                        description "The downstream RPF vector Route Distinguisher.";
                    }

                    leaf downstream-rpfv-proxy {
                        type types-sros:ip-address;
                        description "The address of the downstream RPF vector proxy.";
                    }

                    leaf upstream-rpfv-neighbor {
                        type types-sros:ip-address;
                        description "The address of the upstream RPF vector neighbor.";
                    }

                    leaf rpfv-flags {
                        type bits {
                            bit upstream-neighbor-no-join-attribute { position 0; }
                        }
                        description
                            "The state of the rpf-vectors.

                             When the bit 'upstream-neighbor-no-join-attribute' is set, it
                             indicates that the upstream neighbor towards the rpf-vector
                             proxy does not support join-attributes.";
                    }

                    leaf upstream-rpfv-type {
                        type types-pim:rpfv-type;
                        description "The upstream RPF vector type.";
                    }

                    leaf upstream-rpfv-rd {
                        type types-services:state-vpn-rd;
                        description "The upstream RPF vector Route Distinguisher.";
                    }

                    leaf upstream-rpfv-proxy {
                        type types-sros:ip-address;
                        description "The address of the upstream RPF vector proxy.";
                    }

                    leaf source-flags {
                        type bits {
                            bit spt-bit                        { position 0; }
                            bit rpt-prune-desired              { position 1; }
                        }
                        description
                            "The information about the state of the entry

                             This object is applicable only for (S,G) entries,i.e., when
                             source-type is 'sg'.

                             The (S,G) 'spt-bit' is used to distinguish whether to forward on
                             (*,*,RP) or (*,G) or on (S,G) state. It is updated when the (S,G)
                             data comes on the RPF interface towards the source.
                             'rpt-prune-desired' is set according to the PruneDesired(S,G,rpt)
                             algorithm.";
                    }

                    leaf mode {
                        type enumeration {
                            enum "none"                         { value 0; }
                            enum "sparse"                       { value 1; }
                            enum "dense"                        { value 2; }
                        }
                        description "The mode of operation for the (S,G).";
                    }

                    leaf mrib-nh-address {
                        type types-sros:ip-address-with-zone;
                        description "The next hop address towards the RP.";
                    }

                    leaf standby-rpf-neighbor-address {
                        type types-sros:ip-address;
                        description
                            "The address of the secondary RPF neighbor

                             The value of this object is applicable only when the value of the
                             object 'configure service vprn mvpn umh-selection' is set to 'tunnel-status'
                             indicating that the MVPN is configured with source redundancy.

                             When MVPN is configured with source redundancy, MVPN is capable of
                             receiving traffic from two different PE's for the same source.";
                    }

                    leaf mrib-source-flags {
                        type types-pim:mrib-source-flags;
                        description
                            "The MRIB information about the source. If the entry is of type 'starG'
                             or 'starStarRP', it will contain information about the RP for this group.";
                    }

                    leaf standby-mrib-source-flags {
                        type types-pim:mrib-source-flags;
                        description
                            "The MRIB information about the source reachable through the standby RPF
                             interface.

                             This object is applicable only for (S,G) entries,i.e., when
                             source-type is 'sg'.";
                    }

                    leaf keepalive-timer {
                        type uint32;
                        units "seconds";
                        description
                            "Is applicable only for (S,G) entries. The (S,G) Keepalive Timer is updated by
                             data being forwarded using this (S,G) forwarding state. It is used to keep (S,G)
                             state alive in the absence of explicit (S,G) Joins.";
                    }

                    leaf prune-limit-timer {
                        type uint32;
                        units "seconds";
                        description "The time until which no prunes will be sent upstream.";
                    }

                    leaf graft-retry-timer {
                        type uint32;
                        units "seconds";
                        description
                            "The time interval between which two grafts are sent upstream and no ack is
                             received from the upstream router.";
                    }

                    leaf up-time {
                        type uint32;
                        units "seconds";
                        description "The time since this source group entry got created.";
                    }

                    leaf resolved-by {
                        type enumeration {
                            enum "none"                         { value 0; }
                            enum "multicast-route-table"        { value 1; }
                            enum "unicast-route-table"          { value 2; }
                        }
                        description
                            "Which unicast routing table was used to resolve this source group entry.

                             The value of this object will be 'multicastRouteTable' if the
                             source or Rendezvous Point (RP) is resolved by the multicast-unicast
                             route table. The value of this object will be 'unicastRouteTable' if
                             the source or Rendezvous Point (RP) is resolved by the unicast
                             route table. The value will be 'none' if the source or RP is
                             unresolved.";
                    }

                    leaf upstream-jp-state {
                        type enumeration {
                            enum "not-joined"                   { value 0; }
                            enum "joined"                       { value 1; }
                            enum "pruned"                       { value 2; }
                            enum "forwarding"                   { value 3; }
                            enum "ack-pending"                  { value 4; }
                        }
                        description
                            "The upstream Join-Prune state. This is a result of sending PIM Join-Prune
                             messages towards the source or the RP.";
                    }

                    leaf upstream-jp-timer {
                        type uint32;
                        units "seconds";
                        description
                            "The time remaining before the router sends another Join message to it's
                             upstream neighbor.";
                    }

                    leaf upstream-rpt-jp-state {
                        type enumeration {
                            enum "not-joined-star-g"            { value 0; }
                            enum "not-pruned"                   { value 1; }
                            enum "pruned"                       { value 2; }
                        }
                        description
                            "The upstream RPT Join-Prune state. (S,G,rpt) Joins and Prunes are (S,G) Joins or
                             Prunes sent on the RP tree with the RPT bit set, either to modify the results of
                             (*,G) Joins, or to override the behavior of other upstream LAN peers.";
                    }

                    leaf upstream-rpt-override-timer {
                        type uint32;
                        units "seconds";
                        description
                            "The delay to triggered Join(S,G,rpt) messages to prevent implosions of triggered
                             messages.

                             If non-zero, it means that the router was in 'not-pruned' state and it saw a
                             Prune(S,G,rpt) message being sent to RPF'(S,G,rpt).

                             If the router sees a Join(S,G,rpt) override message being sent by
                             some other router on the LAN while the timer is still non-zero,
                             it simply cancels the override timer. If it does not see a
                             Join(S,G,rpt) message, then on expiry of the override timer, it
                             sends it's own Join(S,G,rpt) message to RPF'(S,G,rpt). A similar
                             scenario exists when RPF'(S,G,rpt) changes to become equal to
                             RPF'(*,G).";
                    }

                    leaf standby-upstream-jp-state {
                        type enumeration {
                            enum "not-joined"                   { value 0; }
                            enum "joined"                       { value 1; }
                        }
                        description
                            "The standby RPF Join-Prune state.

                             This object is applicable only for (S,G) entries,i.e., when
                             source-type is 'sg'.";
                    }

                    leaf standby-upstream-jp-timer {
                        type uint32;
                        units "seconds";
                        description
                            "The time remaining before the router sends another Join message to it's
                             upstream neighbor reachable through the standby RPF interface.

                             This object is applicable only for (S,G) entries,i.e., when
                             source-type is 'sg'.";
                    }

                    leaf register-state {
                        type enumeration {
                            enum "no-info"                      { value 0; }
                            enum "join"                         { value 1; }
                            enum "join-pending"                 { value 2; }
                            enum "prune"                        { value 3; }
                            enum "null-join"                    { value 4; }
                        }
                        description
                            "The register state. The register state is kept at the source DR. When the host
                             starts sending multicast packets and if there are no entries
                             programmed for that group, the source DR sends a Register packet
                             to the RP(G). Register state transition happen based on the register
                             stop timer and the response received from the RP.";
                    }

                    leaf register-stop-timer {
                        type uint32;
                        units "seconds";
                        description
                            "The time remaining before the register-state might transition
                             to a different state. This timer has a non-zero value when the
                             value of register-state is not 'noInfo'.";
                    }

                    leaf register-from-anycast-rp {
                        type boolean;
                        description
                            "Whether a register message for this source  group combination
                             was received from the anycast RP and not from the designated
                             router connected to the source. It  is not applicable when the value of
                             source-type is starStarRP or starG.";
                    }

                    leaf rpf-neighbor-address {
                        type types-sros:ip-address;
                        description "The address of the RPF neighbor.";
                    }

                    leaf rpf-neighbor-interface-name {
                        type string;
                        description "The router's interface index on which the RPF neighbor exists.";
                    }

                    leaf standby-rpf-neighbor-interface-name {
                        type string;
                        description
                            "The router's interface index on which the secondary RPF neighbor exists.

                             The value of this object is applicable only when the value of the
                             object 'configure service vprn mvpn umh-selection' is set to 'tunnel-status'
                             indicating that the MVPN is configured with source redundancy.";
                    }

                    leaf spmsi-rpf-neighbor-interface-name {
                        type string;
                        description
                            "In an MVPN scenario: The router's SPMSI interface index, if any, on which the RPF
                             neighbor exists.";
                    }

                    leaf inherited-outgoing-interface-count {
                        type yang:gauge32;
                        description
                            "The number of interfaces in the inherited outgoing interface list. An 'inherited'
                             list inherits state from other types.";
                    }

                    leaf s-g-rpt-prune-interface-count {
                        type yang:gauge32;
                        description "The number of interfaces on which the router received (S,G,Rpt) prunes.";
                    }

                    leaf spt-switchover-threshold {
                        type uint32;
                        units "kilobps";
                        description
                            "The configured threshold in kilobits per second(kbps) for the group to which
                             this (S,G) belongs.  For a group G configured with a threshold,
                             switchover to SPT for an (S,G) is attempted only if the (S,G)'s rate
                             exceeds this configured threshold.";
                    }

                    leaf ecmp-optional-threshold {
                        type uint32 {
                            range "0..7";
                        }
                        description "The optional threshold value for ECMP balancing.";
                    }

                    leaf administrative-bandwidth {
                        type yang:gauge32 {
                            range "0..40000000";
                        }
                        units "kilobps";
                        description
                            "The administrative bandwidth in kilobits per second(kbps) for the group to which
                             this (S,G) belongs.";
                    }

                    leaf rpt-rpf-neighbor-address {
                        type types-sros:ip-address;
                        description "The address of the RPF neighbor on the RPT.";
                    }

                    leaf immediate-outgoing-interface-count {
                        type yang:gauge32;
                        description
                            "The number of interfaces in the immediate outgoing interface list. An outgoing
                             list can be 'immediate' if it is built directly from the state of
                             the relevant type as indicated by source-type.";
                    }

                    leaf inherited-rpt-outgoing-interface-count {
                        type yang:gauge32;
                        description "The number of interfaces in the inherited outgoing interface list for (S,G,Rpt).";
                    }

                    leaf local-rx-include-interface-count {
                        type yang:gauge32;
                        description
                            "The number of interfaces in the local membership include interface list. Local
                             membership is the result of the local membership mechanism (MLD)
                             running on a interface. Include list contains interfaces which are
                             interested in receiving multicast traffic for this source group entry.";
                    }

                    leaf local-rx-exclude-interface-count {
                        type yang:gauge32;
                        description
                            "The number of interfaces in the local membership exclude interface list. Local
                             membership is the result of the local membership mechanism (MLD)
                             running on the interface. Exclude list contains interfaces which are
                             not interested in receiving multicast traffic for this source group
                             entry.";
                    }

                    leaf join-or-prune-interface-count {
                        type yang:gauge32;
                        description
                            "The number of interfaces on which the router received a Join or Prune message for
                             this source group combination.";
                    }

                    leaf lost-assert-interface-count {
                        type yang:gauge32;
                        description
                            "The number of interfaces on which the router lost assert for this source group
                             combination.";
                    }

                    leaf current-forwarding-rate {
                        type yang:counter64;
                        units "bps";
                        description
                            "The current forwarding rate being used by a source group(S,G) entry or
                             (*,G) entry, where * means any source entry, for the traffic in bits
                             per second(bps). This forwarding rate is calculated before ingress
                             QoS policing or shaping is applied.";
                    }

                    list group-interface {
                        key "sap forwarding-service group-interface-name";
                        description "List of the PIM enabled group-interfaces for an entry in the sg list.";

                        leaf sap {
                            type types-sros:sap;
                            description "SAP identifier.";
                        }

                        leaf forwarding-service {
                            type types-services:service-name;
                            description
                                "Specifies the forwarding service ID for a group-interface in a retailer
                                 context.";
                        }

                        leaf group-interface-name {
                            type types-sros:interface-name;
                            description
                                "The unique value which identifies this group-interface of this virtual
                                 router in the system. This field provides an identifier for
                                 virtual router interfaces similar to the ifIndex values used in the
                                 mib-2 interfaces table for physical interfaces.

                                 The values can be reused for different virtual routers, but are unique within
                                 those entries with the same vrtr-id.

                                 The value for each virtual interface must remain constant at least from
                                 one re-initialization of the system management processor to the next.";
                        }

                        leaf list-flags {
                            type types-pim:sg-flags;
                            description "The different lists that this group-interface belongs to.";
                        }

                    } // list group-interface

                    list host {
                        key "host-address";
                        description "List of PIM enabled hosts and their states for each entry in the sg list.";

                        leaf host-address {
                            type types-sros:ipv6-unicast-address;
                            description
                                "The IP multicast host address for which this entry contains information.
                                 If the ../type is 'star-star-rp', the value of this object will
                                 be zero and host-address will contain the address of the RP.";
                        }

                        leaf host-flags {
                            type types-pim:sg-flags;
                            description "The different lists that this host belongs to.";
                        }

                    } // list host

                    list interface {
                        key "interface-name";
                        description "List of the PIM enabled interfaces for an entry in sg list.";

                        leaf interface-name {
                            type types-sros:interface-name;
                            description "Router interface name.";
                        }

                        leaf interface-flags {
                            type types-pim:sg-flags;
                            description "Set of lists to which this interface belongs";
                        }

                        leaf spmsi-interface-name {
                            type string;
                            description
                                "In an MVPN scenario: The router's SPMSI interface index, if any, corresponding to
                                 the outgoing IPMSI interface.";
                        }

                    } // list interface

                    container statistics {
                        description "Statistics for the entries in the sg list collected by the forwarding engine.";

                        leaf forwarded-packets {
                            type yang:counter64;
                            description
                                "The number of multicast packets that were forwarded to the interfaces in the
                                 outgoing interface list. 'display router/(service vprn) pim ipv4/6 sg interface' lists all the
                                 interfaces in the outgoing interface list.";
                        }

                        leaf discarded-packets {
                            type yang:counter64;
                            description
                                "The number of multicast packets that matched this source group entry but were
                                 discarded. For (S,G) entries, if the traffic is getting forwarded on
                                 the SPT, the packets arriving from the RPT will be discarded.";
                        }

                        leaf rpf-mismatches {
                            type yang:counter64;
                            description
                                "The number of multicast packets that matched this source group entry
                                 but they did not arrive on the interface indicated by
                                 'display router/(service vprn) pim ipv4/6 sg rpf-neighbor-interface-name'.";
                        }

                        leaf forwarded-octets {
                            type yang:counter64;
                            description
                                "The number of multicast octets that were forwarded to the interfaces in the
                                 outgoing interface list. 'display router/(service vprn) pim ipv4/6 sg interface' lists all the
                                 interfaces in the outgoing interface list.";
                        }

                    } // container statistics

                    list multicast-management-operational-data {
                        key "chassis-number slot-number fp-number";
                        description "operational data.";

                        leaf chassis-number {
                            type uint32;
                            description "The unique index identifying this physical chassis.";
                        }

                        leaf slot-number {
                            type uint32;
                            description
                                "The unique value which identifies the IOM slot within a
                                 chassis in the system.";
                        }

                        leaf fp-number {
                            type uint32;
                            description "Forwarding plane within a specific IOM card";
                        }

                        leaf bandwith {
                            type yang:gauge32;
                            units "kilobps";
                            description "Current bandwidth";
                        }

                        leaf current-path {
                            type enumeration {
                                enum "none"                         { value 0; }
                                enum "primary"                      { value 1; }
                                enum "secondary"                    { value 2; }
                                enum "ancillary"                    { value 3; }
                                enum "blackhole"                    { value 4; }
                            }
                            description "Explicit sf path.";
                        }

                        leaf explicit-path {
                            type boolean;
                            description "???";
                        }

                        leaf admin-bw {
                            type yang:gauge32;
                            description "Admin bandwidth.";
                        }

                        leaf preference {
                            type yang:gauge32;
                            description "Preference level.";
                        }

                        leaf blackholed {
                            type boolean;
                            description "In black-hole state";
                        }

                        leaf blackhole-rate {
                            type yang:gauge32;
                            description "The current rate at which this channel will be placed in black-hole state";
                        }

                        leaf highest-bw {
                            type yang:gauge32;
                            description "The highest multicast bandwidth that has been accounted.";
                        }

                        leaf second-highest-bw {
                            type yang:gauge32;
                            description "The second highest multicast bandwidth that has been accounted.";
                        }

                        leaf expiry-time {
                            type uint32;
                            units "seconds";
                            description "Remaining time before the bandwidth update timer on the FP expires";
                        }

                        leaf plane {
                            type uint32;
                            description "Forwarding plane";
                        }

                    } // list multicast-management-operational-data

                } // list sg

                container statistics {
                    description "PIM statistics for a particular PIM instance.";

                    leaf tx-registers {
                        type yang:counter32;
                        description "The number of PIM Register messages transmitted by this instance.";
                    }

                    leaf tx-register-errors {
                        type yang:counter32;
                        description
                            "The number of the times there was an error while transmitting PIM
                             Register messages by this instance.";
                    }

                    leaf tx-null-registers {
                        type yang:counter32;
                        description "The number of PIM Null Register messages transmitted by this instance.";
                    }

                    leaf rx-candidate-rp-advertisements {
                        type yang:counter32;
                        description "The number of PIM Candidate-RP Advertisements (C-RP-Adv) received by this instance.";
                    }

                    leaf tx-candidate-rp-advertisements {
                        type yang:counter32;
                        description
                            "The number of PIM Candidate-RP Advertisements (C-RP-Adv) transmitted by this router
                             instance.";
                    }

                    leaf rx-candidate-rp-advertisement-drops {
                        type yang:counter32;
                        description
                            "The number of PIM Candidate-RP Advertisements (C-RP-Adv) received by this instance,
                             but were dropped.";
                    }

                    leaf tx-candidate-rp-advertisement-errors {
                        type yang:counter32;
                        description "The number of errors while transmitting PIM Candidate-RP Advertisements (C-RP-Adv).";
                    }

                    leaf forwarded-candidate-rp-advertisements {
                        type yang:counter32;
                        description
                            "The number of Candidate-RP Advertisements(C-RP-Adv) that were forwarded by the
                             router. C-RP-Adv's are forwarded when the received advertisement
                             has a router alert set and the destination address is not the
                             router's local address.";
                    }

                    leaf forwarded-candidate-rp-advertisement-drops {
                        type yang:counter32;
                        description
                            "The number of times the Candidate-RP Advertisements(C-RP-Adv) could not be forwarded
                             by the router.";
                    }

                    leaf tx-mdt-join-tlvs {
                        type yang:counter32;
                        description "The number of times MDT Join TLV were transmitted.";
                    }

                    leaf rx-mdt-join-tlvs {
                        type yang:counter32;
                        description "The number of times MDT Join TLV were received.";
                    }

                    leaf tx-mdt-join-tlv-errors {
                        type yang:counter32;
                        description "The number of times MDT Join TLV could not be transmitted.";
                    }

                    leaf rx-mdt-join-tlv-errors {
                        type yang:counter32;
                        description
                            "The number of times MDT Join TLVs were dropped due to errors in the
                             received TLV.";
                    }

                    leaf tx-spmsi-limit-hits {
                        type yang:counter32;
                        description
                            "The number of times the switch from ipmsi to S-PMSI is failed because of reaching the
                             maximum S-PMSI limit configured in
                             TIMETRA-VRTR-MIB::vRtrMvpnSpmsiMaxLimit.";
                    }

                    leaf p2mp-pmsi-create-fails {
                        type yang:counter32;
                        description "The number of times a P2MP PMSI tunnel creation has failed.";
                    }

                    leaf p2mp-pmsi-request-fails {
                        type yang:counter32;
                        description "The number of times a P2MP PMSI tunnel request has failed.";
                    }

                    leaf rx-control-pdu-interface-drops {
                        type yang:counter32;
                        description
                            "The number of control PDU drops on an interface which is operationally down or on an
                             interface on which PIM is not enabled.";
                    }

                    leaf active-tx-s-pmsis {
                        type yang:gauge32;
                        description
                            "The number of active MDTs on which the PE is forwarding packets. This object is
                             applicable to VPRNs only.";
                    }

                    leaf active-tx-receiver-threshold-s-pmsis {
                        type yang:counter32;
                        description
                            "The number of active MDTs on which the PE is forwarding packets. This S-PMSI is
                             threshold controlled.";
                    }

                    leaf active-rx-s-pmsis {
                        type yang:gauge32;
                        description
                            "The number of active Mdts on which the PE is receiving packets.  This object is applicable
                             to VPRNs only.";
                    }

                    leaf active-rx-pseudo-s-pmsis {
                        type yang:counter32;
                        description
                            "The number of active Mdts on which the pseudo PE is receiving packets. This object
                             is applicable to VPRNs only.";
                    }

                    leaf total-tx-s-pmsis {
                        type yang:counter32;
                        description
                            "The number of MDTs created by the PE for forwarding packets. This object is applicable to
                             VPRNs only.";
                    }

                    leaf total-rx-s-pmsis {
                        type yang:counter32;
                        description
                            "The number of MDTs created by the PE for receiving packets. This object is applicable to
                             VPRNs only.";
                    }

                    leaf sg-count {
                        type yang:gauge32;
                        description
                            "The number of entries in 'display router/(service vprn) pim ipv4/6 sg'
                             for which 'type' is 'sg'.";
                    }

                    leaf star-g-count {
                        type yang:gauge32;
                        description
                            "The number of entries in 'display router/(service vprn) pim ipv4/6 sg'
                             for which 'type' is 'starG'.";
                    }

                    leaf star-star-rp-count {
                        type yang:gauge32;
                        description
                            "The number of entries in 'display router/(service vprn) pim ipv4/6 sg'
                             for which 'type' is 'starStarRP'.";
                    }

                    leaf tx-register-ttl-drops {
                        type yang:counter32;
                        description
                            "The number of multicast data packets which could not be encapsulated in Register
                             messages because the Time To Live (TTL) was zero.";
                    }

                    leaf rx-intra-as-ad {
                        type yang:counter32;
                        description "The number of Intra AS AD routes received on this interface.";
                    }

                    leaf tx-intra-as-ad {
                        type yang:counter32;
                        description "The number of Intra AS AD routes transmitted on this interface.";
                    }

                    leaf rx-intra-as-ad-errors {
                        type yang:counter32;
                        description
                            "The number of errors while processing Intra AS AD routes received on this
                             interface.";
                    }

                    leaf tx-inter-as-ad {
                        type yang:counter32;
                        description
                            "The number
                             of Inter AS AD routes transmitted on this interface.";
                    }

                    leaf rx-inter-as-ad {
                        type yang:counter32;
                        description
                            "The number
                             of Inter AS AD routes received on this interface.";
                    }

                    leaf rx-inter-as-ad-errors {
                        type yang:counter32;
                        description
                            "The number of errors while processing Inter AS AD routes received on this
                             interface.";
                    }

                    leaf rx-mdt-safi {
                        type yang:counter32;
                        description
                            "The number
                             of MDT-SAFI AD routes received on this interface.";
                    }

                    leaf tx-mdt-safi {
                        type yang:counter32;
                        description
                            "The number
                             of MDT-SAFI AD routes transmitted on this interface.";
                    }

                    leaf rx-mdt-safi-errors {
                        type yang:counter32;
                        description
                            "The number of errors while processing MDT-SAFI AD routes received on this
                             interface.";
                    }

                    leaf rx-spmsi-ad {
                        type yang:counter32;
                        description "The number of S-PMSI AD routes received on this interface.";
                    }

                    leaf tx-spmsi-ad {
                        type yang:counter32;
                        description "The number of S-PMSI AD routes transmitted on this interface.";
                    }

                    leaf rx-spmsi-ad-errors {
                        type yang:counter32;
                        description
                            "The number of errors while processing S-PMSI AD routes received on
                             this interface.";
                    }

                    leaf rx-leaf-ad {
                        type yang:counter32;
                        description "The number of Leaf AD routes received on this interface.";
                    }

                    leaf tx-leaf-ad {
                        type yang:counter32;
                        description "The number of Leaf AD routes transmitted on this interface.";
                    }

                    leaf rx-leaf-ad-errors {
                        type yang:counter32;
                        description
                            "The number of errors while processing Leaf AD routes received on
                             this interface.";
                    }

                    leaf rx-source-active-ad {
                        type yang:counter32;
                        description "The number of Source Active AD routes received on this interface.";
                    }

                    leaf tx-source-active-ad {
                        type yang:counter32;
                        description "The number of Source Active AD routes transmitted on this interface.";
                    }

                    leaf tx-source-active-ad-errors {
                        type yang:counter32;
                        description
                            "The number of errors while processing Source Active AD routes received
                             on this interface.";
                    }

                    leaf rx-shared-tree-join {
                        type yang:counter32;
                        description "The number of Shared Tree Joins received on this interface.";
                    }

                    leaf tx-shared-tree-join {
                        type yang:counter32;
                        description "The number of Shared Tree Joins transmitted on this interface.";
                    }

                    leaf rx-shared-tree-join-errors {
                        type yang:counter32;
                        description
                            "The number of errors while processing Shared Tree Joins received
                             on this interface.";
                    }

                    leaf rx-source-tree-join {
                        type yang:counter32;
                        description "The number of Source Tree Joins received on this interface.";
                    }

                    leaf tx-source-tree-join {
                        type yang:counter32;
                        description "The number of Source Tree Joins transmitted on this interface.";
                    }

                    leaf rx-source-tree-join-errors {
                        type yang:counter32;
                        description
                            "The number of errors while processing Source Tree Joins received on
                             this interface.";
                    }

                    leaf rx-bgp-packets {
                        type yang:counter32;
                        description
                            "The number
                             of BGP Packets received on this interface.";
                    }

                    leaf tx-bgp-packets {
                        type yang:counter32;
                        description
                            "The number
                             of BGP Packets transmitted on this interface.";
                    }

                } // container statistics

            } // container ipv6

            list interface {
                key "interface-name";
                description "Enter the interface list instance";

                leaf interface-name {
                    type types-sros:interface-name;
                    description "Router interface name";
                }

                leaf auto-created-interface {
                    type boolean;
                    description
                        "The value of this object indicates if this interface was
                         auto created.";
                }

                leaf extranet-type {
                    type enumeration {
                        enum "rx"                           { value 0; }
                        enum "tx"                           { value 1; }
                        enum "none"                         { value 3; }
                    }
                    description
                        "The value of this object indicates whether the extranet interface
                         is of type transmitter or receiver.";
                }

                leaf extranet-mvpn-id {
                    type uint32 {
                        range "0..10240";
                    }
                    description
                        "The value of this object indicates the id associated with the
                         extranet interface. If the interface is not an extranet
                         interface then the value of this object will be '0'.";
                }

                leaf oper-state {
                    type types-sros:oper-state;
                    description
                        "The value of the this object indicates the operational
                         state of the destination.";
                }

                leaf pmsi-type {
                    type enumeration {
                        enum "none"                         { value 0; }
                        enum "ipmsi-tx"                     { value 1; }
                        enum "ipmsi-rx"                     { value 2; }
                        enum "spmsi-tx"                     { value 3; }
                        enum "spmsi-rx"                     { value 4; }
                    }
                    description
                        "The value of this object indicates the type of the tunnel
                         interface.";
                }

                container i-pmsi {
                    description "Inclusive provider-network multicast service interface (I-PMSI)";

                    container rsvp {
                        description
                            "The list of RSVP Inclusive Provider-Network Multicast Service
                             (IPMSI) interfaces.

                             A PMSI can be thought of as a connector between a set of PE routers 
                             forming a multicast domain. From the perspective of a VPN-specific 
                             PIM instance, a PMSI is a single multi-access interface.

                             IPMSI's are used for transmitting the MVPN's multicast data from one
                             PE to others.";

                        leaf extended-tunnel-address {
                            type types-sros:ip-address;
                            description "The extended tunnel address for the PMSI.";
                        }

                        leaf lsp-name {
                            type types-sros:named-item;
                            description
                                "The indicates the the RSVP point to multipoint (P2MP)
                                 lsp name associated with this IPMSI.

                                 In case of terminating IPMSIs the indicates the name of the
                                 tunnel interface.";
                        }

                        leaf p2mp-id {
                            type uint32;
                            description "The P2MP Identifier associated with this PMSI.";
                        }

                        leaf tunnel-id {
                            type uint32;
                            description "The tunnel identifier associated with this PMSI.";
                        }

                    } // container rsvp

                    container bier {
                        description
                            "The list of Bier Inclusive Provider-Network Multicast Service
                             (IPMSI) interfaces.

                             A PMSI can be thought of as a connector between a set of PE routers 
                             forming a multicast domain. From the perspective of a VPN-specific 
                             PIM instance, a PMSI is a single multi-access interface.

                             IPMSI's are used for transmitting the MVPN's multicast data from one
                             PE to others.";

                        leaf root-address {
                            type types-sros:ip-address;
                            description "The tunnel root address of the PMSI.";
                        }

                        leaf subdomain-id {
                            type uint32;
                            description "The BIER sub-domain ID.";
                        }

                        leaf bfr-id {
                            type uint32;
                            description "The BFR ID.";
                        }

                        leaf mpls-label {
                            type uint32;
                            description "The MPLS service label for the PMSI.";
                        }

                    } // container bier

                } // container i-pmsi

                container s-pmsi {
                    description "Selective provider-network multicast service interface (S-PMSI) configuration";

                    container rsvp {
                        description
                            "The list of the RSVP Provider-Network Multicast Service (PMSI) interfaces.

                             A PMSI can be thought of as a connector between a set of PE routers
                             forming a Multicast Domain. From the perspective of a VPN-specific
                             PIM instance, a PMSI is a single multi-access interface.

                             A PMSI interface is created whenever the threshold of a (C-S,C-G)
                             exceeds the configured threshold value specified by Multicast Data Tunnel thresholds.
                             If the data-threshold goes below the value specified by
                             Multicast Data Tunnel thresholds, the PMSI interface is automatically deleted.";

                        leaf extended-tunnel-address {
                            type types-sros:ip-address;
                            description "The extended tunnel address for the PMSI.";
                        }

                        leaf lsp-name {
                            type types-sros:named-item;
                            description
                                "The indicates the the RSVP point to multipoint (P2MP)
                                 lsp name associated with this IPMSI.

                                 In case of terminating IPMSIs the indicates the name of the
                                 tunnel interface.";
                        }

                        leaf p2mp-id {
                            type uint32;
                            description "The P2MP Identifier associated with this PMSI.";
                        }

                        leaf tunnel-id {
                            type uint32;
                            description "The tunnel identifier associated with this PMSI.";
                        }

                    } // container rsvp

                } // container s-pmsi

                container ipv4 {
                    description "Enter the ipv4 context";

                    leaf max-groups-till-now {
                        type yang:counter32;
                        description "The highest value that Current Groups had till now.";
                    }

                    leaf oper-state {
                        type types-sros:oper-state;
                        description
                            "The current operational state associated with this address family
                             for PIM protocol on this interface.";
                    }

                    leaf designated-router {
                        type types-sros:ip-address;
                        description "Designated router IP address.";
                    }

                    leaf oper-dr-priority {
                        type uint32;
                        description "Operational DR priority.";
                    }

                    leaf time-to-next-hello {
                        type uint32;
                        description "Time for next hello.";
                    }

                    leaf tracking-support-oper-state {
                        type types-sros:up-down-status;
                        description "J/P Tracking support operational state.";
                    }

                    container statistics {
                        description "The PIM statistics for a particular interface.";

                        leaf rx-hellos {
                            type yang:counter32;
                            description "The number of PIM hello messages received on this interface.";
                        }

                        leaf tx-hellos {
                            type yang:counter32;
                            description "The number of PIM Hello messages transmitted on this interface.";
                        }

                        leaf rx-hellos-dropped {
                            type yang:counter32;
                            description
                                "The number of PIM Hello messages which were received on this interface but were
                                 dropped.";
                        }

                        leaf rx-join-prunes {
                            type yang:counter32;
                            description
                                "The number of PIM
                                 Join Prune messages received on this interface.";
                        }

                        leaf tx-join-prunes {
                            type yang:counter32;
                            description
                                "The number of PIM
                                 Join Prune messages transmitted on this interface.";
                        }

                        leaf rx-join-prune-errors {
                            type yang:counter32;
                            description
                                "The number of errors while processing Join-Prune messages received on this
                                 interface.";
                        }

                        leaf rx-mvpn-rpfv-jp {
                            type yang:counter32;
                            description
                                "The number of PIM
                                 Join Prune messages received on this interface which were propagated
                                 using RPF vectors for the MVPN.";
                        }

                        leaf tx-mvpn-rpfv-jp {
                            type yang:counter32;
                            description
                                "The number of PIM
                                 Join Prune messages transmitted on this interface which were propagated
                                 using RPF vectors for the MVPN.";
                        }

                        leaf rx-invalid-mvpn-rpfv-jp {
                            type yang:counter32;
                            description
                                "The number of invalid PIM Join Prune messages received on this interface which were
                                 propagated using RPF vectors for the MVPN.";
                        }

                        leaf rx-asserts {
                            type yang:counter32;
                            description "The number of PIM Assert messages received on this interface.";
                        }

                        leaf tx-asserts {
                            type yang:counter32;
                            description "The number of PIM Assert messages transmitted on this interface.";
                        }

                        leaf rx-assert-errors {
                            type yang:counter32;
                            description "The number of errors while processing Assert messages received on this interface.";
                        }

                        leaf rx-registers {
                            type yang:counter32;
                            description "The number of PIM Register messages received on this interface.";
                        }

                        leaf rx-register-errors {
                            type yang:counter32;
                            description "The number of errors while processing Register messages received on this interface.";
                        }

                        leaf rx-null-registers {
                            type yang:counter32;
                            description "The number of PIM Null Register messages received on this interface.";
                        }

                        leaf rx-register-stops {
                            type yang:counter32;
                            description "The number of PIM Register Stop messages received on this interface.";
                        }

                        leaf tx-register-stops {
                            type yang:counter32;
                            description "The number of PIM Register Stop messages transmitted on this interface.";
                        }

                        leaf rx-register-stop-errors {
                            type yang:counter32;
                            description
                                "The number of errors while processing Register Stop messages received on this
                                 interface.";
                        }

                        leaf tx-register-stop-errors {
                            type yang:counter32;
                            description
                                "The number of PIM errors while trasmitting PIM Register Stop messages
                                 on this interface.";
                        }

                        leaf rx-bsm-pdus {
                            type yang:counter32;
                            description "The number of PIM Bootstrap Messages (BSM) received on this interface.";
                        }

                        leaf tx-bsm-pdus {
                            type yang:counter32;
                            description "The number of PIM Bootstrap Messages (BSM) transmitted on this interface.";
                        }

                        leaf rx-bsm-pdu-drops {
                            type yang:counter32;
                            description "The number of PIM Bootstrap Messages (BSM) received on this interface but were dropped.";
                        }

                        leaf tx-bsm-errors {
                            type yang:counter32;
                            description "The number of errors while transmitting PIM Bootstrap Messages (BSM) on this interface.";
                        }

                        leaf rx-auto-rp-announce {
                            type yang:counter32;
                            description "The number Auto-RP announcements received on this interface.";
                        }

                        leaf tx-auto-rp-announce {
                            type yang:counter32;
                            description "The number of Auto-RP announcements transmitted on this interface.";
                        }

                        leaf rx-auto-rp-announce-errors {
                            type yang:counter32;
                            description
                                "The number of errors while processing Auto-RP announcements received on
                                 this interface.";
                        }

                        leaf tx-auto-rp-announce-errors {
                            type yang:counter32;
                            description
                                "The number of errors while transmitting Auto-RP announcements on this
                                 interface.";
                        }

                        leaf rx-auto-rp-mapping {
                            type yang:counter32;
                            description "The number of Auto-RP mappings received on this interface.";
                        }

                        leaf tx-auto-rp-mapping {
                            type yang:counter32;
                            description "The number of Auto-RP mappings transmitted on this interface.";
                        }

                        leaf rx-auto-rp-mapping-errors {
                            type yang:counter32;
                            description
                                "The number of errors while processing Auto-RP mappings received on this
                                 interface.";
                        }

                        leaf tx-auto-rp-mapping-errors {
                            type yang:counter32;
                            description
                                "The number of errors while transmitting Auto-RP mappings on this
                                 interface.";
                        }

                        leaf rx-grafts {
                            type yang:counter32;
                            description "The number of graft messages which were received on this interface.";
                        }

                        leaf tx-grafts {
                            type yang:counter32;
                            description "The number of graft messages which were transmitted from this interface.";
                        }

                        leaf rx-graft-errors {
                            type yang:counter32;
                            description "The number of invalid graft messages which were received on this interface.";
                        }

                        leaf rx-graft-acks {
                            type yang:counter32;
                            description "The number of graft acknowledgement messages which were received on this interface.";
                        }

                        leaf tx-graft-acks {
                            type yang:counter32;
                            description
                                "The number of graft acknowledgement messages which were transmitted from this
                                 interface.";
                        }

                        leaf rx-graft-ack-errors {
                            type yang:counter32;
                            description
                                "The number of invalid graft acknowledgement messages which were received on this
                                 interface.";
                        }

                        leaf rx-packets {
                            type yang:counter32;
                            description "The number of multicast data packets received on this interface.";
                        }

                        leaf tx-packets {
                            type yang:counter32;
                            description "The number of multicast data packets transmitted on this interface.";
                        }

                        leaf rx-invalid-registers {
                            type yang:counter32;
                            description
                                "The number of invalid PIM Register messages received on this interface

                                 A Register message is invalid when the RP address in the message
                                 is not the RP for the group specified in the message. If such a message
                                 arrives, a Invalid Register notification is sent.";
                        }

                        leaf rx-neighbor-unknown {
                            type yang:counter32;
                            description
                                "The number of PIM messages (other than Hello messages) which were received on this
                                 interface and were rejected because the adjacency with the neighbor
                                 router was not already established.";
                        }

                        leaf rx-bad-checksum-discard {
                            type yang:counter32;
                            description
                                "The number of PIM messages received on this interface which were discarded because
                                 of bad checksum.";
                        }

                        leaf rx-bad-encodings {
                            type yang:counter32;
                            description "The number of PIM messages with bad encodings received on this interface.";
                        }

                        leaf rx-bad-version-discard {
                            type yang:counter32;
                            description "The number of PIM messages with bad versions received on this interface.";
                        }

                        leaf rx-candidate-rp-adv-no-router-alert {
                            type yang:counter32;
                            description
                                "The number of Candidate-RP Advertisements(C-RP-Adv) received on this interface
                                 which had no router alert option set.";
                        }

                        leaf rx-bsm-no-router-alert-drops {
                            type yang:counter32;
                            description
                                "The number
                                 of BSM messages that were dropped because router alert option was not
                                 present.";
                        }

                        leaf rx-bsm-wrong-interface-drops {
                            type yang:counter32;
                            description
                                "The number of BSM messages that were dropped either because they were not sent by
                                 the correct RPF neighbor or because they arrived on the
                                 wrong interface.";
                        }

                        leaf rx-invalid-join-prunes {
                            type yang:counter32;
                            description
                                "The number of invalid PIM Join Prune messages received on this interface

                                 A Join Prune message is invalid when the RP address in the message
                                 is not the RP for the group specified in the message. If such a message
                                 arrives, a Invalid Join Prune notification is sent.";
                        }

                        leaf rx-invalid-auto-rp-pdu {
                            type yang:counter32;
                            description
                                "The number of errors while processing Auto-RP messages received on this
                                 interface.";
                        }

                        leaf rx-auto-rp-mapping-rpf-mismatch {
                            type yang:counter32;
                            description
                                "The number of times an Auto-RP mapping message was received on this interface
                                 other than the RPF interface.";
                        }

                        leaf rx-auto-rp-announcement-rpf-mismatch {
                            type yang:counter32;
                            description
                                "The number of times an Auto-RP announcement message was received on this interface
                                 other than the RPF interface.";
                        }

                        leaf rx-unknown-pdu-type {
                            type yang:counter32;
                            description "The number of packets received with an unsupported PIM type.";
                        }

                        leaf join-policy-drops {
                            type yang:counter32;
                            description
                                "The number of times the join policy match resulted in dropping PIM Join-Prune
                                 Message or one of the source group contained in the message.";
                        }

                        leaf register-policy-drops {
                            type yang:counter32;
                            description
                                "The number of times the register policy match resulted in dropping PIM Register
                                 Message.";
                        }

                        leaf bootstrap-import-policy-drops {
                            type yang:counter32;
                            description
                                "The number of Bootstrap Messages received on this interface but were dropped
                                 because of Bootstrap import policy.";
                        }

                        leaf bootstrap-export-policy-drops {
                            type yang:counter32;
                            description
                                "The number of Bootstrap Messages that were not transmitted on this interface
                                 because of Bootstrap export policy.";
                        }

                        leaf mcac-policy-drops {
                            type yang:counter32;
                            description
                                "The number times a PIM Group is dropped because of applying a
                                 multicast CAC policy on this interface.";
                        }

                        leaf sg-count {
                            type yang:gauge32;
                            description
                                "The number of entries in 'display router/(service vprn) pim interface ipv4/6 sg'
                                 for which type is 'sg'.";
                        }

                        leaf star-g-count {
                            type yang:gauge32;
                            description
                                "The number of entries in 'display router/(service vprn) pim interface ipv4/6 sg'
                                 for which type is 'starG'.";
                        }

                        leaf star-star-rp-count {
                            type yang:gauge32;
                            description
                                "The number of entries in 'display router/(service vprn) pim interface ipv4/6 sg'
                                 for which type is 'starStarRP'.";
                        }

                    } // container statistics

                    list neighbor {
                        key "neighbor-address";
                        description "List of the router's PIM neighbors on an interface.";

                        leaf neighbor-address {
                            type types-sros:ipv4-address;
                            description "This value indicates the IPv4 address of the PIM neighbor.";
                        }

                        leaf dr-priority {
                            type uint32;
                            description
                                "This value indicates neighbor's DR priority which is received
                                 in the hello message. If the Hello Message did not contain
                                 the DR priority field, the value of priority will be '1'.";
                        }

                        leaf dr-priority-present {
                            type boolean;
                            description
                                "This value of indicates whether the DR priority field was present
                                 in the Hello message received from the PIM neighbor.";
                        }

                        leaf tracking-support {
                            type boolean;
                            description
                                "This value indicates whether the T bit in the LAN Prune Delay
                                 option was present in the Hello message. This indicates the
                                 neighbor's capability to disable Join message suppression.";
                        }

                        leaf lan-delay {
                            type uint32;
                            units "milliseconds";
                            description
                                "This value indicates the value of lan delay field present in
                                 the Hello message received from the neighbor. ";
                        }

                        leaf lan-delay-present {
                            type boolean;
                            description
                                "This value indicates whether the Hello message received from
                                 the neighbor contained the Lan Delay field.";
                        }

                        leaf generated-id {
                            type uint32;
                            description
                                "This value indicates a randomly generated 32-bit value that is
                                 regenerated each time PIM forwarding is started or restarted on
                                 the interface, including when the router itself restarts.";
                        }

                        leaf override-interval {
                            type uint32;
                            units "milliseconds";
                            description
                                "This value indicates the value of the override interval present
                                 in the Hello message.";
                        }

                        leaf up-time {
                            type uint32;
                            units "seconds";
                            description
                                "This value indicates the time since this PIM neighbor (last)
                                 became a neighbor of the local router.";
                        }

                        leaf expiry-time {
                            type uint32;
                            units "seconds";
                            description
                                "This value indicates the minimum time remaining before this
                                 PIM neighbor will be aged out.";
                        }

                        leaf hold-time {
                            type uint32;
                            units "seconds";
                            description
                                "This value indicates the value of the hold time present in the
                                 Hello message.";
                        }

                        leaf join-attribute-support {
                            type boolean;
                            description
                                "This value indicates whether the Hello Message received from
                                 the neighbor contained the Join Attribute field.";
                        }

                        list secondary-neighbor {
                            key "secondary-neighbor-address";
                            description "Each entry represents the secondary addresses advertised by PIM neighbor.";

                            leaf secondary-neighbor-address {
                                type types-sros:ipv4-address;
                                description
                                    "This value indicates the IPv4 address of the secondary PIM
                                     neighbor.";
                            }

                        } // list secondary-neighbor

                    } // list neighbor

                    list sg {
                        key "type group-address source-address";
                        description
                            "List of the (*,*,RP), (*,G) and (S,G) and (S,G,rpt)
                             entries for which this particular interface has state.";

                        leaf type {
                            type enumeration {
                                enum "star-star-rp"                 { value 0; }
                                enum "star-g"                       { value 1; }
                                enum "sg"                           { value 2; }
                            }
                            description "The type of this entry.";
                        }

                        leaf group-address {
                            type types-sros:ipv4-multicast-address;
                            description
                                "The multicast group address of the entry. It will be zero if the
                                 'type' is 'star-star-rp'.";
                        }

                        leaf source-address {
                            type types-sros:ipv4-address;
                            description
                                "The source address of the multicast sender. It will be zero if the
                                 leaf 'type' value is 'star-g' and it will be the address of
                                 the Rendezvous Point(RP) if the leaf 'type' value is 'star-star-rp'.";
                        }

                        leaf up-time {
                            type uint32;
                            units "seconds";
                            description "The time since this source group entry got created.";
                        }

                        leaf join-prune-state {
                            type types-pim:join-prune-state;
                            description
                                "The Join Prune state for this entry on the interface.

                                 PIM Join or Prune messages are sent by the downstream routers
                                 towards the RPF' neighbor.";
                        }

                        leaf join-prune-timer {
                            type uint32;
                            units "seconds";
                            description
                                "The time remaining before the router transitions the value of
                                 join-prune-state to 'no-info'.

                                 The timer is started or restarted when a valid Join message is
                                 received. If the value of this object is zero and
                                 join-prune-state is 'join' state, it means that the
                                 downstream router sent a holdtime of '0xffff'. In this case,
                                 join-prune-state will not transition until an appropriate
                                 cancelling of Join or Prune message is received.";
                        }

                        leaf prune-pending-timer {
                            type uint32;
                            units "seconds";
                            description
                                "The time remaining before the router transitions the value of
                                 join-prune-state to 'no-info'.

                                 The timer is set when the PIM Prune message is received.";
                        }

                        leaf join-prune-rpt-state {
                            type types-pim:join-prune-state;
                            description
                                "The Join Prune Rpt state for this entry on the interface.

                                 PIM Join or Prune messages are sent by the downstream routers towards the
                                 RPF' neighbor. (S,G,rpt) state is a result of receiving (S,G, rpt) JP message
                                 from the downstream router on the RP tree.";
                        }

                        leaf join-prune-rpt-timer {
                            type uint32;
                            units "seconds";
                            description
                                "The time remaining before the router transitions the value of
                                 join-prune-rpt-state to 'no-info'.

                                 The timer is started or restarted when a valid Join message is
                                 received. If the value of this object is zero and
                                 join-prune-rpt-state is in 'join' state, it means that the
                                 downstream router sent a holdtime of '0xffff'. In this case,
                                 join-prune-rpt-state will not transition until an appropriate
                                 cancelling of Join or Prune message is received from the
                                 downstream router.";
                        }

                        leaf join-prune-rpt-pending-timer {
                            type uint32;
                            units "seconds";
                            description
                                "The time remaining before the router transitions the value of
                                 join-prune-rpt-state to 'no-info'.

                                 The timer is set when the (S,G,rpt) PIM Prune message is received.";
                        }

                        leaf rp-address {
                            type types-sros:ip-address;
                            description "The address of the Rendezvous Point(RP).";
                        }

                        leaf assert-state {
                            type enumeration {
                                enum "no-info"                      { value 0; }
                                enum "lost-assert"                  { value 1; }
                                enum "won-assert"                   { value 2; }
                            }
                            description
                                "The ASSERT state for this entry.

                                 Where multiple PIM routers peer over a shared LAN it  possible
                                 for more than one upstream router to have valid forwarding state
                                 for a packet, which can lead to packet duplication. PIM does not
                                 attempt to prevent this from occurring. Instead it detects when this
                                 has happened and elects a single forwarder amongst the upstream
                                 routers to prevent further duplication. This election is performed
                                 using PIM Assert messages.  Assert messages are also received by
                                 downstream routers on the LAN, and these cause subsequent Join or
                                 Prune messages to be sent to the upstream router that won the Assert.";
                        }

                        leaf assert-timer {
                            type uint32;
                            units "seconds";
                            description
                                "If the value of assert-state is 'lost-assert': the time remaining before
                                 the router transitions the assert-state to 'no-info'.
                                 If the value of assert-state is 'won-assert':  the time remaining before
                                 the ASSERT message is resent.";
                        }

                        leaf assert-metric {
                            type uint32;
                            description "The metric associated by the MRIB for the route towards the source or the RP.";
                        }

                        leaf assert-metric-preference {
                            type uint32;
                            description "The preference associated by the MRIB for the route towards the source or the RP.";
                        }

                        leaf assert-rpt-bit {
                            type boolean;
                            description "The value  is 'true' if the RPT bit is set and 'false' when the RPT bit is not set.";
                        }

                        leaf assert-winner-address {
                            type types-sros:ip-address;
                            description "The ASSERT winner's interface IP address.";
                        }

                        leaf assert-winner-metric {
                            type uint32;
                            description
                                "The ASSERT winner's metric associated by it's MRIB for the route
                                 towards the source or the RP.";
                        }

                        leaf assert-winner-metric-preference {
                            type uint32;
                            description
                                "The ASSERT winner's preference associated by it's MRIB for the
                                 route towards the source or the RP.";
                        }

                        leaf assert-winner-rpt-bit {
                            type boolean;
                            description "The value is 'true' if the RPT bit is set and 'false' when the RPT bit is not set.";
                        }

                        leaf data-mt-interface-name {
                            type types-sros:interface-name;
                            description
                                "The interface name of the Multicast Tunnel(MT) interface.

                                 If the value is not set, it indicates that there is no data MT
                                 associated with this group-source interface to forward
                                 multicast traffic into the service provider network.
                                 If the value is set, it indicates the data MT tunnel
                                 that is used to forward multicast traffic into the
                                 service provider network.";
                        }

                    } // list sg

                } // container ipv4

                container ipv6 {
                    description "Enter the ipv6 context";

                    leaf max-groups-till-now {
                        type yang:counter32;
                        description "The highest value that Current Groups had till now.";
                    }

                    leaf oper-state {
                        type types-sros:oper-state;
                        description
                            "The current operational state associated with this address family
                             for PIM protocol on this interface.";
                    }

                    leaf designated-router {
                        type types-sros:ip-address;
                        description "Designated router IP address.";
                    }

                    leaf oper-dr-priority {
                        type uint32;
                        description "Operational DR priority.";
                    }

                    leaf time-to-next-hello {
                        type uint32;
                        description "Time for next hello.";
                    }

                    leaf tracking-support-oper-state {
                        type types-sros:up-down-status;
                        description "J/P Tracking support operational state.";
                    }

                    container statistics {
                        description "The PIM statistics for a particular interface.";

                        leaf rx-hellos {
                            type yang:counter32;
                            description "The number of PIM hello messages received on this interface.";
                        }

                        leaf tx-hellos {
                            type yang:counter32;
                            description "The number of PIM Hello messages transmitted on this interface.";
                        }

                        leaf rx-hellos-dropped {
                            type yang:counter32;
                            description
                                "The number of PIM Hello messages which were received on this interface but were
                                 dropped.";
                        }

                        leaf rx-join-prunes {
                            type yang:counter32;
                            description
                                "The number of PIM
                                 Join Prune messages received on this interface.";
                        }

                        leaf tx-join-prunes {
                            type yang:counter32;
                            description
                                "The number of PIM
                                 Join Prune messages transmitted on this interface.";
                        }

                        leaf rx-join-prune-errors {
                            type yang:counter32;
                            description
                                "The number of errors while processing Join-Prune messages received on this
                                 interface.";
                        }

                        leaf rx-mvpn-rpfv-jp {
                            type yang:counter32;
                            description
                                "The number of PIM
                                 Join Prune messages received on this interface which were propagated
                                 using RPF vectors for the MVPN.";
                        }

                        leaf tx-mvpn-rpfv-jp {
                            type yang:counter32;
                            description
                                "The number of PIM
                                 Join Prune messages transmitted on this interface which were propagated
                                 using RPF vectors for the MVPN.";
                        }

                        leaf rx-invalid-mvpn-rpfv-jp {
                            type yang:counter32;
                            description
                                "The number of invalid PIM Join Prune messages received on this interface which were
                                 propagated using RPF vectors for the MVPN.";
                        }

                        leaf rx-asserts {
                            type yang:counter32;
                            description "The number of PIM Assert messages received on this interface.";
                        }

                        leaf tx-asserts {
                            type yang:counter32;
                            description "The number of PIM Assert messages transmitted on this interface.";
                        }

                        leaf rx-assert-errors {
                            type yang:counter32;
                            description "The number of errors while processing Assert messages received on this interface.";
                        }

                        leaf rx-registers {
                            type yang:counter32;
                            description "The number of PIM Register messages received on this interface.";
                        }

                        leaf rx-register-errors {
                            type yang:counter32;
                            description "The number of errors while processing Register messages received on this interface.";
                        }

                        leaf rx-null-registers {
                            type yang:counter32;
                            description "The number of PIM Null Register messages received on this interface.";
                        }

                        leaf rx-register-stops {
                            type yang:counter32;
                            description "The number of PIM Register Stop messages received on this interface.";
                        }

                        leaf tx-register-stops {
                            type yang:counter32;
                            description "The number of PIM Register Stop messages transmitted on this interface.";
                        }

                        leaf rx-register-stop-errors {
                            type yang:counter32;
                            description
                                "The number of errors while processing Register Stop messages received on this
                                 interface.";
                        }

                        leaf tx-register-stop-errors {
                            type yang:counter32;
                            description
                                "The number of PIM errors while trasmitting PIM Register Stop messages
                                 on this interface.";
                        }

                        leaf rx-bsm-pdus {
                            type yang:counter32;
                            description "The number of PIM Bootstrap Messages (BSM) received on this interface.";
                        }

                        leaf tx-bsm-pdus {
                            type yang:counter32;
                            description "The number of PIM Bootstrap Messages (BSM) transmitted on this interface.";
                        }

                        leaf rx-bsm-pdu-drops {
                            type yang:counter32;
                            description "The number of PIM Bootstrap Messages (BSM) received on this interface but were dropped.";
                        }

                        leaf tx-bsm-errors {
                            type yang:counter32;
                            description "The number of errors while transmitting PIM Bootstrap Messages (BSM) on this interface.";
                        }

                        leaf rx-auto-rp-announce {
                            type yang:counter32;
                            description "The number Auto-RP announcements received on this interface.";
                        }

                        leaf tx-auto-rp-announce {
                            type yang:counter32;
                            description "The number of Auto-RP announcements transmitted on this interface.";
                        }

                        leaf rx-auto-rp-announce-errors {
                            type yang:counter32;
                            description
                                "The number of errors while processing Auto-RP announcements received on
                                 this interface.";
                        }

                        leaf tx-auto-rp-announce-errors {
                            type yang:counter32;
                            description
                                "The number of errors while transmitting Auto-RP announcements on this
                                 interface.";
                        }

                        leaf rx-auto-rp-mapping {
                            type yang:counter32;
                            description "The number of Auto-RP mappings received on this interface.";
                        }

                        leaf tx-auto-rp-mapping {
                            type yang:counter32;
                            description "The number of Auto-RP mappings transmitted on this interface.";
                        }

                        leaf rx-auto-rp-mapping-errors {
                            type yang:counter32;
                            description
                                "The number of errors while processing Auto-RP mappings received on this
                                 interface.";
                        }

                        leaf tx-auto-rp-mapping-errors {
                            type yang:counter32;
                            description
                                "The number of errors while transmitting Auto-RP mappings on this
                                 interface.";
                        }

                        leaf rx-grafts {
                            type yang:counter32;
                            description "The number of graft messages which were received on this interface.";
                        }

                        leaf tx-grafts {
                            type yang:counter32;
                            description "The number of graft messages which were transmitted from this interface.";
                        }

                        leaf rx-graft-errors {
                            type yang:counter32;
                            description "The number of invalid graft messages which were received on this interface.";
                        }

                        leaf rx-graft-acks {
                            type yang:counter32;
                            description "The number of graft acknowledgement messages which were received on this interface.";
                        }

                        leaf tx-graft-acks {
                            type yang:counter32;
                            description
                                "The number of graft acknowledgement messages which were transmitted from this
                                 interface.";
                        }

                        leaf rx-graft-ack-errors {
                            type yang:counter32;
                            description
                                "The number of invalid graft acknowledgement messages which were received on this
                                 interface.";
                        }

                        leaf rx-packets {
                            type yang:counter32;
                            description "The number of multicast data packets received on this interface.";
                        }

                        leaf tx-packets {
                            type yang:counter32;
                            description "The number of multicast data packets transmitted on this interface.";
                        }

                        leaf rx-invalid-registers {
                            type yang:counter32;
                            description
                                "The number of invalid PIM Register messages received on this interface

                                 A Register message is invalid when the RP address in the message
                                 is not the RP for the group specified in the message. If such a message
                                 arrives, a Invalid Register notification is sent.";
                        }

                        leaf rx-neighbor-unknown {
                            type yang:counter32;
                            description
                                "The number of PIM messages (other than Hello messages) which were received on this
                                 interface and were rejected because the adjacency with the neighbor
                                 router was not already established.";
                        }

                        leaf rx-bad-checksum-discard {
                            type yang:counter32;
                            description
                                "The number of PIM messages received on this interface which were discarded because
                                 of bad checksum.";
                        }

                        leaf rx-bad-encodings {
                            type yang:counter32;
                            description "The number of PIM messages with bad encodings received on this interface.";
                        }

                        leaf rx-bad-version-discard {
                            type yang:counter32;
                            description "The number of PIM messages with bad versions received on this interface.";
                        }

                        leaf rx-candidate-rp-adv-no-router-alert {
                            type yang:counter32;
                            description
                                "The number of Candidate-RP Advertisements(C-RP-Adv) received on this interface
                                 which had no router alert option set.";
                        }

                        leaf rx-bsm-no-router-alert-drops {
                            type yang:counter32;
                            description
                                "The number
                                 of BSM messages that were dropped because router alert option was not
                                 present.";
                        }

                        leaf rx-bsm-wrong-interface-drops {
                            type yang:counter32;
                            description
                                "The number of BSM messages that were dropped either because they were not sent by
                                 the correct RPF neighbor or because they arrived on the
                                 wrong interface.";
                        }

                        leaf rx-invalid-join-prunes {
                            type yang:counter32;
                            description
                                "The number of invalid PIM Join Prune messages received on this interface

                                 A Join Prune message is invalid when the RP address in the message
                                 is not the RP for the group specified in the message. If such a message
                                 arrives, a Invalid Join Prune notification is sent.";
                        }

                        leaf rx-invalid-auto-rp-pdu {
                            type yang:counter32;
                            description
                                "The number of errors while processing Auto-RP messages received on this
                                 interface.";
                        }

                        leaf rx-auto-rp-mapping-rpf-mismatch {
                            type yang:counter32;
                            description
                                "The number of times an Auto-RP mapping message was received on this interface
                                 other than the RPF interface.";
                        }

                        leaf rx-auto-rp-announcement-rpf-mismatch {
                            type yang:counter32;
                            description
                                "The number of times an Auto-RP announcement message was received on this interface
                                 other than the RPF interface.";
                        }

                        leaf rx-unknown-pdu-type {
                            type yang:counter32;
                            description "The number of packets received with an unsupported PIM type.";
                        }

                        leaf join-policy-drops {
                            type yang:counter32;
                            description
                                "The number of times the join policy match resulted in dropping PIM Join-Prune
                                 Message or one of the source group contained in the message.";
                        }

                        leaf register-policy-drops {
                            type yang:counter32;
                            description
                                "The number of times the register policy match resulted in dropping PIM Register
                                 Message.";
                        }

                        leaf bootstrap-import-policy-drops {
                            type yang:counter32;
                            description
                                "The number of Bootstrap Messages received on this interface but were dropped
                                 because of Bootstrap import policy.";
                        }

                        leaf bootstrap-export-policy-drops {
                            type yang:counter32;
                            description
                                "The number of Bootstrap Messages that were not transmitted on this interface
                                 because of Bootstrap export policy.";
                        }

                        leaf mcac-policy-drops {
                            type yang:counter32;
                            description
                                "The number times a PIM Group is dropped because of applying a
                                 multicast CAC policy on this interface.";
                        }

                        leaf sg-count {
                            type yang:gauge32;
                            description
                                "The number of entries in 'display router/(service vprn) pim interface ipv4/6 sg'
                                 for which type is 'sg'.";
                        }

                        leaf star-g-count {
                            type yang:gauge32;
                            description
                                "The number of entries in 'display router/(service vprn) pim interface ipv4/6 sg'
                                 for which type is 'starG'.";
                        }

                        leaf star-star-rp-count {
                            type yang:gauge32;
                            description
                                "The number of entries in 'display router/(service vprn) pim interface ipv4/6 sg'
                                 for which type is 'starStarRP'.";
                        }

                    } // container statistics

                    list neighbor {
                        key "neighbor-address";
                        description "List of the router's PIM neighbors on an interface.";

                        leaf neighbor-address {
                            type types-sros:ipv6-address;
                            description "This value indicates the IPv6 address of the PIM neighbor.";
                        }

                        leaf dr-priority {
                            type uint32;
                            description
                                "This value indicates neighbor's DR priority which is received
                                 in the hello message. If the Hello Message did not contain
                                 the DR priority field, the value of priority will be '1'.";
                        }

                        leaf dr-priority-present {
                            type boolean;
                            description
                                "This value of indicates whether the DR priority field was present
                                 in the Hello message received from the PIM neighbor.";
                        }

                        leaf tracking-support {
                            type boolean;
                            description
                                "This value indicates whether the T bit in the LAN Prune Delay
                                 option was present in the Hello message. This indicates the
                                 neighbor's capability to disable Join message suppression.";
                        }

                        leaf lan-delay {
                            type uint32;
                            units "milliseconds";
                            description
                                "This value indicates the value of lan delay field present in
                                 the Hello message received from the neighbor. ";
                        }

                        leaf lan-delay-present {
                            type boolean;
                            description
                                "This value indicates whether the Hello message received from
                                 the neighbor contained the Lan Delay field.";
                        }

                        leaf generated-id {
                            type uint32;
                            description
                                "This value indicates a randomly generated 32-bit value that is
                                 regenerated each time PIM forwarding is started or restarted on
                                 the interface, including when the router itself restarts.";
                        }

                        leaf override-interval {
                            type uint32;
                            units "milliseconds";
                            description
                                "This value indicates the value of the override interval present
                                 in the Hello message.";
                        }

                        leaf up-time {
                            type uint32;
                            units "seconds";
                            description
                                "This value indicates the time since this PIM neighbor (last)
                                 became a neighbor of the local router.";
                        }

                        leaf expiry-time {
                            type uint32;
                            units "seconds";
                            description
                                "This value indicates the minimum time remaining before this
                                 PIM neighbor will be aged out.";
                        }

                        leaf hold-time {
                            type uint32;
                            units "seconds";
                            description
                                "This value indicates the value of the hold time present in the
                                 Hello message.";
                        }

                        leaf join-attribute-support {
                            type boolean;
                            description
                                "This value indicates whether the Hello Message received from
                                 the neighbor contained the Join Attribute field.";
                        }

                        list secondary-neighbor {
                            key "secondary-neighbor-address";
                            description "Each entry represents the secondary addresses advertised by PIM neighbor.";

                            leaf secondary-neighbor-address {
                                type types-sros:ipv6-address;
                                description
                                    "This value indicates the IPv6 address of the secondary PIM
                                     neighbor.";
                            }

                        } // list secondary-neighbor

                    } // list neighbor

                    list sg {
                        key "type group-address source-address";
                        description
                            "List of the (*,*,RP), (*,G) and (S,G) and (S,G,rpt)
                             entries for which this particular interface has state.";

                        leaf type {
                            type types-pim:sg-type;
                            description "The type of the SG entry.";
                        }

                        leaf group-address {
                            type types-sros:ipv6-multicast-address;
                            description
                                "The multicast group address of the entry. It will be zero if the
                                 'type' is 'star-star-rp'.";
                        }

                        leaf source-address {
                            type types-sros:ipv6-address;
                            description
                                "The source address of the multicast sender. It will be zero if the
                                 leaf 'type' value is 'star-g' and it will be the address of
                                 the Rendezvous Point(RP) if the leaf 'type' value is 'star-star-rp'.";
                        }

                        leaf up-time {
                            type uint32;
                            units "seconds";
                            description "The time since this source group entry got created.";
                        }

                        leaf join-prune-state {
                            type types-pim:join-prune-state;
                            description
                                "The Join Prune state for this entry on the interface.

                                 PIM Join or Prune messages are sent by the downstream routers
                                 towards the RPF' neighbor.";
                        }

                        leaf join-prune-timer {
                            type uint32;
                            units "seconds";
                            description
                                "The time remaining before the router transitions the value of
                                 join-prune-state to 'no-info'.

                                 The timer is started or restarted when a valid Join message is
                                 received. If the value of this object is zero and
                                 join-prune-state is 'join' state, it means that the
                                 downstream router sent a holdtime of '0xffff'. In this case,
                                 join-prune-state will not transition until an appropriate
                                 cancelling of Join or Prune message is received.";
                        }

                        leaf prune-pending-timer {
                            type uint32;
                            units "seconds";
                            description
                                "The time remaining before the router transitions the value of
                                 join-prune-state to 'no-info'.

                                 The timer is set when the PIM Prune message is received.";
                        }

                        leaf join-prune-rpt-state {
                            type types-pim:join-prune-state;
                            description
                                "The Join Prune Rpt state for this entry on the interface.

                                 PIM Join or Prune messages are sent by the downstream routers towards the
                                 RPF' neighbor. (S,G,rpt) state is a result of receiving (S,G, rpt) JP message
                                 from the downstream router on the RP tree.";
                        }

                        leaf join-prune-rpt-timer {
                            type uint32;
                            units "seconds";
                            description
                                "The time remaining before the router transitions the value of
                                 join-prune-rpt-state to 'no-info'.

                                 The timer is started or restarted when a valid Join message is
                                 received. If the value of this object is zero and
                                 join-prune-rpt-state is in 'join' state, it means that the
                                 downstream router sent a holdtime of '0xffff'. In this case,
                                 join-prune-rpt-state will not transition until an appropriate
                                 cancelling of Join or Prune message is received from the
                                 downstream router.";
                        }

                        leaf join-prune-rpt-pending-timer {
                            type uint32;
                            units "seconds";
                            description
                                "The time remaining before the router transitions the value of
                                 join-prune-rpt-state to 'no-info'.

                                 The timer is set when the (S,G,rpt) PIM Prune message is received.";
                        }

                        leaf rp-address {
                            type types-sros:ip-address;
                            description "The address of the Rendezvous Point(RP).";
                        }

                        leaf assert-state {
                            type enumeration {
                                enum "no-info"                      { value 0; }
                                enum "lost-assert"                  { value 1; }
                                enum "won-assert"                   { value 2; }
                            }
                            description
                                "The ASSERT state for this entry.

                                 Where multiple PIM routers peer over a shared LAN it  possible
                                 for more than one upstream router to have valid forwarding state
                                 for a packet, which can lead to packet duplication. PIM does not
                                 attempt to prevent this from occurring. Instead it detects when this
                                 has happened and elects a single forwarder amongst the upstream
                                 routers to prevent further duplication. This election is performed
                                 using PIM Assert messages.  Assert messages are also received by
                                 downstream routers on the LAN, and these cause subsequent Join or
                                 Prune messages to be sent to the upstream router that won the Assert.";
                        }

                        leaf assert-timer {
                            type uint32;
                            units "seconds";
                            description
                                "If the value of assert-state is 'lost-assert': the time remaining before
                                 the router transitions the assert-state to 'no-info'.
                                 If the value of assert-state is 'won-assert':  the time remaining before
                                 the ASSERT message is resent.";
                        }

                        leaf assert-metric {
                            type uint32;
                            description "The metric associated by the MRIB for the route towards the source or the RP.";
                        }

                        leaf assert-metric-preference {
                            type uint32;
                            description "The preference associated by the MRIB for the route towards the source or the RP.";
                        }

                        leaf assert-rpt-bit {
                            type boolean;
                            description "The value  is 'true' if the RPT bit is set and 'false' when the RPT bit is not set.";
                        }

                        leaf assert-winner-address {
                            type types-sros:ip-address;
                            description "The ASSERT winner's interface IP address.";
                        }

                        leaf assert-winner-metric {
                            type uint32;
                            description
                                "The ASSERT winner's metric associated by it's MRIB for the route
                                 towards the source or the RP.";
                        }

                        leaf assert-winner-metric-preference {
                            type uint32;
                            description
                                "The ASSERT winner's preference associated by it's MRIB for the
                                 route towards the source or the RP.";
                        }

                        leaf assert-winner-rpt-bit {
                            type boolean;
                            description "The value is 'true' if the RPT bit is set and 'false' when the RPT bit is not set.";
                        }

                        leaf data-mt-interface-name {
                            type types-sros:interface-name;
                            description
                                "The interface name of the Multicast Tunnel(MT) interface.

                                 If the value is not set, it indicates that there is no data MT
                                 associated with this group-source interface to forward
                                 multicast traffic into the service provider network.
                                 If the value is set, it indicates the data MT tunnel
                                 that is used to forward multicast traffic into the
                                 service provider network.";
                        }

                    } // list sg

                } // container ipv6

                container mcac {
                    description "Enter the mcac context";

                    leaf in-use-mandatory-bandwidth {
                        type uint32;
                        units "kilobps";
                        description
                            "The in-use bandwidth for the mandatory channels for this
                             protocol interface instance.";
                    }

                    leaf in-use-optional-bandwidth {
                        type uint32;
                        units "kilobps";
                        description
                            "The in-use bandwidth for the optional channels for this
                             protocol interface instance.";
                    }

                    leaf available-mandatory-bandwidth {
                        type uint32;
                        units "kilobps";
                        description
                            "The pre-reserved bandwidth for the mandatory channels for
                             this interface instance.";
                    }

                    leaf available-optional-bandwidth {
                        type uint32;
                        units "kilobps";
                        description "The available bandwidth for this interface instance.";
                    }

                    leaf values-in-transit {
                        type boolean;
                        description
                            "The operational (available and in-use mandatory/optional) value for the
                             following objects is in transition due to configuration change:
                             - available-mandatory-bandwidth
                             - available-bandwidth
                             - in-use-mandatory-bandwidth
                             - in-use-optional-bandwidth.";
                    }

                } // container mcac

            } // list interface

            container rp {
                description "Enter the rp context";

                container ipv4 {
                    description "Enter the ipv4 context";

                    container bsr-candidate {
                        description "Enter the bsr-candidate context";

                        leaf bsr-address {
                            type types-sros:ip-address;
                            description "The value of this object indicates the bootstrap address of the router.";
                        }

                        leaf bsr-state {
                            type enumeration {
                                enum "none"                         { value 0; }
                                enum "candidate-bsr"                { value 1; }
                                enum "pending-bsr"                  { value 2; }
                                enum "elected-bsr"                  { value 3; }
                                enum "accept-any"                   { value 4; }
                                enum "accept-preferred"             { value 5; }
                            }
                            description
                                "The value of this object indicates the state of the router
                                 with respect to the bootstrap mechanism.";
                        }

                        leaf up-time {
                            type uint32;
                            units "seconds";
                            description
                                "The value of this object indicates the time since
                                 the current E-BSR became the elected BSR.";
                        }

                        leaf expiry-time {
                            type uint32;
                            units "seconds";
                            description
                                "The value of this object indicates the minimum time remaining
                                 before the elected bootstrap router will be declared down if the
                                 value of bsr-state is not 'elected-bsr'.";
                        }

                        leaf bsr-hash-mask-length {
                            type int32;
                            description "The value of this object indicates the bootstrap hash mask length.";
                        }

                        leaf bsr-rpf-interface {
                            type string {
                                length "0..32";
                            }
                            description "The RPF interface towards the elected BSR.";
                        }

                        leaf bsr-priority {
                            type uint32 {
                                range "0..255";
                            }
                            description "The value of this object indicates the bootstrap priority of the router.";
                        }

                        leaf oper-state {
                            type types-sros:oper-state;
                            description
                                "The value of the this object indicates the operational
                                 state of the destination.";
                        }

                    } // container bsr-candidate

                    container rp-candidate {
                        description "Enter the rp-candidate context";

                        leaf oper-state {
                            type types-sros:oper-state;
                            description
                                "The value of the this object indicates the operational
                                 state of the destination.";
                        }

                        list advertised {
                            key "group-ip-prefix candidate-ip-address";
                            description
                                "List of the C-RP's and the group prefixes sent in the C-RP advertisement.

                                 It will be empty on all routers except the elected BSR router.";

                            leaf group-ip-prefix {
                                type types-sros:ipv4-multicast-prefix;
                                description
                                    "The range of multicast group addresses for which 'candidate-ip-address' is the
                                     candidate RP.";
                            }

                            leaf candidate-ip-address {
                                type types-sros:ipv4-address;
                                description "Candidate RP address.";
                            }

                            leaf priority {
                                type int32;
                                description
                                    "The Candidate RP's priority for becoming a Rendezvous Point (RP).

                                     This value is used to elect RP for a group range. A value of 0 is considered as the
                                     highest priority.";
                            }

                            leaf hold-time {
                                type int32;
                                units "seconds";
                                description
                                    "The hold time of the candidate RP.

                                     It is used by the bootstrap router to timeout the RP entries if it does not
                                     listen to another C-RP advertisement within the holdtime period.";
                            }

                            leaf expiry-time {
                                type uint32;
                                units "seconds";
                                description
                                    "The minimum time remaining before the Candidate-RP will be declared down.

                                     If the local router is not the BSR, this value is 0.";
                            }

                        } // list advertised

                    } // container rp-candidate

                    list set {
                        key "type group-ip-prefix candidate-ip-address";
                        description
                            "An entry of this list is created by:
                             - the elected BSR when it receives the Candidate-RP-Adv messages
                             - other routers on receiving Bootstrap Message(BSM) sent by the
                               elected BSR router;
                             - a router when it receives a Mapping message from the Auto-RP Mapping Agent.";

                        leaf type {
                            type enumeration {
                                enum "dynamic"                      { value 1; }
                                enum "static"                       { value 2; }
                                enum "auto-rp"                      { value 3; }
                            }
                            description
                                "Whether the entry was learned through the bootstrap mechanism, the
                                 Auto-RP mechanism or if it was statically configured using the
                                 (router|service/vprn)/pim/rp/(ipv4|ipv6)/static/address.";
                        }

                        leaf group-ip-prefix {
                            type types-sros:ipv4-multicast-prefix;
                            description
                                "The range of multicast group addresses for which 'candidate-ip-address' is the
                                 candidate RP.";
                        }

                        leaf candidate-ip-address {
                            type types-sros:ipv4-address;
                            description "Candidate RP address.";
                        }

                        leaf priority {
                            type int32;
                            description
                                "The Candidate RP's priority for becoming a Rendezvous Point (RP).

                                 This value is used to elect RP for a group range. A value of 0 is considered as the
                                 highest priority. For static entries, the priority is always 1.";
                        }

                        leaf hold-time {
                            type int32;
                            units "seconds";
                            description
                                "The hold time of the candidate RP.

                                 It is used by the bootstrap router to timeout the RP entries if it does not
                                 listen to another C-RP advertisement within the holdtime period.
                                 It will be zero for static entries.";
                        }

                        leaf expiry-time {
                            type uint32;
                            units "seconds";
                            description "The minimum time remaining before the RP Set group prefix will be declared down.";
                        }

                    } // list set

                } // container ipv4

                container ipv6 {
                    description "Enter the ipv6 context";

                    container bsr-candidate {
                        description "Enter the bsr-candidate context";

                        leaf bsr-address {
                            type types-sros:ip-address;
                            description "The value of this object indicates the bootstrap address of the router.";
                        }

                        leaf bsr-state {
                            type enumeration {
                                enum "none"                         { value 0; }
                                enum "candidate-bsr"                { value 1; }
                                enum "pending-bsr"                  { value 2; }
                                enum "elected-bsr"                  { value 3; }
                                enum "accept-any"                   { value 4; }
                                enum "accept-preferred"             { value 5; }
                            }
                            description
                                "The value of this object indicates the state of the router
                                 with respect to the bootstrap mechanism.";
                        }

                        leaf up-time {
                            type uint32;
                            units "seconds";
                            description
                                "The value of this object indicates the time since
                                 the current E-BSR became the elected BSR.";
                        }

                        leaf expiry-time {
                            type uint32;
                            units "seconds";
                            description
                                "The value of this object indicates the minimum time remaining
                                 before the elected bootstrap router will be declared down if the
                                 value of bsr-state is not 'elected-bsr'.";
                        }

                        leaf bsr-hash-mask-length {
                            type int32;
                            description "The value of this object indicates the bootstrap hash mask length.";
                        }

                        leaf bsr-rpf-interface {
                            type string {
                                length "0..32";
                            }
                            description "The RPF interface towards the elected BSR.";
                        }

                        leaf bsr-priority {
                            type uint32 {
                                range "0..255";
                            }
                            description "The value of this object indicates the bootstrap priority of the router.";
                        }

                        leaf oper-state {
                            type types-sros:oper-state;
                            description
                                "The value of the this object indicates the operational
                                 state of the destination.";
                        }

                    } // container bsr-candidate

                    container rp-candidate {
                        description "Enter the rp-candidate context";

                        leaf oper-state {
                            type types-sros:oper-state;
                            description
                                "The value of the this object indicates the operational
                                 state of the destination.";
                        }

                        list advertised {
                            key "group-ip-prefix candidate-ip-address";
                            description
                                "List of the C-RP's and the group prefixes sent in the C-RP advertisement.

                                 It will be empty on all routers except the elected BSR router.";

                            leaf group-ip-prefix {
                                type types-sros:ipv6-multicast-prefix;
                                description
                                    "The range of multicast group addresses for which 'candidate-ip-address' is the
                                     candidate RP.";
                            }

                            leaf candidate-ip-address {
                                type types-sros:ipv6-address;
                                description "Candidate RP address.";
                            }

                            leaf priority {
                                type int32;
                                description
                                    "The Candidate RP's priority for becoming a Rendezvous Point (RP).

                                     This value is used to elect RP for a group range. A value of 0 is considered as the
                                     highest priority.";
                            }

                            leaf hold-time {
                                type int32;
                                units "seconds";
                                description
                                    "The hold time of the candidate RP.

                                     It is used by the bootstrap router to timeout the RP entries if it does not
                                     listen to another C-RP advertisement within the holdtime period.";
                            }

                            leaf expiry-time {
                                type uint32;
                                units "seconds";
                                description
                                    "The minimum time remaining before the Candidate-RP will be declared down.

                                     If the local router is not the BSR, this value is 0.";
                            }

                        } // list advertised

                    } // container rp-candidate

                    list set {
                        key "type group-ip-prefix candidate-ip-address";
                        description
                            "An entry of this list is created by:
                             - the elected BSR when it receives the Candidate-RP-Adv messages
                             - other routers on receiving Bootstrap Message(BSM) sent by the
                               elected BSR router;
                             - a router when it receives a Mapping message from the Auto-RP Mapping Agent.";

                        leaf type {
                            type enumeration {
                                enum "dynamic"                      { value 1; }
                                enum "static"                       { value 2; }
                                enum "auto-rp"                      { value 3; }
                            }
                            description
                                "Whether the entry was learned through the bootstrap mechanism, the
                                 Auto-RP mechanism or if it was statically configured using the
                                 (router|service/vprn)/pim/rp/(ipv4|ipv6)/static/address.";
                        }

                        leaf group-ip-prefix {
                            type types-sros:ipv6-multicast-prefix;
                            description
                                "The range of multicast group addresses for which 'candidate-ip-address' is the
                                 candidate RP.";
                        }

                        leaf candidate-ip-address {
                            type types-sros:ipv6-address;
                            description "Candidate RP address.";
                        }

                        leaf priority {
                            type int32;
                            description
                                "The Candidate RP's priority for becoming a Rendezvous Point (RP).

                                 This value is used to elect RP for a group range. A value of 0 is considered as the
                                 highest priority. For static entries, the priority is always 1.";
                        }

                        leaf hold-time {
                            type int32;
                            units "seconds";
                            description
                                "The hold time of the candidate RP.

                                 It is used by the bootstrap router to timeout the RP entries if it does not
                                 listen to another C-RP advertisement within the holdtime period.
                                 It will be zero for static entries.";
                        }

                        leaf expiry-time {
                            type uint32;
                            units "seconds";
                            description "The minimum time remaining before the RP Set group prefix will be declared down.";
                        }

                    } // list set

                } // container ipv6

            } // container rp

        } // container pim

    } // grouping state-router-pim

}
