submodule nokia-state-port-dwdm {

    yang-version "1.1";

    belongs-to nokia-state { prefix "state"; }

    import nokia-sros-yang-extensions     { prefix "sros-ext"; }
    import nokia-types-port               { prefix "types-port"; }
    import nokia-types-sros               { prefix "types-sros"; }

    include nokia-state-port-dwdm-coherent;

    sros-ext:sros-major-release "rel19";

    organization "Nokia";

    contact
        "Nokia SR OS Support
         Web: <http://www.nokia.com>";

    description
        "Nokia YANG Data model with operational state for dense wavelength division multiplexing ports on SR OS based routers.

         Copyright 2016 Nokia. All rights reserved. Reproduction of this document
         is authorized on the condition that the foregoing copyright notice is included.

         This nokia-state-port-dwdm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-10-13";

    grouping state-port-dwdm {
        container dwdm {
            description "Enter the dwdm context";

            leaf rxdtv-current-adjustment {
                type uint32 {
                    range "0..10000";
                }
                units "centipercent";
                description
                    "Indicates the current relative adjustment of the receive decision threshold
                     voltage.";
            }

            leaf laser-tunability {
                type enumeration {
                    enum "unequipped"                   { value 0; }
                    enum "not-tunable"                  { value 1; }
                    enum "fully-tunable"                { value 2; }
                    enum "tunable-100g"                 { value 3; }
                }
                description
                    "Indicates if the optical interface laser is tunable or fixed. Value 'unequipped'
                     indicates the optical interface is not equipped with a laser.";
            }

            leaf minimum-channel {
                type types-port:optical-dwdm-extended-channel;
                description
                    "Indicates the minimum DWDM ITU channel supported by a tunable optical
                     interface.";
            }

            leaf maximum-channel {
                type types-port:optical-dwdm-extended-channel;
                description
                    "Indicates the maximum DWDM ITU channel supported by a tunable optical
                     interface.";
            }

            container wavetracker {
                description "Enter the wavetracker context";

                leaf current-alarms {
                    type types-port:dwdm-wavetracker-report-alarms;
                    description "Indicates which monitored alarms are raised against the port.";
                }

                leaf port-type {
                    type enumeration {
                        enum "unknown"                      { value 0; }
                        enum "fixed"                        { value 1; }
                        enum "pluggable"                    { value 2; }
                    }
                    description "Indicates if the port is fixed or if it supports pluggable equipment.";
                }

                container power-control {
                    description "Enter the power-control context";

                    leaf measured-power {
                        type decimal64 {
                            fraction-digits 2;
                        }
                        units "decibel-milliwatts";
                        description
                            "Indicates the current average output power of the port's
                             transmitted optical signal.";
                    }

                    leaf maximum-power {
                        type decimal64 {
                            fraction-digits 2;
                        }
                        units "decibel-milliwatts";
                        description
                            "Indicates the maximum average output power of the port's
                             transmitted optical signal at end of life.";
                    }

                    leaf minimum-power {
                        type decimal64 {
                            fraction-digits 2;
                        }
                        units "decibel-milliwatts";
                        description
                            "Indicates the maximum average output power of the port's
                             transmitted optical signal at end of life.";
                    }

                    leaf lower-power-margin {
                        type decimal64 {
                            fraction-digits 2;
                        }
                        units "decibel-milliwatts";
                        description
                            "Indicates how much the average output power of the port's
                             transmitted optical signal can be decreased.";
                    }

                    leaf upper-power-margin {
                        type decimal64 {
                            fraction-digits 2;
                        }
                        units "decibel-milliwatts";
                        description
                            "Indicates how much the average output power of the port's
                             transmitted optical signal can be increased.";
                    }

                } // container power-control

                container sff-voa {
                    description "The container of DWDM wavetracker SFF VOA state.";

                    leaf equipped {
                        type boolean;
                        description "Indicates whether or not an SFF VOA is present.";
                    }

                    leaf model-number {
                        type types-sros:named-item-255-or-empty;
                        description "Indicates the model number information for the SFF VOA.";
                    }

                    leaf serial-number {
                        type types-sros:named-item-255-or-empty;
                        description "Indicates the serial number information for the SFF VOA.";
                    }

                    leaf type {
                        type enumeration {
                            enum "none"                         { value 0; }
                            enum "fast"                         { value 1; }
                            enum "slow"                         { value 2; }
                        }
                        description "Indicates if the SFP VOA is fast or slow.";
                    }

                } // container sff-voa

            } // container wavetracker

            uses state-port-dwdm-coherent;
        } // container dwdm

    } // grouping state-port-dwdm

}
