submodule nokia-state-router-rsvp {

    yang-version "1.1";

    belongs-to nokia-state { prefix "state"; }

    import ietf-yang-types                { prefix "yang"; }
    import nokia-sros-yang-extensions     { prefix "sros-ext"; }
    import nokia-types-sros               { prefix "types-sros"; }

    include nokia-state-router;

    sros-ext:sros-major-release "rel19";

    organization "Nokia";

    contact
        "Nokia SR OS Support
         Web: <http://www.nokia.com>";

    description
        "Nokia YANG Data model with operational state for RSVP protocol on SR OS based routers.

         Copyright 2016 Nokia. All rights reserved. Reproduction of this document
         is authorized on the condition that the foregoing copyright notice is included.

         This nokia-state-router-rsvp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-10-16";

    grouping state-router-rsvp {
        container rsvp {
            description "Enter the rsvp context";

            leaf oper-state {
                type types-sros:oper-state;
                description
                    "The value of the this object indicates the operational
                     state of the destination.";
            }

            list interface {
                key "interface-name";
                description "Enter the interface list instance";

                leaf interface-name {
                    type leafref {
                        path "../../../interface/interface-name";
                    }
                    description "Index for router RSVP interface";
                }

                leaf active-sessions {
                    type yang:counter32;
                    description
                        "The total number of active RSVP sessions on this interface.
                         This count includes sessions that have requested bandwidth
                         as well as sessions that have not requested any bandwidth.";
                }

                leaf auth-key-id {
                    type yang:counter64;
                    description
                        "A locally unique key identifier is generated using some combination
                         of the address of the sending interface and the key number.";
                }

                leaf auth-rx-seq-num {
                    type yang:counter64;
                    description
                        "The value of this object indicates a monotonically increasing,
                         unique sequence number for the receiver.";
                }

                leaf auth-tx-seq-num {
                    type yang:counter64;
                    description
                        "The value of this object indicates a monotonically increasing,
                         unique sequence number for the sender.";
                }

                leaf dste-bc-ct0 {
                    type yang:counter64;
                    units "kilobps";
                    description "Bandwidth Constraint (BC) for Class Type 0 (CT0).";
                }

                leaf dste-bc-ct1 {
                    type yang:counter64;
                    units "kilobps";
                    description "Bandwidth Constraint (BC) for Class Type 1 (CT1).";
                }

                leaf dste-bc-ct2 {
                    type yang:counter64;
                    units "kilobps";
                    description "Bandwidth Constraint (BC) for Class Type 2 (CT2).";
                }

                leaf dste-bc-ct3 {
                    type yang:counter64;
                    units "kilobps";
                    description "Bandwidth Constraint (BC) for Class Type 3 (CT3).";
                }

                leaf dste-bc-ct4 {
                    type yang:counter64;
                    units "kilobps";
                    description "Bandwidth Constraint (BC) for Class Type 4 (CT4).";
                }

                leaf dste-bc-ct5 {
                    type yang:counter64;
                    units "kilobps";
                    description "Bandwidth Constraint (BC) for Class Type 5 (CT5).";
                }

                leaf dste-bc-ct6 {
                    type yang:counter64;
                    units "kilobps";
                    description "Bandwidth Constraint (BC) for Class Type 6 (CT6).";
                }

                leaf dste-bc-ct7 {
                    type yang:counter64;
                    units "kilobps";
                    description "Bandwidth Constraint (BC) for Class Type 7 (CT7).";
                }

                leaf total-sessions {
                    type yang:counter32;
                    description "The total number of RSVP sessions on this interface.";
                }

                leaf port-speed {
                    type uint32;
                    units "megabps";
                    description
                        "Interface bandwidth in mega-bits per second (Mbps) for the RSVP
                         protocol on this interface.";
                }

                leaf next-igp-update {
                    type uint32;
                    units "seconds";
                    description
                        "Time remaining in seconds before the next TE update would be sent
                         to IGP for the interface.";
                }

                leaf igp-update-pending {
                    type boolean;
                    description
                        "The TE update which is to be sent to IGP on any bandwidth change
                         is pending for the interface.";
                }

                leaf total-bw {
                    type uint64;
                    units "megabps";
                    description
                        "The amount of bandwidth in mega-bits per second (Mbps) available
                         to be reserved for the RSVP protocol on this interface.  This is
                         typically the (port Speed * subscription Percentage).";
                }

                leaf oper-state {
                    type types-sros:oper-state;
                    description "Current operating state of this RSVP protocol instance on this router.";
                }

                leaf reserved-bw {
                    type uint64;
                    units "megabps";
                    description
                        "Amount of bandwidth in mega-bits per second (Mbps) to reserved by
                         the RSVP sessions on this interface.  A value of zero (0) indicates
                         that no bandwidth is reserved.";
                }

                leaf neighbor-count {
                    type yang:gauge32;
                    description "Number of neighbors on this interface.";
                }

                leaf dbw-last-sample {
                    type yang:counter64;
                    units "kilobps";
                    description "The total number of SR-MPLS labeled packets transmitted from this interface.";
                }

                leaf dbw-last-sample-index {
                    type uint32;
                    description "The latest SR-MPLS sample index in current sample interval.";
                }

                leaf dbw-latest-cal-dbw {
                    type yang:counter64;
                    units "kilobps";
                    description "The lastest calculated DBw.";
                }

                leaf advertised-mrlb {
                    type yang:counter64;
                    units "kilobps";
                    description "The lastest advertised maximum reservable link bandwidth.";
                }

                list bandwidth-info {
                    key "te-class";
                    description "Bandwidth info per RSVP interface.";

                    leaf te-class {
                        type uint32 {
                            range "0..7";
                        }
                        description "Unique value that identifies the TE class.";
                    }

                    leaf reserved-bw {
                        type yang:counter64;
                        units "kilobps";
                        description
                            "Indicates the amount of bandwidth in kilobits per second (Kbps)
                             that is currently reserved by the RSVP sessions on this interface.
                             A value of zero (0) indicates that no bandwidth is reserved.";
                    }

                    leaf unreserved-bw {
                        type yang:counter64;
                        units "kilobps";
                        description "Indicates the unreserved bandwidth for each TE class.";
                    }

                } // list bandwidth-info

                container statistics {
                    description "RSVP interface statistics.";

                    leaf hello-timeouts {
                        type yang:counter32;
                        description "The total number of hello messages that timed out on this RSVP interface.";
                    }

                    leaf total-packets-sent {
                        type yang:counter64;
                        description
                            "The total number of RSVP packets, including error packets, that
                             have been transmitted on this RSVP interface.";
                    }

                    leaf total-packets-received {
                        type yang:counter64;
                        description
                            "The total number of RSVP packets, including errors, received on
                             this RSVP interface.";
                    }

                    leaf bad-packets-sent {
                        type yang:counter64;
                        description
                            "The total number of RSVP packets with errors that have been transmitted
                             on this RSVP interface.";
                    }

                    leaf bad-packets-received {
                        type yang:counter64;
                        description "The total number of RSVP packets with errors received on this RSVP interface.";
                    }

                    leaf paths-sent {
                        type yang:counter64;
                        description
                            "The total number of RSVP PATH messages that have been transmitted
                             from this RSVP interface.";
                    }

                    leaf paths-received {
                        type yang:counter64;
                        description
                            "The total number of RSVP PATH messages that have been received on
                             this RSVP interface.";
                    }

                    leaf path-errors-sent {
                        type yang:counter64;
                        description
                            "The total number of RSVP PATH ERROR messages that have been transmitted
                             from this RSVP interface.";
                    }

                    leaf path-errors-received {
                        type yang:counter64;
                        description
                            "The total number of RSVP PATH ERROR messages that have been received
                             on this RSVP interface.";
                    }

                    leaf path-tears-sent {
                        type yang:counter64;
                        description
                            "The total number of RSVP PATH TEAR messages that have been transmitted
                             from this RSVP interface.";
                    }

                    leaf path-tears-received {
                        type yang:counter64;
                        description
                            "The total number of RSVP PATH TEAR messages that have been received on
                             this RSVP interface.";
                    }

                    leaf resvs-sent {
                        type yang:counter64;
                        description
                            "The total number of RSVP RESV messages that have been transmitted
                             from this RSVP interface.";
                    }

                    leaf resvs-received {
                        type yang:counter64;
                        description
                            "The total number of RSVP RESV messages that have been received
                             on this RSVP interface.";
                    }

                    leaf resv-confirms-sent {
                        type yang:counter64;
                        description
                            "The total number of RSVP RESV CONFIRM messages that have been
                             transmitted from this RSVP interface.";
                    }

                    leaf resv-confirms-received {
                        type yang:counter64;
                        description
                            "The total number of RSVP RESV CONFIRM messages that have been
                             received on this RSVP interface.";
                    }

                    leaf resv-errors-sent {
                        type yang:counter64;
                        description
                            "The total number of RSVP RESV ERROR messages that have been
                             transmitted from this RSVP interface.";
                    }

                    leaf resv-errors-received {
                        type yang:counter64;
                        description
                            "The total number of RSVP RESV ERROR messages that have been
                             received on this RSVP interface.";
                    }

                    leaf resv-tears-sent {
                        type yang:counter64;
                        description
                            "The total number of RSVP RESV TEAR messages that have been
                             transmitted from this RSVP interface.";
                    }

                    leaf resv-tears-received {
                        type yang:counter64;
                        description
                            "The total number of RSVP RESV TEAR messages that have been
                             received on this RSVP interface.";
                    }

                    leaf refresh-summaries-sent {
                        type yang:counter64;
                        description
                            "The total number of summary refresh, SREFRESH, messages that
                             have been transmitted on this RSVP interface when refresh
                             reduction is enabled.";
                    }

                    leaf refresh-summaries-received {
                        type yang:counter64;
                        description
                            "The total number of RSVP summary refresh, SREFRESH, messages
                             received on this RSVP interface.";
                    }

                    leaf acks-sent {
                        type yang:counter64;
                        description
                            "The total number of RSVP ACK messages that have been transmitted
                             on this RSVP interface.";
                    }

                    leaf acks-received {
                        type yang:counter64;
                        description
                            "The total number of RSVP ACK messages received on this RSVP
                             interface.";
                    }

                    leaf bundle-packets-sent {
                        type yang:counter64;
                        description
                            "The total number of RSVP bundled packets that have been
                             transmitted on this RSVP interface.";
                    }

                    leaf bundle-packets-received {
                        type yang:counter64;
                        description
                            "The total number of RSVP bundled packets received on this
                             RSVP interface.  Bundled packets are sent when refresh
                             reduction is enabled.";
                    }

                    leaf hellos-sent {
                        type yang:counter64;
                        description
                            "The total number of RSVP HELLO REQ packets that have been
                             transmitted on this RSVP interface.";
                    }

                    leaf hellos-received {
                        type yang:counter64;
                        description
                            "The total number of RSVP HELLO REQ messages received on this
                             RSVP interface.";
                    }

                    leaf auth-errors-sent {
                        type yang:counter64;
                        description
                            "The total number of RSVP packets with MD5 errors sent by this
                             RSVP interface.";
                    }

                    leaf auth-errors-received {
                        type yang:counter64;
                        description
                            "The total number of RSVP packets with MD5 errors received on this
                             RSVP interface.";
                    }

                } // container statistics

                list neighbor {
                    key "ip-address";
                    description "RSVP interface neighbor.";

                    leaf ip-address {
                        type types-sros:ip-address;
                        description "This value indicates the type/address address of the RSVP neighbor.";
                    }

                    leaf hello-state {
                        type types-sros:oper-state;
                        description "Current operational state of the RSVP neighbor.";
                    }

                    leaf last-oper-change {
                        type types-sros:time-interval;
                        description
                            "Time interval which has elapsed since the RSVP neighbor's
                             operational state last changed.";
                    }

                    leaf flags {
                        type bits {
                            bit local-refresh-reduction        { position 0; }
                            bit local-reliable-delivery        { position 1; }
                            bit remote-refresh-reduction       { position 2; }
                            bit remote-message-id              { position 3; }
                        }
                        description
                            "The value of flags indicates the set of properties for
                             this RSVP neighbor. The bits are defined as follows :
                             localRefreshReduction  - If set, implies that refresh reduction is
                                                      configured locally for this neighbor.
                             localReliableDelivery  - If set, implies that reliable delivery is
                                                      configured locally for this neighbor.
                             remoteRefreshReduction - If set, implies that the refresh reduction
                                                      is supported on the remote end.
                             remoteMessageId        - If set, implies that message ID object is
                                                      supported on the remote end.";
                    }

                    leaf source-instance {
                        type string;
                        description "Source instance for this neighbor.";
                    }

                    leaf dst-instance {
                        type string;
                        description "Destination instance for this neighbor.";
                    }

                    leaf hello-refresh-time-remaining {
                        type uint32;
                        units "seconds";
                        description
                            "Indicates the time remaining in the Hello refresh timer. When the
                             Hello refresh timer expires, a Hello message is sent to the neighbor.";
                    }

                    leaf hello-timeout {
                        type uint32;
                        units "seconds";
                        description
                            "Indicates the time remaining in the Hello timeout timer. If a
                             Hello message is not received from the neighbor before this timer
                             expires, the neighbor is considered operationally down.";
                    }

                    leaf srefresh-time-remaining {
                        type uint32;
                        units "seconds";
                        description
                            "Indicates the time remaining in the Srefresh timer. An Srefresh
                             message is sent when this timer expires.";
                    }

                    leaf epoch-num-received {
                        type uint32;
                        description "Indicates the epoch number received from the neighbor.";
                    }

                    leaf max-msg-id-received {
                        type uint32;
                        description "Indicates the highest message ID received from neighbor.";
                    }

                    leaf gr-helper-state {
                        type enumeration {
                            enum "none"                         { value 0; }
                            enum "restart-in-progress"          { value 1; }
                            enum "recovery-in-progress"         { value 2; }
                            enum "cleanup"                      { value 3; }
                        }
                        description "Indicates the current state of the neighbor after loss of communication.";
                    }

                    leaf gr-helper-time-remaining {
                        type uint32;
                        units "seconds";
                        description
                            "Indicates the amount of time remaining, in seconds, for the restart
                             phase or recovery phase to timeout. If the timer expires, the RSVP
                             session not recovered will be torn down.";
                    }

                    leaf remote-gr-capability {
                        type boolean;
                        description "Indicates whether or not the neighbor supports graceful restart.";
                    }

                    leaf remote-graceful-restart-time {
                        type uint32;
                        units "milliseconds";
                        description "Indicates the restart timer advertised by the neighbor.";
                    }

                    leaf remote-graceful-recovery-time {
                        type uint32;
                        units "milliseconds";
                        description "Indicates the recovery timer advertised by the neighbor.";
                    }

                    container statistics {
                        description "RSVP interface neighbor statistics.";

                        leaf hello-timeout-count {
                            type yang:counter32;
                            description "Number of times the hello timeout timer expired for the neighbor.";
                        }

                        leaf hello-instance-mismatch-count {
                            type yang:counter32;
                            description
                                "Number of times the source and destination instances received in
                                 a Hello message did not match the destination and source instance
                                 for this neighbor.";
                        }

                        leaf out-of-order-msg-count {
                            type yang:counter32;
                            description "Number of out of order messages received from the neighbor.";
                        }

                        leaf retransmitted-msg-count {
                            type yang:counter32;
                            description
                                "Number of times messages have been retransmitted to the neighbor
                                 because the neighbor did not acknowledge that it received the message.";
                        }

                        leaf gr-procedure-invoked-count {
                            type yang:counter32;
                            description "Number of times that GR helper procedure has been invoked.";
                        }

                    } // container statistics

                } // list neighbor

            } // list interface

            list session {
                key "session-index";
                description "RSVP session.";

                leaf session-index {
                    type uint32;
                    description
                        "The unique value that identifies this RSVP session for the RSVP
                         protocol for this virtual router in the system. It is a unique
                         value among entries with the same value of vRtrID.";
                }

                leaf tunnel-id {
                    type uint32 {
                        range "1..65535";
                    }
                    description "Indicates the Tunnel ID for this RSVP session.";
                }

                leaf lsp-id {
                    type uint32 {
                        range "1..65535";
                    }
                    description "Indicates the LSP ID for this RSVP session.";
                }

                leaf sender-address {
                    type types-sros:ip-address;
                    description "IP address of the originating node for this RSVP session.";
                }

                leaf session-type {
                    type enumeration {
                        enum "unknown"                      { value 1; }
                        enum "p2p-originate"                { value 2; }
                        enum "p2p-transit"                  { value 3; }
                        enum "p2p-terminate"                { value 4; }
                        enum "detour-originate-for-p2p"     { value 5; }
                        enum "detour-transit-for-p2p"       { value 6; }
                        enum "detour-terminate-for-p2p"     { value 7; }
                        enum "dynamic-bypass-for-p2p"       { value 8; }
                        enum "manual-bypass-for-p2p"        { value 9; }
                        enum "p2mp-s2l-originate"           { value 10; }
                        enum "p2mp-s2l-transit"             { value 11; }
                        enum "p2mp-s2l-terminate"           { value 12; }
                        enum "dynamic-bypass-for-p2mp-s2l"  { value 13; }
                    }
                    description "Indicates this node's position in the path of this RSVP session.";
                }

                leaf in-if-index {
                    type uint32;
                    description "Indicates the incoming interface for this RSVP session.";
                }

                leaf out-if-index {
                    type uint32;
                    description "Indicates the outgoing interface for this RSVP session";
                }

                leaf in-label {
                    type uint32;
                    description "Indicates the incoming label for this RSVP session.";
                }

                leaf out-label {
                    type uint32;
                    description "Indicates the outgoing label for this RSVP session.";
                }

                leaf ext-tunnel-id {
                    type types-sros:ip-address;
                    description "Indicates the extended Tunnel ID for this RSVP session.";
                }

                leaf oper-state {
                    type types-sros:oper-state;
                    description "The current operational state of this RSVP session.";
                }

                leaf exclude-node-address {
                    type types-sros:ip-address;
                    description
                        "Indicates the address of the node to be avoided as signaled in the
                         EXCLUDE_ROUTE object(XRO).";
                }

                leaf resv-style {
                    type enumeration {
                        enum "unknown"                      { value 1; }
                        enum "se"                           { value 2; }
                        enum "ff"                           { value 3; }
                    }
                    description "Indicates the reservation style used for this RSVP session.";
                }

                leaf previous-hop {
                    type types-sros:ip-address;
                    description "IP address of the node that forwarded the RSVP PATH message.";
                }

                leaf next-hop {
                    type types-sros:ip-address;
                    description "IP address of the next-hop for this RSVP session.";
                }

                leaf endpoint-address {
                    type types-sros:ip-address;
                    description
                        "Indicates the IP address of the destination node for this RSVP
                         session.";
                }

                leaf bypass-session-index {
                    type uint32;
                    description
                        "Session index of the RSVP session that serves as a bypass tunnel
                         for this RSVP session. It is 0 if there is no bypass tunnel for
                         this RSVP session.";
                }

                leaf actual-hop-index {
                    type int32;
                    description "Indicates the primary index identifying recorded hop list.";
                }

                leaf cspf-hop-index {
                    type int32;
                    description "Indicates the primary index identifying CSPF hop list.";
                }

                leaf setup-priority {
                    type uint32 {
                        range "0..7";
                    }
                    description
                        "The setup priority used for this RSVP session when there is not
                         enough bandwidth available to setup this session.  If the setup
                         priority is greater than the hold priority for another established
                         session, then this session can preempt the existing session.  A value
                         of zero (0) is the highest priority and a value of seven (7) is the
                         lowest priority.";
                }

                leaf hold-priority {
                    type uint32 {
                        range "0..7";
                    }
                    description
                        "The hold priority to be used for this RSVP session when there
                         is insufficient bandwidth available to setup another session.
                         The other session's setup priority is compared against this session's
                         hold priority. If its setup priority is higher than this session's hold
                         priority, this session may be preempted by the other session.  A value
                         of zero (0) is the highest priority and a value of seven (7) is the
                         lowest priority.";
                }

                leaf session-name {
                    type types-sros:display-string {
                        length "1..160";
                    }
                    description "The signaled name of this RSVP session.";
                }

                leaf protection-type {
                    type enumeration {
                        enum "none"                         { value 0; }
                        enum "detour"                       { value 1; }
                        enum "facility"                     { value 2; }
                        enum "not-applicable"               { value 3; }
                    }
                    description
                        "Indicates the type of protection whether facility or detour
                         for this RSVP session";
                }

                leaf session-attribute-flags {
                    type uint32;
                    description
                        "Bit-mask that indicates the current setting of the attribute
                         flags for this RSVP session.  Session attributes include local
                         protection, label recording, reservation styles, bandwidth protection
                         desired and node protection desired.";
                }

                leaf class-type {
                    type uint32 {
                        range "0..7";
                    }
                    description "Indicates the class type for this RSVP session.";
                }

                leaf lsp-attribute-flags {
                    type bits {
                        bit reserved0                      { position 0; }
                        bit reserved1                      { position 1; }
                        bit reserved2                      { position 2; }
                        bit reserved3                      { position 3; }
                        bit reserved4                      { position 4; }
                        bit reserved5                      { position 5; }
                        bit reserved6                      { position 6; }
                        bit reserved7                      { position 7; }
                        bit reserved8                      { position 8; }
                        bit elc                            { position 9; }
                    }
                    description "Indicates the set of properties for LSP Attribute for this RSVP Session.";
                }

                leaf p2mp-id {
                    type uint32;
                    description "Indicates the P2MP ID if this RSVP session is for a P2MP LSP.";
                }

                leaf sub-group-id {
                    type uint32;
                    description
                        "Indicates the sub-group ID if the RSVP session is for a P2MP
                         LSP.";
                }

                leaf sub-group-originator-id {
                    type types-sros:ip-address;
                    description
                        "Indicates the sub-group originator ID if the RSVP session is for
                         a P2MP LSP.";
                }

                leaf local-protection-available {
                    type boolean;
                    description
                        "Indicates whether link or node downstream from this node is
                         protected via a local repair mechanism.";
                }

                leaf local-protection-in-use {
                    type boolean;
                    description
                        "Indicates whether local protection is being used to maintain
                         the tunnel supporting this RSVP session.";
                }

                leaf local-protection-properties {
                    type bits {
                        bit srlg-not-strict                { position 0; }
                        bit srlg-disjoint                  { position 1; }
                    }
                    description
                        "Indicates criteria or constraints that were used at the time of
                         computation of the FRR bypass tunnel or detour session associated
                         with any primary LSP path on the system. This is applicable only
                         for sessions being protected by FRR bypass tunnels or detours.";
                }

                container bypass {
                    description "RSVP session bypass information.";

                    leaf in-use {
                        type boolean;
                        description
                            "Indicates if a protected LSP is actively using this bypass
                             tunnel.";
                    }

                    leaf avoid-node-address {
                        type types-sros:ip-address;
                        description
                            "Router ID of the immediate downstream node or the IP address of
                             the link that the PLR is trying to avoid.";
                    }

                    leaf is-inter-area {
                        type boolean;
                        description "Indicates whether the bypass tunnel is either inter-area or intra-area.";
                    }

                    leaf path-cost {
                        type uint32;
                        description "Indicates the total path cost for this bypass tunnel.";
                    }

                    leaf up-time {
                        type types-sros:time-interval;
                        description
                            "Indicates the total time in 10-millisecond units that the bypass tunnel
                             has been operational.";
                    }

                    leaf age {
                        type types-sros:time-interval;
                        description
                            "Age (i.e., time from creation till now) of this bypass tunnel
                             in 10-millisecond periods.";
                    }

                    leaf protected-lsp-count {
                        type yang:gauge32;
                        description "Number of LSPs that are protected by this bypass tunnel.";
                    }

                    leaf downstream-label {
                        type uint32;
                        description "Indicates the downstream-label for this bypass tunnel.";
                    }

                    leaf last-resignal-attempt {
                        type yang:date-and-time;
                        description "Indicates the last resignal attempt on this bypass tunnel.";
                    }

                    leaf last-resignal-attempt-reason {
                        type enumeration {
                            enum "none"                         { value 0; }
                            enum "timer-expiry"                 { value 1; }
                            enum "manual-resignal"              { value 2; }
                        }
                        description
                            "Indicates the reason for the last resignal attempt for this bypass
                             tunnel.";
                    }

                    leaf last-resignal {
                        type enumeration {
                            enum "none"                         { value 0; }
                            enum "not-attempted"                { value 1; }
                            enum "failed"                       { value 2; }
                            enum "successful"                   { value 3; }
                        }
                        description "Indicates the status of the last resignal attempt for this bypass tunnel.";
                    }

                    leaf last-resignal-reason {
                        type enumeration {
                            enum "none"                         { value 0; }
                            enum "path-optimal"                 { value 1; }
                            enum "no-connected-plrs"            { value 2; }
                            enum "node-prot-retry-in-prog"      { value 3; }
                            enum "resignal-in-prog"             { value 4; }
                            enum "node-prot-retry-bypass"       { value 5; }
                            enum "resignal-bypass"              { value 6; }
                            enum "cspf-failed"                  { value 7; }
                            enum "setup-failed"                 { value 8; }
                        }
                        description
                            "Indicates the reason why the last resignal attempt for this bypass
                             tunnel was not attempted or failed.";
                    }

                } // container bypass

                container detour {
                    description "RSVP session detour information.";

                    leaf plr-id {
                        type types-sros:ip-address;
                        description
                            "IP address that identifies the beginning point of detour which is a
                             PLR.";
                    }

                    leaf up-time {
                        type types-sros:time-interval;
                        description
                            "Total time in 10-millisecond units that the detour LSP
                             has been operational.";
                    }

                    leaf age {
                        type types-sros:time-interval;
                        description
                            "Age (i.e., time from creation till now) of this detour LSP
                             in 10-millisecond periods.";
                    }

                    leaf avoid-node-id {
                        type types-sros:ip-address;
                        description
                            "Router ID of the immediate downstream node that the PLR is trying
                             to avoid.";
                    }

                } // container detour

                container statistics {
                    description "RSVP session statistics.";

                    leaf path-received {
                        type yang:counter64;
                        description "The total number of RSVP PATH messages received for this RSVP session.";
                    }

                    leaf path-sent {
                        type yang:counter64;
                        description "The total number of RSVP PATH messages transmitted for this RSVP session.";
                    }

                    leaf resv-received {
                        type yang:counter64;
                        description "The total number of RSVP RESV messages received for this RSVP session.";
                    }

                    leaf resv-sent {
                        type yang:counter64;
                        description "The total number of RSVP RESV messages transmitted for this RSVP session.";
                    }

                    leaf spath-received {
                        type yang:counter64;
                        description
                            "Number of times PATH was refreshed using message ID from full PATH
                             refresh or Srefresh message for this RSVP session.";
                    }

                    leaf spath-sent {
                        type yang:counter64;
                        description
                            "Number of times PATH refresh for the session was sent as a part
                             of a Srefresh message.";
                    }

                    leaf sresv-received {
                        type yang:counter64;
                        description
                            "Number of times RESV was refreshed using message ID from full
                             RESV refresh or Srefresh message for this RSVP session.";
                    }

                    leaf sresv-sent {
                        type yang:counter64;
                        description
                            "Number of times RESV refresh for the session was sent as a part
                             of a Srefresh message.";
                    }

                } // container statistics

            } // list session

            container statistics {
                description "RSVP statistics.";

                leaf path-timeouts {
                    type yang:counter32;
                    description "Total number of PATH timeouts.";
                }

                leaf resv-timeouts {
                    type yang:counter32;
                    description "Total number of RESV timeouts.";
                }

                leaf gr-helper-path-timeouts {
                    type yang:counter32;
                    description
                        "Total number of PATH timeouts that occurred due to the session
                         not being recovered during recovery phase of the graceful
                         restart procedure.";
                }

                leaf gr-helper-resv-timeouts {
                    type yang:counter32;
                    description
                        "Total number of RESV timeouts that occurred due to the session
                         not being recovered during recovery phase of the graceful
                         restart procedure.";
                }

            } // container statistics

        } // container rsvp

    } // grouping state-router-rsvp

}
