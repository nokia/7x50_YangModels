submodule nokia-conf-submgt-local-user-db {

    yang-version "1.1";

    belongs-to nokia-conf { prefix "conf"; }

    import nokia-sros-yang-extensions     { prefix "sros-ext"; }
    import nokia-types-services           { prefix "types-services"; }
    import nokia-types-sros               { prefix "types-sros"; }
    import nokia-types-subscriber-mgmt    { prefix "types-submgt"; }

    include nokia-conf-groups;

    sros-ext:sros-major-release "rel19";

    organization "Nokia";

    contact
        "Nokia SR OS Support
         Web: <http://www.nokia.com>";

    description
        "Nokia YANG Data model to configure subscriber management local user database on SR OS based routers.

         Copyright 2016 Nokia. All rights reserved. Reproduction of this document
         is authorized on the condition that the foregoing copyright notice is included.

         This nokia-conf-submgt-local-user-db YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-10-09";

    grouping conf-submgt-local-user-db {
        list local-user-db {
            key "name";
            max-elements 127;
            description "Enter the local-user-db list instance";

            leaf name {
                type types-sros:named-item;
                description "Local user database name";
            }

            leaf admin-state {
                type types-sros:admin-state;
                default "disable";
                description "Administrative state of the local user database";
            }

            leaf description {
                type types-sros:description;
                description "Text description";
            }

            leaf-list apply-groups {
                type leafref {
                    path "../../../groups/group/name";
                }
                max-elements 8;
                ordered-by user;
                description "Apply a configuration group at this level";
            }

            container ipoe {
                description "Enter the ipoe context";

                leaf-list match-list {
                    type enumeration {
                        enum "circuit-id"                   { value 1; }
                        enum "mac"                          { value 2; }
                        enum "remote-id"                    { value 3; }
                        enum "sap-id"                       { value 4; }
                        enum "service-id"                   { value 5; }
                        enum "string"                       { value 6; }
                        enum "system-id"                    { value 7; }
                        enum "option60"                     { value 8; }
                        enum "encap-tag-range"              { value 9; }
                        enum "dual-stack-remote-id"         { value 10; }
                        enum "derived-id"                   { value 11; }
                        enum "ip"                           { value 12; }
                    }
                    max-elements 4;
                    ordered-by user;
                    sros-ext:auto-restart-to-modify;
                    description "IPoE host match type";
                }

                list mask {
                    key "type";
                    description "Enter the mask list instance";

                    leaf type {
                        type enumeration {
                            enum "circuit-id"                   { value 1; }
                            enum "remote-id"                    { value 3; }
                            enum "sap-id"                       { value 4; }
                            enum "string"                       { value 6; }
                            enum "system-id"                    { value 7; }
                            enum "option60"                     { value 8; }
                        }
                        description "Matching type to identify a host";
                    }

                    leaf-list apply-groups {
                        type leafref {
                            path "../../../../../groups/group/name";
                        }
                        max-elements 8;
                        ordered-by user;
                        description "Apply a configuration group at this level";
                    }

                    container prefix {
                        presence "prefix";
                        description "Enter the prefix context";

                        choice prefix {
                            mandatory true;
                            case length {

                                leaf length {
                                    type uint32 {
                                        range "1..127";
                                    }
                                    description "Prefix length";
                                }

                            }
                            case string {

                                leaf string {
                                    type string {
                                        length "1..127";
                                    }
                                    description "Prefix string";
                                }

                            }
                        }
                    } // container prefix

                    container suffix {
                        presence "suffix";
                        description "Enter the suffix context";

                        choice suffix {
                            mandatory true;
                            case length {

                                leaf length {
                                    type uint32 {
                                        range "1..127";
                                    }
                                    description "Suffix length";
                                }

                            }
                            case string {

                                leaf string {
                                    type string {
                                        length "1..127";
                                        pattern "[^*].*";
                                    }
                                    description "Suffix string";
                                }

                            }
                        }
                    } // container suffix

                } // list mask

                list host {
                    key "host-name";
                    description "Enter the host list instance";

                    leaf host-name {
                        type types-sros:named-item;
                        description "Host key";
                    }

                    leaf admin-state {
                        type types-sros:admin-state;
                        default "disable";
                        description "Administrative state of the host";
                    }

                    leaf retail-service-id {
                        type types-services:service-id-maf;
                        description "Configure the retail service-id";
                    }

                    leaf rip-policy {
                        type types-sros:named-item;
                        description "RIP policy";
                    }

                    leaf-list apply-groups {
                        type leafref {
                            path "../../../../../groups/group/name";
                        }
                        max-elements 8;
                        ordered-by user;
                        description "Apply a configuration group at this level";
                    }

                    container host-identification {
                        description "Enter the host-identification context";

                        leaf derived-id {
                            type types-sros:display-string;
                            description "Derived ID string";
                        }

                        leaf mac {
                            type types-sros:mac-unicast-address;
                            description "MAC address";
                        }

                        leaf sap-id {
                            type types-sros:display-string;
                            description "SAP ID";
                        }

                        leaf ip-prefix {
                            type types-sros:ip-prefix-with-host-bits;
                            description "IP interface name";
                        }

                        leaf string {
                            type types-sros:display-string;
                            description "VSO string";
                        }

                        leaf service-id {
                            type types-services:service-id-maf;
                            description "Service ID";
                        }

                        leaf system-id {
                            type types-sros:display-string;
                            description "System ID";
                        }

                        container circuit-id {
                            description "Enter the circuit-id context";

                            choice format {
                                case ascii-string {

                                    leaf ascii-string {
                                        type string {
                                            length "1..127";
                                        }
                                        description "Circuit ID as ASCII string";
                                    }

                                }
                                case hex-string {

                                    leaf hex-string {
                                        type types-sros:hex-string {
                                            length "1..256";
                                        }
                                        description "Circuit ID as hexadecimal string";
                                    }

                                }
                            }
                        } // container circuit-id

                        container remote-id {
                            description "Enter the remote-id context";

                            choice format {
                                case ascii-string {

                                    leaf ascii-string {
                                        type string {
                                            length "1..255";
                                        }
                                        description "Remote ID as ASCII string";
                                    }

                                }
                                case hex-string {

                                    leaf hex-string {
                                        type types-sros:hex-string {
                                            length "1..512";
                                        }
                                        description "Remote ID as hexadecimal string";
                                    }

                                }
                            }
                        } // container remote-id

                        container option60 {
                            description "Enter the option60 context";

                            choice format {
                                case ascii-string {

                                    leaf ascii-string {
                                        type types-sros:named-item;
                                        description "Option 60 as ASCII string";
                                    }

                                }
                                case hex-string {

                                    leaf hex-string {
                                        type types-sros:hex-string {
                                            length "1..64";
                                        }
                                        description "Option 60 as hexadecimal string";
                                    }

                                }
                            }
                        } // container option60

                        container encap-tag-range {
                            presence "encap-tag-range";
                            description "Enter the encap-tag-range context";

                            leaf from {
                                type types-sros:atm-or-vlan-encap;
                                mandatory true;
                                description "Start tag";
                            }

                            leaf to {
                                type types-sros:atm-or-vlan-encap;
                                mandatory true;
                                description "End tag";
                            }

                        } // container encap-tag-range

                    } // container host-identification

                    container authentication {
                        description "Enter the authentication context";

                        leaf radius-auth-policy {
                            type types-sros:named-item;
                            description "Host authentication policy";
                        }

                        leaf gx-policy {
                            type types-sros:named-item;
                            description "Diameter application policy";
                        }

                        leaf nasreq-auth-policy {
                            type types-sros:named-item;
                            description "Diameter NASREQ application policy to use for authentication";
                        }

                        leaf auth-domain-name {
                            type types-sros:named-item;
                            description "Authentication domain name for this host";
                        }

                    } // container authentication

                    container radius-accounting-policy {
                        description "Enter the radius-accounting-policy context";

                        leaf name {
                            type types-sros:named-item;
                            description "RADIUS accounting policy for generating accounting information";
                        }

                        leaf duplicate {
                            type types-sros:named-item;
                            description "RADIUS accounting policy for generating duplicate accounting information";
                        }

                    } // container radius-accounting-policy

                    container gtp-interface {
                        presence "gtp-interface";
                        description "Enter the gtp-interface context";

                        leaf name {
                            type types-sros:named-item;
                            mandatory true;
                            description "IP interface name";
                        }

                        leaf service-id {
                            type types-services:service-id-maf;
                            mandatory true;
                            description "Service ID";
                        }

                    } // container gtp-interface

                    container identification {
                        presence "identification";
                        description "Enter the identification context";

                        leaf option-number {
                            type uint32 {
                                range "1..254";
                            }
                            sros-ext:immutable;
                            default "254";
                            description "The option number used to return the strings in case the LUDB is linked to a DHCP server.";
                        }

                        leaf ancp-string {
                            type string {
                                length "1..63";
                            }
                            description "ANCP string";
                        }

                        leaf category-map-name {
                            type types-sros:named-item;
                            description "Category map name";
                        }

                        leaf int-dest-id {
                            type types-submgt:int-dest-id;
                            description "Intermediate destination ID";
                        }

                        leaf sla-profile-string {
                            type string {
                                length "1..32";
                            }
                            description "SLA profile string";
                        }

                        leaf sub-profile-string {
                            type string {
                                length "1..32";
                            }
                            description "Sub profile string";
                        }

                        leaf subscriber-id {
                            type types-sros:named-item;
                            description "Subscriber ID";
                        }

                        leaf spi-sharing-group-id {
                            type int32 {
                                range "0..65535";
                            }
                            description "SPI sharing group ID";
                        }

                    } // container identification

                    container match-radius-proxy-cache {
                        description "Enter the match-radius-proxy-cache context";

                        leaf fail-action {
                            type enumeration {
                                enum "continue"                     { value 1; }
                                enum "drop"                         { value 2; }
                            }
                            default "drop";
                            description "Action when no match is found";
                        }

                        leaf mac-format {
                            type types-submgt:mac-specification;
                            default "aa:";
                            description "MAC address format";
                        }

                        container match {
                            description "Enter the match context";

                            choice format {
                                default "mac";
                                case mac {

                                    leaf mac {
                                        type boolean;
                                        default "true";
                                        description "Match MAC address of DHCP client";
                                    }

                                }
                                case circuit-id {

                                    leaf circuit-id {
                                        type boolean;
                                        description "Match circuit ID in DHCP Option 82";
                                    }

                                }
                                case remote-id {

                                    leaf remote-id {
                                        type boolean;
                                        description "Match remote ID in DHCP Option 82";
                                    }

                                }
                                case option {

                                    leaf ipv4-option {
                                        type uint8 {
                                            range "1..254";
                                        }
                                        description "DHCP option number";
                                    }

                                    leaf ipv6-option {
                                        type uint32 {
                                            range "1..65535";
                                        }
                                        description "DHCPv6 option number";
                                    }

                                }
                            }
                        } // container match

                        container server {
                            presence "server";
                            description "Enter the server context";

                            leaf service {
                                type types-services:external-service-id;
                                description "Service ID";
                            }

                            leaf name {
                                type types-sros:named-item;
                                mandatory true;
                                description "Server Name";
                            }

                        } // container server

                    } // container match-radius-proxy-cache

                    container msap-defaults {
                        description "Enter the msap-defaults context";

                        leaf policy {
                            type types-sros:named-item;
                            description "MSAP policy";
                        }

                        leaf service {
                            type types-services:service-id-maf;
                            description "The service id.";
                        }

                        container group-interface {
                            presence "group-interface";
                            description "Enter the group-interface context";

                            leaf name {
                                type types-sros:named-item;
                                mandatory true;
                                description "IP interface name";
                            }

                            choice parameters {
                                case prefix {

                                    leaf prefix {
                                        type enumeration {
                                            enum "port-id"                      { value 2; }
                                        }
                                        description "prefix.";
                                    }

                                }
                                case suffix {

                                    leaf suffix {
                                        type enumeration {
                                            enum "port-id"                      { value 2; }
                                        }
                                        description "Suffix for the group interface";
                                    }

                                }
                            }
                        } // container group-interface

                    } // container msap-defaults

                    container wpp {
                        description "Enter the wpp context";

                        leaf restore-to-initial-on-disconnect {
                            type enumeration {
                                enum "restore"                      { value 1; }
                                enum "no-restore"                   { value 2; }
                            }
                            description "Restore initial profiles after a host has disconnected";
                        }

                        container portal {
                            description "Enter the portal context";

                            choice portal {
                                case portal {

                                    leaf router-instance {
                                        type union {
                                            type enumeration {
                                                enum "base"                         { value 0; }
                                            }
                                            type types-services:external-service-id;
                                        }
                                        default "base";
                                        description "The virtual router instance of the WPP portal for the hosts";
                                    }

                                    leaf name {
                                        type types-sros:named-item;
                                        description "Name for the WPP portal of the hosts";
                                    }

                                }
                                case portal-group {

                                    leaf portal-group {
                                        type types-sros:named-item;
                                        description "WPP portal group for this interface";
                                    }

                                }
                            }
                        } // container portal

                        container initial {
                            description "Enter the initial context";

                            leaf sub-profile {
                                type types-sros:named-item;
                                description "Initial subscriber profile";
                            }

                            leaf sla-profile {
                                type types-sros:named-item;
                                description "Initial SLA profile";
                            }

                        } // container initial

                    } // container wpp

                    container ipv4 {
                        description "Enter the ipv4 context";

                        leaf gi-address {
                            type types-sros:ipv4-unicast-address;
                            description "The DHCP gi-address of this host.";
                        }

                        leaf server {
                            type types-sros:ipv4-unicast-address;
                            description "IPv4 address of the DHCP server";
                        }

                        container address {
                            description "Enter the address context";

                            choice address {
                                case ip-address {

                                    leaf ip-address {
                                        type types-sros:ipv4-unicast-address;
                                        description "IPv4 host address";
                                    }

                                }
                                case gi-address {

                                    leaf gi-address {
                                        type enumeration {
                                            enum "subnet-scope"                 { value 0; }
                                            enum "pool-scope"                   { value 1; }
                                        }
                                        description "Use gi-address to select a pool with the given scope";
                                    }

                                }
                                case pool {

                                    container pool {
                                        presence "pool";
                                        description "Enter the pool context";

                                        leaf primary {
                                            type types-sros:named-item;
                                            mandatory true;
                                            description "Primary pool name";
                                        }

                                        leaf secondary {
                                            type types-sros:named-item;
                                            description "Secondary pool name";
                                        }

                                        leaf delimiter {
                                            type string {
                                                length "1";
                                            }
                                            description "Delimiter character to combine primary and secondary pool names";
                                        }

                                    } // container pool

                                }
                                case use-pool-from-client {

                                    container use-pool-from-client {
                                        presence "use-pool-from-client";
                                        description "Enter the use-pool-from-client context";

                                        leaf delimiter {
                                            type string {
                                                length "1";
                                            }
                                            description "Delimiter character to combine primary and secondary pool names";
                                        }

                                    } // container use-pool-from-client

                                }
                            }
                        } // container address

                        list option {
                            key "number";
                            description "Enter the option list instance";

                            leaf number {
                                type union {
                                    type uint32 {
                                        range "1..254";
                                    }
                                    type enumeration {
                                        enum "subnet-mask"                  { value 1; }
                                        enum "default-router"               { value 3; }
                                        enum "dns-server"                   { value 6; }
                                        enum "domain-name"                  { value 15; }
                                        enum "netbios-name-server"          { value 44; }
                                        enum "netbios-node-type"            { value 46; }
                                        enum "lease-time"                   { value 51; }
                                        enum "lease-renew-time"             { value 58; }
                                        enum "lease-rebind-time"            { value 59; }
                                    }
                                }
                                description "DHCP option to send identification strings to client";
                            }

                            leaf-list apply-groups {
                                type leafref {
                                    path "../../../../../../../groups/group/name";
                                }
                                max-elements 8;
                                ordered-by user;
                                description "Apply a configuration group at this level";
                            }

                            choice value {
                                mandatory true;
                                description "The value of the DHCP option.";
                                case ascii-string {

                                    leaf ascii-string {
                                        when "not(../number = 46) and not(../number = 51) and not(../number = 58) and not(../number = 59)";
                                        type types-sros:string-not-all-spaces {
                                            length "1..127";
                                        }
                                        description "DHCP option specified as an ASCII string";
                                    }

                                }
                                case hex-string {

                                    leaf hex-string {
                                        when "not(../number = 46) and not(../number = 51) and not(../number = 58) and not(../number = 59)";
                                        type types-sros:hex-string {
                                            length "1..256";
                                        }
                                        description "DHCP option specified as hexadecimal string";
                                    }

                                }
                                case netbios-node-type {

                                    leaf netbios-node-type {
                                        when "../number = 46";
                                        type enumeration {
                                            enum "b-node"                       { value 1; }
                                            enum "p-node"                       { value 2; }
                                            enum "m-node"                       { value 4; }
                                            enum "h-node"                       { value 8; }
                                        }
                                        description "DHCP option as NetBIOS node type";
                                    }

                                }
                                case duration {

                                    leaf duration {
                                        when "../number = 51 or ../number = 58 or ../number = 59";
                                        type types-sros:time-duration {
                                            range "10..315446399";
                                        }
                                        units "seconds";
                                        description "DHCP option as time duration";
                                    }

                                }
                                case ipv4-address {

                                    leaf-list ipv4-address {
                                        when "not(../number = 46) and not(../number = 51) and not(../number = 58) and not(../number = 59)";
                                        type types-sros:ipv4-address;
                                        max-elements 4;
                                        description "DHCP option as a list of IPv4 addresses";
                                    }

                                }
                                case empty {

                                    leaf empty {
                                        when "not(../number = 46) and not(../number = 51) and not(../number = 58) and not(../number = 59)";
                                        type empty;
                                        description "Empty DHCP option.";
                                    }

                                }
                            }
                        } // list option

                    } // container ipv4

                    container ipv6 {
                        description "Enter the ipv6 context";

                        leaf address {
                            type types-sros:ipv6-unicast-address;
                            description "IPv6 address of this host";
                        }

                        leaf address-pool {
                            type types-sros:named-item;
                            description "IPv6 address pool name";
                        }

                        leaf delegated-prefix {
                            type types-sros:ipv6-unicast-prefix;
                            description "IPv6 delegated prefix of this host";
                        }

                        leaf delegated-prefix-length {
                            type uint32 {
                                range "48..64";
                            }
                            description "Delegated prefix length";
                        }

                        leaf delegated-prefix-pool {
                            type types-sros:named-item;
                            description "Delegated prefix pool";
                        }

                        leaf slaac-prefix {
                            type types-sros:ipv6-unicast-prefix;
                            description "IPv6 SLAAC prefix of this host";
                        }

                        leaf slaac-prefix-pool {
                            type types-sros:named-item;
                            description "IPv6 SLAAC prefix pool of this host";
                        }

                        leaf router-advertisement-policy {
                            type types-sros:named-item;
                            description "IPv6 router advertisement policy";
                        }

                        leaf server {
                            type types-sros:ipv6-unicast-address;
                            description "IPv6 address of the DHCP server";
                        }

                        leaf link-address {
                            type types-sros:ipv6-unicast-address;
                            description "The DHCP Relay link-address.";
                        }

                        container timers {
                            description "Enter the timers context";

                            leaf preferred-lifetime {
                                type union {
                                    type types-sros:time-duration {
                                        range "300..315446399";
                                    }
                                    type enumeration {
                                        enum "infinite"                     { value -1; }
                                    }
                                }
                                units "seconds";
                                description "Time for a lease to remain preferred";
                            }

                            leaf rebind {
                                type types-sros:time-duration {
                                    range "0..1209600";
                                }
                                units "seconds";
                                description "Rebind timer (T2)";
                            }

                            leaf renew {
                                type types-sros:time-duration {
                                    range "0..604800";
                                }
                                units "seconds";
                                description "Renew timer (T1)";
                            }

                            leaf valid-lifetime {
                                type union {
                                    type types-sros:time-duration {
                                        range "300..315446399";
                                    }
                                    type enumeration {
                                        enum "infinite"                     { value -1; }
                                    }
                                }
                                units "seconds";
                                description "Time for a lease to remain valid";
                            }

                        } // container timers

                        list option {
                            key "number";
                            description "Enter the option list instance";

                            leaf number {
                                type union {
                                    type uint32 {
                                        range "23";
                                    }
                                    type enumeration {
                                        enum "dns-server"                   { value 23; }
                                    }
                                }
                                description "The number of the DHCPv6 option.";
                            }

                            leaf-list apply-groups {
                                type leafref {
                                    path "../../../../../../../groups/group/name";
                                }
                                max-elements 8;
                                ordered-by user;
                                description "Apply a configuration group at this level";
                            }

                            choice value {
                                mandatory true;
                                description "The value of the DHCP option.";
                                case hex-string {

                                    leaf hex-string {
                                        type types-sros:hex-string {
                                            length "1..256";
                                        }
                                        description "DHCP option specified as hexadecimal string";
                                    }

                                }
                                case ipv6-address {

                                    leaf-list ipv6-address {
                                        type types-sros:ipv6-address;
                                        max-elements 4;
                                        description "DHCP option specified as a list of IPv6 addresses";
                                    }

                                }
                            }
                        } // list option

                    } // container ipv6

                    list mld-import {
                        key "policy-name";
                        max-elements 14;
                        description "Add a list entry for mld-import";

                        leaf policy-name {
                            type types-sros:named-item;
                            description "MLD import policy for this host";
                        }

                    } // list mld-import

                    container to-client-options {
                        description "Enter the to-client-options context";

                        list ipv4-option {
                            key "number";
                            description "Enter the ipv4-option list instance";

                            leaf number {
                                type union {
                                    type uint32 {
                                        range "1..254";
                                    }
                                    type enumeration {
                                        enum "subnet-mask"                  { value 1; }
                                        enum "default-router"               { value 3; }
                                        enum "dns-server"                   { value 6; }
                                        enum "domain-name"                  { value 15; }
                                        enum "netbios-name-server"          { value 44; }
                                        enum "netbios-node-type"            { value 46; }
                                        enum "lease-time"                   { value 51; }
                                        enum "lease-renew-time"             { value 58; }
                                        enum "lease-rebind-time"            { value 59; }
                                    }
                                }
                                description "DHCP option to send identification strings to client";
                            }

                            leaf-list apply-groups {
                                type leafref {
                                    path "../../../../../../../groups/group/name";
                                }
                                max-elements 8;
                                ordered-by user;
                                description "Apply a configuration group at this level";
                            }

                            choice value {
                                mandatory true;
                                description "The value of the DHCP option.";
                                case ascii-string {

                                    leaf ascii-string {
                                        type types-sros:string-not-all-spaces {
                                            length "1..127";
                                        }
                                        description "DHCP option specified as an ASCII string";
                                    }

                                }
                                case hex-string {

                                    leaf hex-string {
                                        type types-sros:hex-string {
                                            length "1..256";
                                        }
                                        description "DHCP option specified as hexadecimal string";
                                    }

                                }
                                case netbios-node-type {

                                    leaf netbios-node-type {
                                        when "../number = 46";
                                        type enumeration {
                                            enum "b-node"                       { value 1; }
                                            enum "p-node"                       { value 2; }
                                            enum "m-node"                       { value 4; }
                                            enum "h-node"                       { value 8; }
                                        }
                                        description "DHCP option as NetBIOS node type";
                                    }

                                }
                                case duration {

                                    leaf duration {
                                        when "../number = 51 or ../number = 58 or ../number = 59";
                                        type types-sros:time-duration {
                                            range "10..315446399";
                                        }
                                        units "seconds";
                                        description "DHCP option as time duration";
                                    }

                                }
                                case ipv4-address {

                                    leaf-list ipv4-address {
                                        when "not(../number = 46) and not(../number = 51) and not(../number = 58) and not(../number = 59)";
                                        type types-sros:ipv4-address;
                                        max-elements 4;
                                        description "DHCP option as a list of IPv4 addresses";
                                    }

                                }
                                case empty {

                                    leaf empty {
                                        type empty;
                                        description "Empty DHCP option";
                                    }

                                }
                            }
                        } // list ipv4-option

                        list ipv6-option {
                            key "number";
                            description "Enter the ipv6-option list instance";

                            leaf number {
                                type union {
                                    type uint32 {
                                        range "1..65535";
                                    }
                                    type enumeration {
                                        enum "dns-server"                   { value 23; }
                                        enum "domain-name"                  { value 24; }
                                    }
                                }
                                description "DHCP option number";
                            }

                            leaf-list apply-groups {
                                type leafref {
                                    path "../../../../../../../groups/group/name";
                                }
                                max-elements 8;
                                ordered-by user;
                                description "Apply a configuration group at this level";
                            }

                            choice value {
                                mandatory true;
                                description "The value of the DHCP option.";
                                case ascii-string {

                                    leaf ascii-string {
                                        type types-sros:string-not-all-spaces {
                                            length "1..127";
                                        }
                                        description "DHCP option specified as an ASCII string";
                                    }

                                }
                                case hex-string {

                                    leaf hex-string {
                                        type types-sros:hex-string {
                                            length "1..256";
                                        }
                                        description "DHCP option specified as hexadecimal string";
                                    }

                                }
                                case domain-string {

                                    leaf domain-string {
                                        type string {
                                            length "1..127";
                                            pattern "[a-z0-9\\-]+(\\.[a-z0-9\\-]+)*";
                                        }
                                        description "DHCP option specified as a domain name";
                                    }

                                }
                                case ipv6-address {

                                    leaf-list ipv6-address {
                                        type types-sros:ipv6-address;
                                        max-elements 4;
                                        description "DHCP option specified as a list of IPv6 addresses";
                                    }

                                }
                                case empty {

                                    leaf empty {
                                        type empty;
                                        description "Empty DHCP option";
                                    }

                                }
                            }
                        } // list ipv6-option

                    } // container to-client-options

                    container to-server-options {
                        description "Enter the to-server-options context";

                        list ipv6-option {
                            key "number";
                            description "Enter the ipv6-option list instance";

                            leaf number {
                                type union {
                                    type uint32 {
                                        range "1..65535";
                                    }
                                    type enumeration {
                                        enum "dns-server"                   { value 23; }
                                        enum "domain-name"                  { value 24; }
                                    }
                                }
                                description "DHCP option number";
                            }

                            leaf-list apply-groups {
                                type leafref {
                                    path "../../../../../../../groups/group/name";
                                }
                                max-elements 8;
                                ordered-by user;
                                description "Apply a configuration group at this level";
                            }

                            choice value {
                                mandatory true;
                                description "The value of the DHCP option.";
                                case ascii-string {

                                    leaf ascii-string {
                                        type types-sros:string-not-all-spaces {
                                            length "1..127";
                                        }
                                        description "DHCP option specified as an ASCII string";
                                    }

                                }
                                case hex-string {

                                    leaf hex-string {
                                        type types-sros:hex-string {
                                            length "1..256";
                                        }
                                        description "DHCP option specified as hexadecimal string";
                                    }

                                }
                                case domain-string {

                                    leaf domain-string {
                                        type string {
                                            length "1..127";
                                            pattern "[a-z0-9\\-]+(\\.[a-z0-9\\-]+)*";
                                        }
                                        description "DHCP option specified as a domain name";
                                    }

                                }
                                case ipv6-address {

                                    leaf-list ipv6-address {
                                        type types-sros:ipv6-address;
                                        max-elements 4;
                                        description "DHCP option specified as a list of IPv6 addresses";
                                    }

                                }
                                case empty {

                                    leaf empty {
                                        type empty;
                                        description "Empty DHCP option";
                                    }

                                }
                            }
                        } // list ipv6-option

                    } // container to-server-options

                } // list host

            } // container ipoe

            container ppp {
                description "Enter the ppp context";

                leaf-list match-list {
                    type enumeration {
                        enum "circuit-id"                   { value 1; }
                        enum "mac"                          { value 2; }
                        enum "remote-id"                    { value 3; }
                        enum "user-name"                    { value 4; }
                        enum "service-name"                 { value 5; }
                        enum "sap-id"                       { value 6; }
                        enum "encap-tag-range"              { value 7; }
                        enum "derived-id"                   { value 8; }
                    }
                    max-elements 3;
                    ordered-by user;
                    sros-ext:auto-restart-to-modify;
                    description "PPP host match criteria";
                }

                list mask {
                    key "type";
                    description "Enter the mask list instance";

                    leaf type {
                        type enumeration {
                            enum "circuit-id"                   { value 1; }
                            enum "remote-id"                    { value 3; }
                            enum "user-name"                    { value 4; }
                            enum "service-name"                 { value 5; }
                            enum "sap-id"                       { value 6; }
                        }
                        description "Matching type to identify a host";
                    }

                    leaf-list apply-groups {
                        type leafref {
                            path "../../../../../groups/group/name";
                        }
                        max-elements 8;
                        ordered-by user;
                        description "Apply a configuration group at this level";
                    }

                    container prefix {
                        presence "prefix";
                        description "Enter the prefix context";

                        choice prefix {
                            mandatory true;
                            case length {

                                leaf length {
                                    type uint32 {
                                        range "1..127";
                                    }
                                    description "Prefix length";
                                }

                            }
                            case string {

                                leaf string {
                                    type string {
                                        length "1..127";
                                    }
                                    description "Prefix string";
                                }

                            }
                        }
                    } // container prefix

                    container suffix {
                        presence "suffix";
                        description "Enter the suffix context";

                        choice suffix {
                            mandatory true;
                            case length {

                                leaf length {
                                    type uint32 {
                                        range "1..127";
                                    }
                                    description "Suffix length";
                                }

                            }
                            case string {

                                leaf string {
                                    type string {
                                        length "1..127";
                                        pattern "[^*].*";
                                    }
                                    description "Suffix string";
                                }

                            }
                        }
                    } // container suffix

                } // list mask

                list host {
                    key "host-name";
                    description "Enter the host list instance";

                    leaf host-name {
                        type types-sros:named-item;
                        description "Host key";
                    }

                    leaf admin-state {
                        type types-sros:admin-state;
                        default "disable";
                        description "Administrative state of the host";
                    }

                    leaf retail-service-id {
                        type types-services:service-id-maf;
                        description "Configure the retail service-id";
                    }

                    leaf rip-policy {
                        type types-sros:named-item;
                        description "RIP policy";
                    }

                    leaf pado-delay {
                        type types-sros:time-duration {
                            range "1..30";
                        }
                        units "deciseconds";
                        description "Delay timeout before sending a PADO";
                    }

                    leaf steering-profile {
                        type types-sros:named-item;
                        description "Steering profile";
                    }

                    leaf-list apply-groups {
                        type leafref {
                            path "../../../../../groups/group/name";
                        }
                        max-elements 8;
                        ordered-by user;
                        description "Apply a configuration group at this level";
                    }

                    container host-identification {
                        description "Enter the host-identification context";

                        leaf derived-id {
                            type types-sros:display-string;
                            description "Derived ID string";
                        }

                        leaf mac {
                            type types-sros:mac-unicast-address;
                            description "MAC address";
                        }

                        leaf sap-id {
                            type types-sros:display-string;
                            description "SAP ID";
                        }

                        leaf service-name {
                            type types-sros:display-string;
                            description "Service name";
                        }

                        container circuit-id {
                            description "Enter the circuit-id context";

                            choice format {
                                case ascii-string {

                                    leaf ascii-string {
                                        type string {
                                            length "1..127";
                                        }
                                        description "Circuit ID as ASCII string";
                                    }

                                }
                                case hex-string {

                                    leaf hex-string {
                                        type types-sros:hex-string {
                                            length "1..256";
                                        }
                                        description "Circuit ID as hexadecimal string";
                                    }

                                }
                            }
                        } // container circuit-id

                        container remote-id {
                            description "Enter the remote-id context";

                            choice format {
                                case ascii-string {

                                    leaf ascii-string {
                                        type string {
                                            length "1..255";
                                        }
                                        description "Remote ID as ASCII string";
                                    }

                                }
                                case hex-string {

                                    leaf hex-string {
                                        type types-sros:hex-string {
                                            length "1..512";
                                        }
                                        description "Remote ID as hexadecimal string";
                                    }

                                }
                            }
                        } // container remote-id

                        container encap-tag-range {
                            presence "encap-tag-range";
                            description "Enter the encap-tag-range context";

                            leaf from {
                                type types-sros:atm-or-vlan-encap;
                                mandatory true;
                                description "Start tag";
                            }

                            leaf to {
                                type types-sros:atm-or-vlan-encap;
                                mandatory true;
                                description "End tag";
                            }

                        } // container encap-tag-range

                        container user-name {
                            presence "user-name";
                            description "Enter the user-name context";

                            leaf name {
                                type types-sros:display-string {
                                    length "1..253";
                                }
                                mandatory true;
                                description "Full or part of PPP user name as specified with the format.";
                            }

                            leaf format {
                                type enumeration {
                                    enum "full"                         { value 1; }
                                    enum "no-domain"                    { value 2; }
                                    enum "domain-only"                  { value 3; }
                                }
                                default "full";
                                description "User name format.";
                            }

                        } // container user-name

                    } // container host-identification

                    container authentication {
                        description "Enter the authentication context";

                        leaf radius-auth-policy {
                            type types-sros:named-item;
                            description "Host authentication policy";
                        }

                        leaf gx-policy {
                            type types-sros:named-item;
                            description "Diameter application policy";
                        }

                        leaf nasreq-auth-policy {
                            type types-sros:named-item;
                            description "Diameter NASREQ application policy to use for authentication";
                        }

                        leaf padi-auth-policy {
                            type types-sros:named-item;
                            description "Authentication policy name";
                        }

                        leaf pre-auth-policy {
                            type types-sros:named-item;
                            description "Pre-authentication policy of this host";
                        }

                        leaf user-db {
                            type types-sros:named-item;
                            description "Local user DB to use for PPP PAP/CHAP authentication";
                        }

                    } // container authentication

                    container lns-interface {
                        presence "lns-interface";
                        description "Enter the lns-interface context";

                        leaf name {
                            type types-sros:named-item;
                            mandatory true;
                            description "IP interface name";
                        }

                        leaf service-id {
                            type types-services:service-id-maf;
                            mandatory true;
                            description "Service ID";
                        }

                    } // container lns-interface

                    container radius-accounting-policy {
                        description "Enter the radius-accounting-policy context";

                        leaf name {
                            type types-sros:named-item;
                            description "RADIUS accounting policy for generating accounting information";
                        }

                        leaf duplicate {
                            type types-sros:named-item;
                            description "RADIUS accounting policy for generating duplicate accounting information";
                        }

                    } // container radius-accounting-policy

                    container identification {
                        presence "identification";
                        description "Enter the identification context";

                        leaf option-number {
                            type uint32 {
                                range "1..254";
                            }
                            sros-ext:immutable;
                            default "254";
                            description "The option number used to return the strings in case the LUDB is linked to a DHCP server.";
                        }

                        leaf ancp-string {
                            type string {
                                length "1..63";
                            }
                            description "ANCP string";
                        }

                        leaf category-map-name {
                            type types-sros:named-item;
                            description "Category map name";
                        }

                        leaf int-dest-id {
                            type types-submgt:int-dest-id;
                            description "Intermediate destination ID";
                        }

                        leaf sla-profile-string {
                            type string {
                                length "1..32";
                            }
                            description "SLA profile string";
                        }

                        leaf sub-profile-string {
                            type string {
                                length "1..32";
                            }
                            description "Sub profile string";
                        }

                        leaf subscriber-id {
                            type types-sros:named-item;
                            description "Subscriber ID";
                        }

                        leaf spi-sharing-group-id {
                            type int32 {
                                range "0..65535";
                            }
                            description "SPI sharing group ID";
                        }

                    } // container identification

                    container msap-defaults {
                        description "Enter the msap-defaults context";

                        leaf policy {
                            type types-sros:named-item;
                            description "MSAP policy";
                        }

                        leaf service {
                            type types-services:service-id-maf;
                            description "The service id.";
                        }

                        container group-interface {
                            presence "group-interface";
                            description "Enter the group-interface context";

                            leaf name {
                                type types-sros:named-item;
                                mandatory true;
                                description "IP interface name";
                            }

                            choice parameters {
                                case prefix {

                                    leaf prefix {
                                        type enumeration {
                                            enum "port-id"                      { value 2; }
                                        }
                                        description "prefix.";
                                    }

                                }
                                case suffix {

                                    leaf suffix {
                                        type enumeration {
                                            enum "port-id"                      { value 2; }
                                        }
                                        description "Suffix for the group interface";
                                    }

                                }
                            }
                        } // container group-interface

                    } // container msap-defaults

                    container access-loop-information {
                        description "Enter the access-loop-information context";

                        container circuit-id {
                            presence "circuit-id";
                            description "Enter the circuit-id context";

                            choice format {
                                mandatory true;
                                case ascii-string {

                                    leaf ascii-string {
                                        type string {
                                            length "1..63";
                                        }
                                        description "Circuit ID as an ASCII string";
                                    }

                                }
                                case sap-id {

                                    leaf sap-id {
                                        type boolean;
                                        description "SAP ID as circuit ID";
                                    }

                                }
                            }
                        } // container circuit-id

                        container remote-id {
                            presence "remote-id";
                            description "Enter the remote-id context";

                            choice format {
                                mandatory true;
                                case ascii-string {

                                    leaf ascii-string {
                                        type string {
                                            length "1..63";
                                        }
                                        description "Remote-id as an ASCII string.";
                                    }

                                }
                                case mac {

                                    leaf mac {
                                        type boolean;
                                        description "Use MAC address as remote ID";
                                    }

                                }
                            }
                        } // container remote-id

                    } // container access-loop-information

                    container l2tp {
                        description "Enter the l2tp context";

                        container group {
                            presence "group";
                            description "Enter the group context";

                            leaf name {
                                type string {
                                    length "1..63";
                                }
                                mandatory true;
                                description "Tunnel group name";
                            }

                            leaf service-id {
                                type types-services:external-service-id;
                                description "Service-id for group.";
                            }

                        } // container group

                    } // container l2tp

                    container password {
                        description "Enter the password context";

                        choice password {
                            case pap {

                                leaf pap {
                                    type types-sros:encrypted-leaf {
                                        length "1..115";
                                    }
                                    description "PAP protocol.";
                                }

                            }
                            case chap {

                                leaf chap {
                                    type types-sros:encrypted-leaf {
                                        length "1..115";
                                    }
                                    description "CHAP protocol";
                                }

                            }
                            case ignore {

                                leaf ignore {
                                    type empty;
                                    description "Ignore.";
                                }

                            }
                        }
                    } // container password

                    container access-loop-encapsulation {
                        presence "access-loop-encapsulation";
                        description "Enter the access-loop-encapsulation context";

                        leaf rate-down {
                            type uint32 {
                                range "1..100000";
                            }
                            units "kilobps";
                            description "Last mile link downstream rate in the access loop";
                        }

                        leaf-list apply-groups {
                            type leafref {
                                path "../../../../../../groups/group/name";
                            }
                            max-elements 8;
                            ordered-by user;
                            description "Apply a configuration group at this level";
                        }

                        container encap-offset {
                            description "Enter the encap-offset context";

                            leaf type {
                                type enumeration {
                                    enum "pppoa-llc"                    { value 1; }
                                    enum "pppoa-null"                   { value 2; }
                                    enum "pppoeoa-llc"                  { value 3; }
                                    enum "pppoeoa-llc-fcs"              { value 4; }
                                    enum "pppoeoa-llc-tagged"           { value 5; }
                                    enum "pppoeoa-llc-tagged-fcs"       { value 6; }
                                    enum "pppoeoa-null"                 { value 7; }
                                    enum "pppoeoa-null-fcs"             { value 8; }
                                    enum "pppoeoa-null-tagged"          { value 9; }
                                    enum "pppoeoa-null-tagged-fcs"      { value 10; }
                                    enum "ipoa-llc"                     { value 11; }
                                    enum "ipoa-null"                    { value 12; }
                                    enum "ipoeoa-llc"                   { value 13; }
                                    enum "ipoeoa-llc-fcs"               { value 14; }
                                    enum "ipoeoa-llc-tagged"            { value 15; }
                                    enum "ipoeoa-llc-tagged-fcs"        { value 16; }
                                    enum "ipoeoa-null"                  { value 17; }
                                    enum "ipoeoa-null-fcs"              { value 18; }
                                    enum "ipoeoa-null-tagged"           { value 19; }
                                    enum "ipoeoa-null-tagged-fcs"       { value 20; }
                                    enum "pppoe"                        { value 21; }
                                    enum "pppoe-tagged"                 { value 22; }
                                    enum "ipoe"                         { value 23; }
                                    enum "ipoe-tagged"                  { value 24; }
                                }
                                description "Egress encapsulation type";
                            }

                        } // container encap-offset

                    } // container access-loop-encapsulation

                    container ipv4 {
                        description "Enter the ipv4 context";

                        leaf ignore-df-bit {
                            type boolean;
                            default "false";
                            description "Ignore the DF bit in the IPv4 header when fragmenting";
                        }

                        container address {
                            description "Enter the address context";

                            choice address {
                                case ip-address {

                                    leaf ip-address {
                                        type types-sros:ipv4-unicast-address;
                                        description "IPv4 host address";
                                    }

                                }
                                case gi-address {

                                    leaf gi-address {
                                        type enumeration {
                                            enum "subnet-scope"                 { value 0; }
                                            enum "pool-scope"                   { value 1; }
                                        }
                                        description "Use gi-address to select a pool with the given scope";
                                    }

                                }
                                case pool {

                                    container pool {
                                        presence "pool";
                                        description "Enter the pool context";

                                        leaf primary {
                                            type types-sros:named-item;
                                            mandatory true;
                                            description "Primary pool name";
                                        }

                                        leaf secondary {
                                            type types-sros:named-item;
                                            description "Secondary pool name";
                                        }

                                        leaf delimiter {
                                            type string {
                                                length "1";
                                            }
                                            description "Delimiter character to combine primary and secondary pool names";
                                        }

                                    } // container pool

                                }
                                case use-pool-from-client {

                                    container use-pool-from-client {
                                        presence "use-pool-from-client";
                                        description "Enter the use-pool-from-client context";

                                        leaf delimiter {
                                            type string {
                                                length "1";
                                            }
                                            description "Delimiter character to combine primary and secondary pool names";
                                        }

                                    } // container use-pool-from-client

                                }
                            }
                        } // container address

                        list option {
                            key "number";
                            description "Enter the option list instance";

                            leaf number {
                                type union {
                                    type uint32 {
                                        range "1..254";
                                    }
                                    type enumeration {
                                        enum "subnet-mask"                  { value 1; }
                                        enum "default-router"               { value 3; }
                                        enum "dns-server"                   { value 6; }
                                        enum "domain-name"                  { value 15; }
                                        enum "netbios-name-server"          { value 44; }
                                        enum "netbios-node-type"            { value 46; }
                                        enum "lease-time"                   { value 51; }
                                        enum "lease-renew-time"             { value 58; }
                                        enum "lease-rebind-time"            { value 59; }
                                    }
                                }
                                description "DHCP option to send identification strings to client";
                            }

                            leaf-list apply-groups {
                                type leafref {
                                    path "../../../../../../../groups/group/name";
                                }
                                max-elements 8;
                                ordered-by user;
                                description "Apply a configuration group at this level";
                            }

                            choice value {
                                mandatory true;
                                description "The value of the DHCP option.";
                                case ascii-string {

                                    leaf ascii-string {
                                        when "not(../number = 46) and not(../number = 51) and not(../number = 58) and not(../number = 59)";
                                        type types-sros:string-not-all-spaces {
                                            length "1..127";
                                        }
                                        description "DHCP option specified as an ASCII string";
                                    }

                                }
                                case hex-string {

                                    leaf hex-string {
                                        when "not(../number = 46) and not(../number = 51) and not(../number = 58) and not(../number = 59)";
                                        type types-sros:hex-string {
                                            length "1..256";
                                        }
                                        description "DHCP option specified as hexadecimal string";
                                    }

                                }
                                case netbios-node-type {

                                    leaf netbios-node-type {
                                        when "../number = 46";
                                        type enumeration {
                                            enum "b-node"                       { value 1; }
                                            enum "p-node"                       { value 2; }
                                            enum "m-node"                       { value 4; }
                                            enum "h-node"                       { value 8; }
                                        }
                                        description "DHCP option as NetBIOS node type";
                                    }

                                }
                                case duration {

                                    leaf duration {
                                        when "../number = 51 or ../number = 58 or ../number = 59";
                                        type types-sros:time-duration {
                                            range "10..315446399";
                                        }
                                        units "seconds";
                                        description "DHCP option as time duration";
                                    }

                                }
                                case ipv4-address {

                                    leaf-list ipv4-address {
                                        when "not(../number = 46) and not(../number = 51) and not(../number = 58) and not(../number = 59)";
                                        type types-sros:ipv4-address;
                                        max-elements 4;
                                        description "DHCP option as a list of IPv4 addresses";
                                    }

                                }
                                case empty {

                                    leaf empty {
                                        when "not(../number = 46) and not(../number = 51) and not(../number = 58) and not(../number = 59)";
                                        type empty;
                                        description "Empty DHCP option.";
                                    }

                                }
                            }
                        } // list option

                    } // container ipv4

                    container ipv6 {
                        description "Enter the ipv6 context";

                        leaf address {
                            type types-sros:ipv6-unicast-address;
                            description "IPv6 address of this host";
                        }

                        leaf address-pool {
                            type types-sros:named-item;
                            description "IPv6 address pool name";
                        }

                        leaf delegated-prefix {
                            type types-sros:ipv6-unicast-prefix;
                            description "IPv6 delegated prefix of this host";
                        }

                        leaf delegated-prefix-length {
                            type uint32 {
                                range "48..64";
                            }
                            description "Delegated prefix length";
                        }

                        leaf delegated-prefix-pool {
                            type types-sros:named-item;
                            description "Delegated prefix pool";
                        }

                        leaf slaac-prefix {
                            type types-sros:ipv6-unicast-prefix;
                            description "IPv6 SLAAC prefix of this host";
                        }

                        leaf slaac-prefix-pool {
                            type types-sros:named-item;
                            description "IPv6 SLAAC prefix pool of this host";
                        }

                        leaf router-advertisement-policy {
                            type types-sros:named-item;
                            description "IPv6 router advertisement policy";
                        }

                        leaf force-ipv6cp {
                            type boolean;
                            default "false";
                            description "forces ipv6 control protocol.";
                        }

                        container timers {
                            description "Enter the timers context";

                            leaf preferred-lifetime {
                                type union {
                                    type types-sros:time-duration {
                                        range "300..315446399";
                                    }
                                    type enumeration {
                                        enum "infinite"                     { value -1; }
                                    }
                                }
                                units "seconds";
                                description "Time for a lease to remain preferred";
                            }

                            leaf rebind {
                                type types-sros:time-duration {
                                    range "0..1209600";
                                }
                                units "seconds";
                                description "Rebind timer (T2)";
                            }

                            leaf renew {
                                type types-sros:time-duration {
                                    range "0..604800";
                                }
                                units "seconds";
                                description "Renew timer (T1)";
                            }

                            leaf valid-lifetime {
                                type union {
                                    type types-sros:time-duration {
                                        range "300..315446399";
                                    }
                                    type enumeration {
                                        enum "infinite"                     { value -1; }
                                    }
                                }
                                units "seconds";
                                description "Time for a lease to remain valid";
                            }

                        } // container timers

                        list option {
                            key "number";
                            description "Enter the option list instance";

                            leaf number {
                                type union {
                                    type uint32 {
                                        range "23";
                                    }
                                    type enumeration {
                                        enum "dns-server"                   { value 23; }
                                    }
                                }
                                description "The number of the DHCPv6 option.";
                            }

                            leaf-list apply-groups {
                                type leafref {
                                    path "../../../../../../../groups/group/name";
                                }
                                max-elements 8;
                                ordered-by user;
                                description "Apply a configuration group at this level";
                            }

                            choice value {
                                mandatory true;
                                description "The value of the DHCP option.";
                                case hex-string {

                                    leaf hex-string {
                                        type types-sros:hex-string {
                                            length "1..256";
                                        }
                                        description "DHCP option specified as hexadecimal string";
                                    }

                                }
                                case ipv6-address {

                                    leaf-list ipv6-address {
                                        type types-sros:ipv6-address;
                                        max-elements 4;
                                        description "DHCP option specified as a list of IPv6 addresses";
                                    }

                                }
                            }
                        } // list option

                    } // container ipv6

                    list mld-import {
                        key "policy-name";
                        max-elements 14;
                        description "Add a list entry for mld-import";

                        leaf policy-name {
                            type types-sros:named-item;
                            description "MLD import policy for this host";
                        }

                    } // list mld-import

                    container to-client-options {
                        description "Enter the to-client-options context";

                        list ipv6-option {
                            key "number";
                            description "Enter the ipv6-option list instance";

                            leaf number {
                                type union {
                                    type uint32 {
                                        range "1..65535";
                                    }
                                    type enumeration {
                                        enum "dns-server"                   { value 23; }
                                        enum "domain-name"                  { value 24; }
                                    }
                                }
                                description "DHCP option number";
                            }

                            leaf-list apply-groups {
                                type leafref {
                                    path "../../../../../../../groups/group/name";
                                }
                                max-elements 8;
                                ordered-by user;
                                description "Apply a configuration group at this level";
                            }

                            choice value {
                                mandatory true;
                                description "The value of the DHCP option.";
                                case ascii-string {

                                    leaf ascii-string {
                                        type types-sros:string-not-all-spaces {
                                            length "1..127";
                                        }
                                        description "DHCP option specified as an ASCII string";
                                    }

                                }
                                case hex-string {

                                    leaf hex-string {
                                        type types-sros:hex-string {
                                            length "1..256";
                                        }
                                        description "DHCP option specified as hexadecimal string";
                                    }

                                }
                                case domain-string {

                                    leaf domain-string {
                                        type string {
                                            length "1..127";
                                            pattern "[a-z0-9\\-]+(\\.[a-z0-9\\-]+)*";
                                        }
                                        description "DHCP option specified as a domain name";
                                    }

                                }
                                case ipv6-address {

                                    leaf-list ipv6-address {
                                        type types-sros:ipv6-address;
                                        max-elements 4;
                                        description "DHCP option specified as a list of IPv6 addresses";
                                    }

                                }
                                case empty {

                                    leaf empty {
                                        type empty;
                                        description "Empty DHCP option";
                                    }

                                }
                            }
                        } // list ipv6-option

                    } // container to-client-options

                } // list host

            } // container ppp

        } // list local-user-db

    } // grouping conf-submgt-local-user-db

}
