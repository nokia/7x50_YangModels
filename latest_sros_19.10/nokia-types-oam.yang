module nokia-types-oam {

    yang-version "1.1";

    namespace "urn:nokia.com:sros:ns:yang:sr:types-oam";

    prefix "types-oam";

    import nokia-sros-yang-extensions     { prefix "sros-ext"; }


    sros-ext:sros-major-release "rel19";

    organization "Nokia";

    contact
        "Nokia SR OS Support
         Web: <http://www.nokia.com>";

    description
        "Common OAM and Service Assurance Agent (SAA) type definitions data types used in the SR OS management system.

         Copyright 2016 Nokia. All rights reserved. Reproduction of this document
         is authorized on the condition that the foregoing copyright notice is included.

         This nokia-types-oam YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-03-04";

    typedef saa-threshold-direction {
        type enumeration {
            enum "inbound"                      { value 1; }
            enum "outbound"                     { value 2; }
            enum "round-trip"                   { value 3; }
        }
        description "An SAA threshold is configured against a packet flow direction.";
    }

    typedef padding-pattern {
        type union {
            type enumeration {
                enum "sequential"                   { value -1; }
            }
            type uint32 {
                range "0..65535";
            }
        }
        default "sequential";
    }

    typedef direction {
        type enumeration {
            enum "forward"                      { value 1; }
            enum "backward"                     { value 2; }
            enum "round-trip"                   { value 3; }
        }
        description "OAM-PM measurement direction";
    }

    typedef statistics-measurement-interval-duration {
        type enumeration {
            enum "raw"                          { value 1; }
            enum "15-mins"                      { value 2; }
            enum "1-hour"                       { value 3; }
            enum "1-day"                        { value 4; }
            enum "5-mins"                       { value 5; }
        }
        description "OAM-PM measurement interval duration or raw data";
    }

    typedef measurement-interval-duration {
        type enumeration {
            enum "15-mins"                      { value 2; }
            enum "1-hour"                       { value 3; }
            enum "1-day"                        { value 4; }
            enum "5-mins"                       { value 5; }
        }
        description "OAM-PM measurement interval duration";
    }

    typedef forwarding-class {
        type enumeration {
            enum "be"                           { value 0; }
            enum "l2"                           { value 1; }
            enum "af"                           { value 2; }
            enum "l1"                           { value 3; }
            enum "h2"                           { value 4; }
            enum "ef"                           { value 5; }
            enum "h1"                           { value 6; }
            enum "nc"                           { value 7; }
        }
        default "be";
        description "The forwarding class type for the session";
    }

    typedef dscp-resolve {
        type enumeration {
            enum "resolve"                      { value 1000; }
        }
        description "Default value for OAM-PM DSCP configuration field";
    }

    typedef twamp-server-connection-count {
        type uint32 {
            range "0..64";
        }
        description "The number of concurrent control connections supported by a TWAMP server";
    }

    typedef twamp-server-session-count {
        type uint32 {
            range "0..128";
        }
        description "The number of concurrent test sessions supported by a TWAMP server";
    }

    typedef oam-pm-session-test-detected-tx-error {
        type enumeration {
            enum "none"                         { value 1; }
            enum "port-down"                    { value 2; }
            enum "no-tx-port"                   { value 3; }
            enum "eth-parent-admin-down"        { value 4; }
            enum "eth-no-mep-or-admin-down"     { value 5; }
            enum "unexpected-error"             { value 6; }
            enum "no-service"                   { value 7; }
            enum "service-admin-down"           { value 8; }
            enum "service-oper-down"            { value 9; }
            enum "no-route"                     { value 10; }
            enum "no-interface"                 { value 11; }
            enum "no-direct-interface"          { value 12; }
            enum "source-interface-down"        { value 13; }
            enum "source-ip-not-local"          { value 14; }
            enum "next-hop-ip-is-local"         { value 15; }
            enum "dest-mac-resolve-fail"        { value 16; }
            enum "mpls-dm-system-disabled"      { value 17; }
            enum "lsp-not-available"            { value 18; }
            enum "lsp-oper-down"                { value 19; }
            enum "udp-return-ip-not-local"      { value 20; }
        }
        description
            "Reason for the inability (if any) to launch test frames for the specified test

             none                      (1) - no transmit failure has been detected
             port-down                 (2) - the transmit port is operationally down
             no-tx-port                (3) - an egress has not been found
             eth-parent-admin-down     (4) - the parent (e.g. the SAP, SDP, service, or port) of the MEP is administratively down
             eth-no-mep-or-admin-down  (5) - the test's MEP is not fully configured or the MEP is administratively down
             unexpected-error          (6) - transmission failed due to unexpected conditions, such as failed memory allocation, traffic congestion, or failure to obtain the necessary resources
             no-service                (7) - the service associated with this test session was not found
             service-admin-down        (8) - the service associated with this test session is administratively down
             service-oper-down         (9) - the service associated with this test session is operationally down
             no-route                 (10) - there is no IP route to the destination address
             no-interface             (11) - there is no IP interface that matches the configured forwarding interface
             no-direct-interface      (12) - there is no appropriate IP interface for bypass-routing to the destination address
             source-interface-down    (13) - the IP interface associated with the source address is down
             source-ip-not-local      (14) - the source address is not local
             next-hop-ip-is-local     (15) - the next-hop address is local
             dest-mac-resolve-fail    (16) - unable to resolve the remote-mepid to a unicast layer2 MAC address
             mpls-dm-system-disable   (17) - MPLS-DM disabled at system level
             lsp-not-available        (18) - LSP not available (e.g. not configured)
             lsp-oper-down            (19) - LSP is operationally down
             udp-return-ip-not-local  (20) - UDP Return IP address is not local";
    }

    typedef oam-pm-session-mpls-dm-rx-status {
        type enumeration {
            enum "success"                      { value 1; }
            enum "notif-data-format-invalid"    { value 2; }
            enum "notif-initialization-in-progress" { value 3; }
            enum "notif-data-reset-occurred"    { value 4; }
            enum "notif-resource-temporarily-unavail" { value 5; }
            enum "error-unspecified-error"      { value 16; }
            enum "error-unsupported-version"    { value 17; }
            enum "error-unsupported-control-code" { value 18; }
            enum "error-unsupported-data-format" { value 19; }
            enum "error-authentication-failure" { value 20; }
            enum "error-invalid-destination-node-id" { value 21; }
            enum "error-connection-mismatch"    { value 22; }
            enum "error-unsupported-mandtlv-object" { value 23; }
            enum "error-unsupported-query-interval" { value 24; }
            enum "error-administrative-block"   { value 25; }
            enum "error-resource-unavailable"   { value 26; }
            enum "error-resource-released"      { value 27; }
            enum "error-invalid-message"        { value 28; }
            enum "error-protocol-error"         { value 29; }
            enum "none"                         { value 256; }
            enum "error-timeout"                { value 257; }
        }
        description
            "The most recent receive status for an OAM-PM MPLS-DM test.

             A value less than 256 was copied from the Control Code field of
             the most recent MPLS-DM response message.  The value indicates
             whether or not the most recent query message (sent by this node as
             part of an MPLS-DM test) was processed successfully by the far-end
             node.

             'none(256)' is a proprietary code point, indicating the receive status
             is irrelevant or unknown (e.g. the test has not been started).

             'error-timeout(257)' is a proprietary code point, indicating the most
             recent receive event for a running test was an internal timeout,
             rather than the expected receipt of an MPLS-DM response message.";
    }

}
