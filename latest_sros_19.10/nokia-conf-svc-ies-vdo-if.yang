submodule nokia-conf-svc-ies-vdo-if {

    yang-version "1.1";

    belongs-to nokia-conf { prefix "conf"; }

    import nokia-sros-yang-extensions     { prefix "sros-ext"; }
    import nokia-types-services           { prefix "types-services"; }
    import nokia-types-sros               { prefix "types-sros"; }

    include nokia-conf-filter;
    include nokia-conf-groups;
    include nokia-conf-isa;
    include nokia-conf-isa-video-group;
    include nokia-conf-log;
    include nokia-conf-qos;
    include nokia-conf-system;
    include nokia-conf-system-security;

    sros-ext:sros-major-release "rel19";

    organization "Nokia";

    contact
        "Nokia SR OS Support
         Web: <http://www.nokia.com>";

    description
        "Nokia YANG Data model to configure ies service video interfaces on SR OS based routers.

         Copyright 2016 Nokia. All rights reserved. Reproduction of this document
         is authorized on the condition that the foregoing copyright notice is included.

         This nokia-conf-svc-ies-vdo-if YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-02-14";

    grouping conf-svc-ies-vdo-if-video-interface {
        list video-interface {
            key "interface-name";
            description "Enter the video-interface list instance";

            leaf interface-name {
                type types-sros:interface-name {
                    length "1..29";
                }
                description "Interface name";
            }

            leaf admin-state {
                type types-sros:admin-state;
                default "disable";
                description "Administrative state of the video interface";
            }

            leaf accounting-policy {
                type leafref {
                    path "../../../../log/accounting-policy/policy-id";
                }
                description "Accounting Policy";
            }

            leaf description {
                type types-sros:description;
                description "Text description";
            }

            leaf cpu-protection {
                type leafref {
                    path "../../../../system/security/cpu-protection/policy/policy-id";
                }
                description "CPU protection policy";
            }

            leaf multicast-service {
                type types-services:external-service-id;
                description "Service ID of the associated multicast service.";
            }

            leaf output-format {
                type enumeration {
                    enum "udp"                          { value 1; }
                    enum "rtp-udp"                      { value 2; }
                }
                default "rtp-udp";
                description "Output format";
            }

            leaf-list apply-groups {
                type leafref {
                    path "../../../../groups/group/name";
                }
                max-elements 8;
                ordered-by user;
                description "Apply a configuration group at this level";
            }

            container rt-client {
                presence "rt-client";
                description "Enter the rt-client context";

                leaf src-address {
                    type types-sros:ipv4-unicast-address;
                    mandatory true;
                    description "An IP address for the RT client.";
                }

                leaf-list apply-groups {
                    type leafref {
                        path "../../../../../groups/group/name";
                    }
                    max-elements 8;
                    ordered-by user;
                    description "Apply a configuration group at this level";
                }

            } // container rt-client

            container adi {
                description "Enter the adi context";

                container scte30 {
                    description "Enter the scte30 context";

                    list ad-server {
                        key "address";
                        max-elements 4;
                        description "Add a list entry for ad-server";

                        leaf address {
                            type types-sros:ipv4-address;
                            description "Ad server address";
                        }

                    } // list ad-server

                    container local-address {
                        presence "local-address";
                        description "Enter the local-address context";

                        leaf control {
                            type types-sros:ipv4-unicast-address;
                            mandatory true;
                            description "Control";
                        }

                        leaf data {
                            type types-sros:ipv4-unicast-address;
                            mandatory true;
                            description "Data";
                        }

                        leaf-list apply-groups {
                            type leafref {
                                path "../../../../../../../groups/group/name";
                            }
                            max-elements 8;
                            ordered-by user;
                            description "Apply a configuration group at this level";
                        }

                    } // container local-address

                } // container scte30

            } // container adi

            container video-sap {
                presence "video-sap";
                description "Enter the video-sap context";

                leaf video-group-id {
                    type leafref {
                        path "../../../../../isa/video-group/video-group-id";
                    }
                    sros-ext:immutable;
                    mandatory true;
                    description "Group id for the video interface.";
                }

                leaf-list apply-groups {
                    type leafref {
                        path "../../../../../groups/group/name";
                    }
                    max-elements 8;
                    ordered-by user;
                    description "Apply a configuration group at this level";
                }

                container egress {
                    description "Enter the egress context";

                    leaf-list apply-groups {
                        type leafref {
                            path "../../../../../../groups/group/name";
                        }
                        max-elements 8;
                        ordered-by user;
                        description "Apply a configuration group at this level";
                    }

                    container filter {
                        description "Enter the filter context";

                        leaf ip {
                            type leafref {
                                path "../../../../../../../filter/ip-filter/filter-name";
                            }
                            description "IPv4 filter policy name";
                        }

                    } // container filter

                    container qos {
                        description "Enter the qos context";

                        leaf policy-name {
                            type leafref {
                                path "../../../../../../../qos/sap-egress/sap-egress-policy-name";
                            }
                            description "SAP-egress QoS policy";
                        }

                    } // container qos

                } // container egress

                container ingress {
                    description "Enter the ingress context";

                    leaf-list apply-groups {
                        type leafref {
                            path "../../../../../../groups/group/name";
                        }
                        max-elements 8;
                        ordered-by user;
                        description "Apply a configuration group at this level";
                    }

                    container filter {
                        description "Enter the filter context";

                        leaf ip {
                            type leafref {
                                path "../../../../../../../filter/ip-filter/filter-name";
                            }
                            description "IPv4 filter policy name";
                        }

                    } // container filter

                    container qos {
                        description "Enter the qos context";

                        leaf policy-name {
                            type leafref {
                                path "../../../../../../../qos/sap-ingress/sap-ingress-policy-name";
                            }
                            description "SAP-ingress QoS policy";
                        }

                    } // container qos

                } // container ingress

            } // container video-sap

            list address {
                key "ip-address";
                max-elements 16;
                description "Add a list entry for address";

                leaf ip-address {
                    type types-sros:ipv4-prefix-with-host-bits;
                    description "IPv4 address for the video interface within the service";
                }

            } // list address

            list channel {
                key "mcast-address source";
                description "Enter the channel list instance";

                leaf mcast-address {
                    type types-sros:ipv4-multicast-address;
                    description "Multicast channel address";
                }

                leaf source {
                    type types-sros:ipv4-unicast-address;
                    description "Unicast source address";
                }

                leaf channel-name {
                    type types-sros:named-item;
                    mandatory true;
                    description "max 32 chars.";
                }

                leaf description {
                    type types-sros:description;
                    description "Text description";
                }

                leaf scte35-action {
                    type enumeration {
                        enum "forward"                      { value 1; }
                        enum "drop"                         { value 2; }
                    }
                    default "forward";
                    description "Enable/disable forwarding scte 35 cue avails.";
                }

                leaf-list apply-groups {
                    type leafref {
                        path "../../../../../groups/group/name";
                    }
                    max-elements 8;
                    ordered-by user;
                    description "Apply a configuration group at this level";
                }

                list zone-channel {
                    key "zone-mcast-address zone-source";
                    description "Enter the zone-channel list instance";

                    leaf zone-mcast-address {
                        type types-sros:ipv4-multicast-address;
                        description "Multicast zone channel address";
                    }

                    leaf zone-source {
                        type types-sros:ipv4-unicast-address;
                        description "Unicast source address";
                    }

                    leaf adi-channel-name {
                        type types-sros:named-item;
                        description "max 32 chars.";
                    }

                    leaf-list apply-groups {
                        type leafref {
                            path "../../../../../../groups/group/name";
                        }
                        max-elements 8;
                        ordered-by user;
                        description "Apply a configuration group at this level";
                    }

                } // list zone-channel

            } // list channel

        } // list video-interface

    } // grouping conf-svc-ies-vdo-if-video-interface

}
