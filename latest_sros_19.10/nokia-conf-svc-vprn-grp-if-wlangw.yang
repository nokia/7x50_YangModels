submodule nokia-conf-svc-vprn-grp-if-wlangw {

    yang-version "1.1";

    belongs-to nokia-conf { prefix "conf"; }

    import nokia-sros-yang-extensions     { prefix "sros-ext"; }
    import nokia-types-qos                { prefix "types-qos"; }
    import nokia-types-services           { prefix "types-services"; }
    import nokia-types-sros               { prefix "types-sros"; }
    import nokia-types-subscriber-mgmt    { prefix "types-submgt"; }
    import nokia-types-wlangw             { prefix "types-wlangw"; }

    include nokia-conf-aaa;
    include nokia-conf-groups;
    include nokia-conf-isa;
    include nokia-conf-qos;
    include nokia-conf-service;
    include nokia-conf-submgt-isa-filter;
    include nokia-conf-submgt-isa-policer;
    include nokia-conf-submgt-vrgw;
    include nokia-conf-subscriber-mgmt;
    include nokia-conf-svc-nat;
    include nokia-conf-svc-vpls;

    sros-ext:sros-major-release "rel19";

    organization "Nokia";

    contact
        "Nokia SR OS Support
         Web: <http://www.nokia.com>";

    description
        "Nokia YANG Data model to configure vprn service group interface WLAN Gateway on SR OS based routers.

         Copyright 2016 Nokia. All rights reserved. Reproduction of this document
         is authorized on the condition that the foregoing copyright notice is included.

         This nokia-conf-svc-vprn-grp-if-wlangw YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-09-20";

    grouping conf-svc-vprn-grp-if-wlangw-wlan-gw {
        container wlan-gw {
            when "../type = 'wlan-gw'";
            description "Enter the wlan-gw context";

            leaf admin-state {
                type types-sros:admin-state;
                default "disable";
                description "Administrative state of WLAN Gateway on this group interface";
            }

            leaf oper-down-on-group-degrade {
                type boolean;
                default "false";
                description "Bring interface operationally down when its ISA WLAN Gateway becomes degraded";
            }

            leaf tcp-mss-adjust {
                type uint32 {
                    range "160..10240";
                }
                units "bytes";
                description "Value for the TCP Maximum Segment Size (MSS) option if not present, or if value is higher";
            }

            leaf wlan-gw-group {
                type leafref {
                    path "../../../../../../isa/wlan-gw-group/id";
                }
                sros-ext:auto-restart-to-modify;
                description "Identifier of the WLAN Gateway ISA group to terminate UEs for this group interface";
            }

            leaf gateway-router {
                type string;
                sros-ext:auto-restart-to-modify;
                description "The routing instance where the tunneled UE traffic is routed, or empty to specify that the routing instance corresponding to the service containing this interface is used.";
            }

            leaf-list apply-groups {
                type leafref {
                    path "../../../../../../groups/group/name";
                }
                max-elements 8;
                ordered-by user;
                description "Apply a configuration group at this level";
            }

            container lanext {
                presence "Whether Home LAN Extension is enabled for this group interface.";
                sros-ext:auto-restart-to-modify;
                description "Enter the lanext context";

                leaf max-bd {
                    type uint32 {
                        range "1..131071";
                    }
                    sros-ext:auto-restart-to-modify;
                    default "131071";
                    description "Maximum number of bridge domains";
                }

            } // container lanext

            container learn-ap-mac {
                presence
                    "Whether the system sends ARP or ND packets upon certain events,
                     in order to learn the MAC address of the Access Point.";
                description "Enter the learn-ap-mac context";

                leaf delay-auth {
                    type boolean;
                    default "false";
                    description "Delay authentication until ARP/ND is answered or timed out, after which AP MAC can be included";
                }

            } // container learn-ap-mac

            container mobility {
                description "Enter the mobility context";

                leaf hold-time {
                    type types-sros:time-duration {
                        range "0..255";
                    }
                    units "seconds";
                    default "5";
                    description "Minimum time between two mobility events for a single UE";
                }

                leaf inter-tunnel-type {
                    type boolean;
                    sros-ext:auto-restart-to-modify;
                    default "false";
                    description "Enable mobility between terminating tunnel types";
                }

                leaf inter-vlan {
                    type boolean;
                    default "false";
                    description "Enable mobility within different VLANs within the same range of VLAN Q-tags";
                }

                container trigger {
                    description "Enter the trigger context";

                    leaf data {
                        type boolean;
                        default "false";
                        description "Use data traffic as mobility trigger";
                    }

                    leaf iapp {
                        type boolean;
                        default "false";
                        description "Use Inter Access Point Protocol (IAPP) messages as mobility trigger";
                    }

                    leaf control {
                        type boolean;
                        default "false";
                        description "Use control traffic (DHCP, DHCPv6, and ICMPv6-RS messages) as mobility trigger";
                    }

                } // container trigger

            } // container mobility

            container tunnel-egress-qos {
                description "Enter the tunnel-egress-qos context";

                leaf admin-state {
                    type types-sros:admin-state;
                    sros-ext:auto-restart-to-modify;
                    default "disable";
                    description "Administrative state of egress QoS for WLAN-GW tunnels";
                }

                leaf agg-rate-limit {
                    type types-qos:pir-rate-override;
                    default "max";
                    description "Aggregate rate limit of each shaper associated with this interface";
                }

                leaf granularity {
                    type types-wlangw:shaping-granularity;
                    sros-ext:auto-restart-to-modify;
                    default "per-tunnel";
                    description "Granularity of the egress shaping for WLAN Gateway";
                }

                leaf hold-time {
                    type union {
                        type types-sros:time-duration {
                            range "1..86400";
                        }
                        type enumeration {
                            enum "infinite"                     { value -1; }
                        }
                    }
                    units "seconds";
                    description "Minimum time that the egress QoS resources associated with a tunnel (such as a shaper) are held";
                }

                leaf multi-client-only {
                    type boolean;
                    default "false";
                    description "Tunnel traffic to shape when multiple UEs use this tunnel";
                }

                leaf qos {
                    type leafref {
                        path "../../../../../../../qos/sap-egress/sap-egress-policy-name";
                    }
                    sros-ext:auto-restart-to-modify;
                    description "Identifier of the egress QoS policy associated with each tunnel of this interface";
                }

                leaf scheduler-policy {
                    type leafref {
                        path "../../../../../../../qos/scheduler-policy/scheduler-policy-name";
                    }
                    sros-ext:auto-restart-to-modify;
                    description "Identifier of the egress scheduler policy associated with each tunnel of this interface";
                }

            } // container tunnel-egress-qos

            container tunnel-encaps {
                description "Enter the tunnel-encaps context";

                leaf learn-l2tp-cookie {
                    type union {
                        type enumeration {
                            enum "never"                        { value 2; description "The cookie will never be interpreted."; }
                            enum "always"                       { value 3; description "The cookie will always be interpreted,
                            regardless of the value of its first two octets."; }
                        }
                        type types-sros:hex-string {
                            length "6";
                        }
                    }
                    default "never";
                    description "System that learns the cookie from L2TP tunnels terminating on this interface";
                }

            } // container tunnel-encaps

            container l2-ap {
                description "Enter the l2-ap context";

                leaf auto-sub-id-fmt {
                    type enumeration {
                        enum "include-ap-tags"              { value 0; }
                        enum "sap-only"                     { value 1; }
                    }
                    default "include-ap-tags";
                    description "Format of the auto-generated subscriber ID";
                }

                leaf default-encap-type {
                    type enumeration {
                        enum "null"                         { value 1; }
                        enum "dot1q"                        { value 2; }
                        enum "qinq"                         { value 10; }
                    }
                    sros-ext:auto-restart-to-modify;
                    default "null";
                    description "Default encapsulation type for Layer 2 access points";
                }

                list access-point {
                    key "sap-id";
                    description "Enter the access-point list instance";

                    leaf sap-id {
                        type types-sros:sap;
                        description "SAP ID for the Layer 2 access point";
                    }

                    leaf admin-state {
                        type types-sros:admin-state;
                        default "disable";
                        description "Administrative state of the L2 access points";
                    }

                    leaf encap-type {
                        type enumeration {
                            enum "null"                         { value 1; }
                            enum "dot1q"                        { value 2; }
                            enum "qinq"                         { value 10; }
                        }
                        description "Service encapsulation type of this access point";
                    }

                    leaf epipe-sap-template {
                        type leafref {
                            path "../../../../../../../template/epipe-sap-template/name";
                        }
                        description "Parameters template for the internal connections with the ISA cards";
                    }

                    leaf-list apply-groups {
                        type leafref {
                            path "../../../../../../../../groups/group/name";
                        }
                        max-elements 8;
                        ordered-by user;
                        description "Apply a configuration group at this level";
                    }

                } // list access-point

            } // container l2-ap

            list gateway-address {
                key "address";
                max-elements 10;
                sros-ext:auto-restart-to-modify;
                description "Enter the gateway-address list instance";

                leaf address {
                    type types-sros:ip-unicast-without-local-address;
                    description "Gateway endpoint address of the WLAN Gateway tunnel";
                }

                leaf-list apply-groups {
                    type leafref {
                        path "../../../../../../../groups/group/name";
                    }
                    max-elements 8;
                    ordered-by user;
                    description "Apply a configuration group at this level";
                }

                container purpose {
                    description "Enter the purpose context";

                    leaf xconnect {
                        type boolean;
                        default "false";
                        description "Use tunnel IP address for crosse-connect traffic";
                    }

                } // container purpose

            } // list gateway-address

            list vlan-range {
                key "range";
                description "Enter the vlan-range list instance";

                leaf range {
                    type string {
                        pattern "((([0-9]|[1-9][0-9]{1,2}|[1-3][0-9]{3}|40[0-8][0-9]|409[0-5]))(\\.\\.(([0-9]|[1-9][0-9]{1,2}|[1-3][0-9]{3}|40[0-8][0-9]|409[0-5])))?)|(unmatched)";
                    }
                    description "IEEE 802.1q VLAN tag range";
                }

                leaf http-redirect-policy {
                    type leafref {
                        path "../../../../../../../subscriber-mgmt/http-redirect-policy/name";
                    }
                    description "Default HTTP redirect policy for portal authentication";
                }

                leaf idle-timeout-action {
                    type types-wlangw:idle-timeout-action;
                    default "remove";
                    description "Action to perform when the idle timeout expires";
                }

                leaf nat-policy {
                    type leafref {
                        path "../../../../../../nat/nat-policy/name";
                    }
                    description "NAT policy for DSM and ISA portal authentication";
                }

                leaf retail-service {
                    type types-services:service-name;
                    description "Default retail service for new UEs in this range";
                }

                leaf-list apply-groups {
                    type leafref {
                        path "../../../../../../../groups/group/name";
                    }
                    max-elements 8;
                    ordered-by user;
                    description "Apply a configuration group at this level";
                }

                container authentication {
                    description "Enter the authentication context";

                    leaf hold-time {
                        type types-sros:time-duration {
                            range "0..3600";
                        }
                        units "seconds";
                        default "5";
                        description "Minimum time to hold a UE down after an authentication failure";
                    }

                    leaf on-control-plane {
                        type boolean;
                        default "false";
                        description "Trigger authentication on first control plane packet instead of first data packet";
                    }

                    leaf policy {
                        type leafref {
                            path "../../../../../../../../aaa/radius/isa-policy/name";
                        }
                        description "RADIUS policy for authentication";
                    }

                    leaf vlan-mismatch-timeout {
                        type types-sros:time-duration {
                            range "5..60";
                        }
                        units "seconds";
                        description "Timeout value for the RADIUS proxy cache if a packet is received with a non-matching VLAN";
                    }

                } // container authentication

                container data-triggered-ue-creation {
                    description "Enter the data-triggered-ue-creation context";

                    leaf admin-state {
                        type types-sros:admin-state;
                        default "disable";
                        description "Administrative state of data-triggered UE creation";
                    }

                    container create-proxy-cache-entry {
                        description "Enter the create-proxy-cache-entry context";

                        leaf mac-format {
                            type types-submgt:mac-specification;
                            default "aa:";
                            description "MAC address format";
                        }

                        container proxy-server {
                            presence
                                "Enables creating cache entries in the specified proxy
                                 server.";
                            description "Enter the proxy-server context";

                            leaf router-instance {
                                type string;
                                mandatory true;
                                description "The router instance of the RADIUS Proxy server.";
                            }

                            leaf name {
                                type types-sros:named-item;
                                mandatory true;
                                description "RADIUS Proxy server name";
                            }

                        } // container proxy-server

                    } // container create-proxy-cache-entry

                } // container data-triggered-ue-creation

                container l2-service {
                    presence
                        "All traffic in this VLAN range will terminate in the associated
                         layer 2 service instead of the parent service of this group
                         interface.";
                    description "Enter the l2-service context";

                    leaf admin-state {
                        type types-sros:admin-state;
                        default "disable";
                        description "Administrative state of Layer 2 service for VLAN range";
                    }

                    leaf description {
                        type types-sros:description;
                        description "Text description";
                    }

                    leaf service {
                        type leafref {
                            path "../../../../../../../vpls/service-name";
                        }
                        mandatory true;
                        description "Layer 2 service associated with the range";
                    }

                } // container l2-service

                container dhcp4 {
                    description "Enter the dhcp4 context";

                    leaf admin-state {
                        type types-sros:admin-state;
                        default "disable";
                        description "Administrative state of the DHCPv4 protocol";
                    }

                    leaf l2-aware-ip-address {
                        type union {
                            type types-sros:ipv4-unicast-address;
                            type enumeration {
                                enum "from-pool"                    { value 0; description "The l2-aware IP address should be allocated
                                from a pool."; }
                            }
                        }
                        description "L2-Aware NAT inside IP address";
                    }

                    leaf-list dns {
                        type types-sros:ipv4-unicast-address;
                        max-elements 2;
                        ordered-by user;
                        description "DNS servers signaled in DHCP";
                    }

                    leaf-list nbns {
                        type types-sros:ipv4-unicast-address;
                        max-elements 2;
                        ordered-by user;
                        description "NetBIOS servers signaled in DHCP";
                    }

                    container lease-time {
                        description "Enter the lease-time context";

                        leaf active {
                            type types-sros:time-duration {
                                range "300..3600";
                            }
                            units "seconds";
                            default "600";
                            description "IP address lease time for the UE after successful (portal) authentication";
                        }

                        leaf initial {
                            type types-sros:time-duration {
                                range "300..3600";
                            }
                            units "seconds";
                            default "600";
                            description "IP address lease time that is provided before and during (portal) authentication to the UE";
                        }

                    } // container lease-time

                } // container dhcp4

                container dhcp6 {
                    description "Enter the dhcp6 context";

                    leaf admin-state {
                        type types-sros:admin-state;
                        default "disable";
                        description "Administrative state of the protocol";
                    }

                    leaf-list apply-groups {
                        type leafref {
                            path "../../../../../../../../groups/group/name";
                        }
                        max-elements 8;
                        ordered-by user;
                        description "Apply a configuration group at this level";
                    }

                    container preferred-lifetime {
                        description "Enter the preferred-lifetime context";

                        leaf active {
                            type types-sros:time-duration {
                                range "300..3600";
                            }
                            units "seconds";
                            default "600";
                            description "Preferred signaled lifetime after full authentication";
                        }

                        leaf initial {
                            type types-sros:time-duration {
                                range "300..3600";
                            }
                            units "seconds";
                            default "300";
                            description "Preferred signaled lifetime when the UE is not fully authenticated";
                        }

                    } // container preferred-lifetime

                    container valid-lifetime {
                        description "Enter the valid-lifetime context";

                        leaf active {
                            type types-sros:time-duration {
                                range "300..3600";
                            }
                            units "seconds";
                            default "600";
                            description "Signaled valid lifetime after full authentication";
                        }

                        leaf initial {
                            type types-sros:time-duration {
                                range "300..3600";
                            }
                            units "seconds";
                            default "300";
                            description "Valid signaled lifetime when the UE is not fully authenticated";
                        }

                    } // container valid-lifetime

                } // container dhcp6

                container slaac {
                    description "Enter the slaac context";

                    leaf admin-state {
                        type types-sros:admin-state;
                        default "disable";
                        description "Administrative state of the protocol";
                    }

                    leaf-list apply-groups {
                        type leafref {
                            path "../../../../../../../../groups/group/name";
                        }
                        max-elements 8;
                        ordered-by user;
                        description "Apply a configuration group at this level";
                    }

                    container preferred-lifetime {
                        description "Enter the preferred-lifetime context";

                        leaf active {
                            type types-sros:time-duration {
                                range "300..3600";
                            }
                            units "seconds";
                            default "600";
                            description "Preferred signaled lifetime after full authentication";
                        }

                        leaf initial {
                            type types-sros:time-duration {
                                range "300..3600";
                            }
                            units "seconds";
                            default "300";
                            description "Preferred signaled lifetime when the UE is not fully authenticated";
                        }

                    } // container preferred-lifetime

                    container valid-lifetime {
                        description "Enter the valid-lifetime context";

                        leaf active {
                            type types-sros:time-duration {
                                range "300..3600";
                            }
                            units "seconds";
                            default "600";
                            description "Signaled valid lifetime after full authentication";
                        }

                        leaf initial {
                            type types-sros:time-duration {
                                range "300..3600";
                            }
                            units "seconds";
                            default "300";
                            description "Valid signaled lifetime when the UE is not fully authenticated";
                        }

                    } // container valid-lifetime

                } // container slaac

                container dsm {
                    description "Enter the dsm context";

                    leaf admin-state {
                        type types-sros:admin-state;
                        default "disable";
                        description "Administrative state of DSM";
                    }

                    leaf accounting-policy {
                        type leafref {
                            path "../../../../../../../../aaa/radius/isa-policy/name";
                        }
                        sros-ext:auto-restart-to-modify;
                        description "ISA Radius Policy for accounting";
                    }

                    leaf-list apply-groups {
                        type leafref {
                            path "../../../../../../../../groups/group/name";
                        }
                        max-elements 8;
                        ordered-by user;
                        description "Apply a configuration group at this level";
                    }

                    container accounting-update {
                        presence "Interim Accounting Update";
                        description "Enter the accounting-update context";

                        leaf interval {
                            type uint32 {
                                range "5..259200";
                            }
                            units "minutes";
                            mandatory true;
                            description "Time interval between consecutive Interim accounting update messages";
                        }

                    } // container accounting-update

                    container ingress {
                        description "Enter the ingress context";

                        leaf policer {
                            type leafref {
                                path "../../../../../../../../../subscriber-mgmt/isa-policer/name";
                            }
                            description "Policer for ingress traffic";
                        }

                        leaf ip-filter {
                            type leafref {
                                path "../../../../../../../../../subscriber-mgmt/isa-filter/name";
                            }
                            description "Filter for ingress traffic";
                        }

                    } // container ingress

                    container egress {
                        description "Enter the egress context";

                        leaf policer {
                            type leafref {
                                path "../../../../../../../../../subscriber-mgmt/isa-policer/name";
                            }
                            description "Policer for egress traffic";
                        }

                    } // container egress

                    container one-time-redirect {
                        description "Enter the one-time-redirect context";

                        leaf url {
                            type types-wlangw:one-time-http-redirect-url;
                            description "URL for redirected HTTP protocol packets that can be overridden by AAA";
                        }

                        leaf port {
                            type uint32 {
                                range "1..65535";
                            }
                            default "80";
                            description "Destination port of packets considered for HTTP redirect";
                        }

                    } // container one-time-redirect

                } // container dsm

                container vrgw {
                    description "Enter the vrgw context";

                    leaf admin-state {
                        type types-sros:admin-state;
                        default "disable";
                        description "Administrative state of VRGW";
                    }

                    leaf-list apply-groups {
                        type leafref {
                            path "../../../../../../../../groups/group/name";
                        }
                        max-elements 8;
                        ordered-by user;
                        description "Apply a configuration group at this level";
                    }

                    container brg {
                        description "Enter the brg context";

                        leaf default-brg-profile {
                            type leafref {
                                path "../../../../../../../../../subscriber-mgmt/vrgw/brg-profile/brg-profile-name";
                            }
                            sros-ext:auto-restart-to-modify;
                            description "Default BRG profile to use if the AAA server does not specify one";
                        }

                        leaf authenticated-brg-only {
                            type boolean;
                            sros-ext:auto-restart-to-modify;
                            default "false";
                            description "Only allow hosts from BRGs pre-authenticated using the radius-proxy";
                        }

                    } // container brg

                    container lanext {
                        description "Enter the lanext context";

                        leaf admin-state {
                            type types-sros:admin-state;
                            sros-ext:auto-restart-to-modify;
                            default "disable";
                            description "Administrative state of HLE";
                        }

                        leaf assistive-address-resolution {
                            type boolean;
                            sros-ext:auto-restart-to-modify;
                            default "false";
                            description "ISA assists in address resolution";
                        }

                        leaf bd-mac-prefix {
                            type string {
                                length "8";
                                pattern "[0-9a-f][02468ace](:[0-9a-f]{2}){2}";
                            }
                            sros-ext:auto-restart-to-modify;
                            description "Prefix from which BD MACs for MAC translation are derived";
                        }

                        leaf mac-translation {
                            type boolean;
                            sros-ext:auto-restart-to-modify;
                            default "false";
                            description "Hide MAC address of home host by translating it to BD MAC";
                        }

                        leaf-list apply-groups {
                            type leafref {
                                path "../../../../../../../../../groups/group/name";
                            }
                            max-elements 8;
                            ordered-by user;
                            sros-ext:auto-restart-to-modify;
                            description "Apply a configuration group at this level";
                        }

                        container access {
                            sros-ext:auto-restart-to-modify;
                            description "Enter the access context";

                            leaf max-mac {
                                type uint32 {
                                    range "1..256";
                                }
                                sros-ext:auto-restart-to-modify;
                                default "20";
                                description "Maximum number of MAC entries in bridged domain from access side";
                            }

                            leaf multi-access {
                                type boolean;
                                sros-ext:auto-restart-to-modify;
                                default "false";
                                description "Allow multiple access points";
                            }

                            leaf policer {
                                type leafref {
                                    path "../../../../../../../../../../subscriber-mgmt/isa-policer/name";
                                }
                                sros-ext:auto-restart-to-modify;
                                description "Policer for ingress home traffic";
                            }

                        } // container access

                        container network {
                            sros-ext:auto-restart-to-modify;
                            description "Enter the network context";

                            leaf admin-state {
                                type types-sros:admin-state;
                                sros-ext:auto-restart-to-modify;
                                default "enable";
                                description "Administrative state of network";
                            }

                            leaf max-mac {
                                type uint32 {
                                    range "1..64";
                                }
                                sros-ext:auto-restart-to-modify;
                                default "20";
                                description "Maximum number of MAC entries in bridged domain from network side";
                            }

                            leaf policer {
                                type leafref {
                                    path "../../../../../../../../../../subscriber-mgmt/isa-policer/name";
                                }
                                sros-ext:auto-restart-to-modify;
                                description "Policer for ingress data center traffic";
                            }

                        } // container network

                    } // container lanext

                } // container vrgw

                container xconnect {
                    description "Enter the xconnect context";

                    leaf admin-state {
                        type types-sros:admin-state;
                        default "disable";
                        description "Administrative state of the cross-connect";
                    }

                    leaf-list apply-groups {
                        type leafref {
                            path "../../../../../../../../groups/group/name";
                        }
                        max-elements 8;
                        ordered-by user;
                        description "Apply a configuration group at this level";
                    }

                    container accounting {
                        description "Enter the accounting context";

                        leaf policy {
                            type leafref {
                                path "../../../../../../../../../aaa/radius/isa-policy/name";
                            }
                            sros-ext:auto-restart-to-modify;
                            description "ISA RADIUS accounting policy for cross-connected UEs";
                        }

                        leaf update-interval {
                            type types-sros:time-duration {
                                range "5..259200";
                            }
                            units "minutes";
                            description "Time between consecutive Interim accounting update messages";
                        }

                        leaf mobility-updates {
                            type boolean;
                            default "false";
                            description "Accounting updates triggered by mobility";
                        }

                    } // container accounting

                } // container xconnect

            } // list vlan-range

        } // container wlan-gw

    } // grouping conf-svc-vprn-grp-if-wlangw-wlan-gw

}
