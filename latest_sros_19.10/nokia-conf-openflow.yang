submodule nokia-conf-openflow {

    yang-version "1.1";

    belongs-to nokia-conf { prefix "conf"; }

    import nokia-sros-yang-extensions     { prefix "sros-ext"; }
    import nokia-types-services           { prefix "types-services"; }
    import nokia-types-sros               { prefix "types-sros"; }

    include nokia-conf-system;
    include nokia-conf-system-security;
    include nokia-conf-system-security-tls;

    sros-ext:sros-major-release "rel19";

    organization "Nokia";

    contact
        "Nokia SR OS Support
         Web: <http://www.nokia.com>";

    description
        "Nokia YANG Data model to configure openflow parameters on SR OS based routers.

         Copyright 2016 Nokia. All rights reserved. Reproduction of this document
         is authorized on the condition that the foregoing copyright notice is included.

         This nokia-conf-openflow YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-11-04";

    grouping conf-openflow {
        container openflow {
            description "Enter the openflow context";

            list of-controller {
                key "controller-id";
                max-elements 1;
                description "Enter the of-controller list instance";

                leaf controller-id {
                    type uint32;
                    default "1";
                    description "OpenFlow controller id. Currently is supported only value of 1.";
                }

                leaf admin-state {
                    type types-sros:admin-state;
                    default "disable";
                    description "Administrative state of an OpenFlow controller instance.";
                }

                leaf description {
                    type types-sros:description;
                    description "Text description";
                }

                leaf version {
                    type enumeration {
                        enum "version-1-3-1"                { value 4; }
                    }
                    default "version-1-3-1";
                    description "OpenFlow version negotiated between an OpenFlow controller and the switch.";
                }

                leaf address {
                    type types-sros:ipv4-address;
                    sros-ext:auto-restart-to-modify;
                    description "Local IPv4 address for OpenFlow controller to be used for packets on both main and aux channels. By default, this is the management IP address of the system. It may also correspond to the system IP address or another loopback address configured on the system. The OpenFlow controller must be shutdown to change its address.";
                }

                leaf echo-interval {
                    type uint32 {
                        range "10..3600";
                    }
                    units "seconds";
                    default "10";
                    description "Time interval between two consecutive OpenFlow echo request transmissions for a given OpenFlow session.";
                }

                leaf echo-multiple {
                    type uint32 {
                        range "3..100";
                    }
                    default "3";
                    description "Multiplier for OpenFlow control channel echo packets. The OpenFlow control channel is considered operationally down if no reply is heard from the switch after the specified multiplier.";
                }

                leaf tls-server-profile {
                    type leafref {
                        path "../../../system/security/tls/server-tls-profile/server-profile-name";
                    }
                    sros-ext:auto-restart-to-modify;
                    description "Specifies the profile name used by the controller.";
                }

                leaf role {
                    type enumeration {
                        enum "equal"                        { value 0; }
                    }
                    default "equal";
                    description "The role that the controller will request to OpenFlow switches when multiple controllers are connected to a switch.";
                }

                leaf ipv6-address {
                    type types-sros:ipv6-unicast-address;
                    description "Local IPv6 address for OpenFlow controller to be used for packets on both main and aux channels. The OpenFlow controller must be shutdown to change its address.";
                }

            } // list of-controller

            list of-switch {
                key "name";
                max-elements 8;
                description "Enter the of-switch list instance";

                leaf name {
                    type types-sros:named-item;
                    description "The name of this OpenFlow switch.";
                }

                leaf admin-state {
                    type types-sros:admin-state;
                    default "disable";
                    description "Administrative state of an OpenFlow switch instance.";
                }

                leaf description {
                    type types-sros:very-long-description;
                    description "Text description";
                }

                leaf ofs-id {
                    type uint32 {
                        range "1..8";
                    }
                    sros-ext:immutable;
                    description "Unique identifier of an OpenFlow switch instance.";
                }

                leaf echo-interval {
                    type uint32 {
                        range "1..3600";
                    }
                    units "seconds";
                    default "10";
                    description "Time interval between two consecutive OpenFlow echo request transmissions for a given OpenFlow session.";
                }

                leaf echo-multiple {
                    type uint32 {
                        range "3..100";
                    }
                    default "3";
                    description "Multiplier for OpenFlow control channel echo packets. The OpenFlow control channel is considered operationally down if no reply is heard from the switch after the specified multiplier.";
                }

                leaf aux-channel {
                    type boolean;
                    default "false";
                    description "The operational status of the auxiliary channel established between an OpenFlow controller and switch.";
                }

                leaf-list logical-port-status {
                    type enumeration {
                        enum "rsvp-te"                      { value 1; }
                        enum "mpls-tp"                      { value 2; }
                        enum "sr-te"                        { value 3; }
                    }
                    max-elements 3;
                    description "Logical port type for status change reporting";
                }

                list flowtable {
                    key "table-id";
                    max-elements 1;
                    sros-ext:auto-restart-to-modify;
                    description "Enter the flowtable list instance";

                    leaf table-id {
                        type uint32;
                        description "OpenFlow table ID.";
                    }

                    leaf max-size {
                        type uint32 {
                            range "1..524288";
                        }
                        default "1000";
                        description "Maximum number of entries that the flowtable can have. The maximum size cannot be changed if any entries are present in the flowtable.";
                    }

                    leaf mismatch-action {
                        type enumeration {
                            enum "drop"                         { value 1; }
                            enum "fall-through"                 { value 2; }
                            enum "packet-in"                    { value 3; }
                        }
                        default "fall-through";
                        description "Action to be performed when no match is found in the flowtable. When the value is set to 'drop', packets are dropped if no match is found in flowtable. When the value is set to 'fall-through, evaluating is continued based on filter policy.";
                    }

                    leaf switch-defined-cookie {
                        type boolean;
                        default "false";
                        description "Enable switch-defined cookie encoding";
                    }

                } // list flowtable

                list controller {
                    key "address port";
                    max-elements 2;
                    sros-ext:auto-restart-to-modify;
                    description "Enter the controller list instance";

                    leaf address {
                        type types-sros:ip-unicast-address;
                        description "IP address of the OpenFlow channel to the controller";
                    }

                    leaf port {
                        type uint32 {
                            range "1..65535";
                        }
                        description "Controller port.";
                    }

                    leaf tls-client-profile {
                        type leafref {
                            path "../../../../system/security/tls/client-tls-profile/client-profile-name";
                        }
                        description "Specifies the profile name used by the controller.";
                    }

                    leaf service-name {
                        type types-services:service-name;
                        description "The unique value which identifies the Service identifier";
                    }

                    leaf ofc-loopback {
                        type types-sros:ip-unicast-address;
                        description "The controller loop back IPv4 address.";
                    }

                } // list controller

            } // list of-switch

        } // container openflow

    } // grouping conf-openflow

}
