submodule nokia-state-vrrp {

    yang-version "1.1";

    belongs-to nokia-state { prefix "state"; }

    import ietf-yang-types                { prefix "yang"; }
    import nokia-sros-yang-extensions     { prefix "sros-ext"; }
    import nokia-types-sros               { prefix "types-sros"; }
    import nokia-types-vrrp               { prefix "types-vrrp"; }


    sros-ext:sros-major-release "rel19";

    organization "Nokia";

    contact
        "Nokia SR OS Support
         Web: <http://www.nokia.com>";

    description
        "Nokia YANG Data model with operational state for VRRP policy options on SR OS based routers.

         Copyright 2016 Nokia. All rights reserved. Reproduction of this document
         is authorized on the condition that the foregoing copyright notice is included.

         This nokia-state-vrrp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2018-10-01";

    grouping state-vrrp {
        container vrrp {
            description "Enter the vrrp context";

            list policy {
                key "policy-id";
                description "Enter the policy list instance";

                leaf policy-id {
                    type uint32 {
                        range "1..9999";
                    }
                    description "Policy ID that is be used when creating a Priority Control Policy";
                }

                leaf reference-count {
                    type union {
                        type enumeration {
                            enum "not-applied"                  { value 0; }
                        }
                        type uint32 {
                            range "1..max";
                        }
                    }
                    description
                        "The value indicates the number of VRRPs to which the policy has been applied.
                         The policy cannot be deleted unless this value is 0.";
                }

                leaf current-explicit-priority {
                    type union {
                        type uint32 {
                            range "0..254";
                        }
                        type enumeration {
                            enum "none"                         { value 255; }
                        }
                    }
                    description
                        "When multiple explicitly defined events associated with the
                         priority control policy happen simultaneously, the lowest value
                         of all the current explicit priorities will be used as the
                         in-use priority for the virtual router.";
                }

                leaf current-delta-sum {
                    type union {
                        type types-vrrp:priority;
                        type enumeration {
                            enum "none"                         { value 0; }
                        }
                    }
                    description
                        "When multiple delta events associated with the priority control
                         policy happen simultaneously, the sum of the priorities of all
                         these delta events is specified by the variable current-delta-sum.
                         This sum is subtracted from the base priority of the virtual router
                         to give the in-use priority.";
                }

                container priority-event {
                    description "Enter the priority-event context";

                    list host-unreachable {
                        key "ip-address";
                        description "Enter the host-unreachable list instance";

                        leaf ip-address {
                            type types-sros:ip-address-with-zone;
                            description "Priority control event that monitors the ability to receive ICMP Echo Reply packets from a host";
                        }

                        leaf last-transition {
                            type yang:date-and-time;
                            description
                                "The value indicates the sysUpTime when the operational state of the
                                 event last changed.";
                        }

                        leaf event-in-use {
                            type boolean;
                            description
                                "If value is 'true', then the event is currently affecting the in-use priority
                                 of some virtual router.";
                        }

                        leaf hold-set-remaining {
                            type types-vrrp:event-hold-state;
                            units "seconds";
                            description
                                "The value indicates the current value of the hold-set timer i.e. the
                                 amount of time remaining before the event will transition
                                 into the cleared state.";
                        }

                        leaf hold-clear-remaining {
                            type types-vrrp:event-hold-state;
                            units "seconds";
                            description
                                "The value indicates the current value of the hold-clear timer i.e. the
                                 amount of time remaining before the cleared event will have
                                 an effect on the VRRP.";
                        }

                        leaf oper-state {
                            type types-vrrp:host-unreachable-event-oper-state;
                            description "The value indicates the current operational state of the event.";
                        }

                        leaf previous-state {
                            type types-vrrp:host-unreachable-event-oper-state;
                            description "The value indicates the previous operational state of the event.";
                        }

                        container statistics {
                            description "Statistics for host unreachable setup.";

                            leaf set-counter {
                                type yang:counter32;
                                description
                                    "The value indicates the number of times the event has transitioned to one of the
                                     'set' states.";
                            }

                        } // container statistics

                    } // list host-unreachable

                    list lag-port-down {
                        key "lag-id";
                        description "Enter the lag-port-down list instance";

                        leaf lag-id {
                            type types-sros:lag-interface;
                            description "LAG ID for the reduced LAG ports";
                        }

                        leaf last-transition {
                            type yang:date-and-time;
                            description
                                "The value indicates the sysUpTime when the operational state of the
                                 event last changed.";
                        }

                        leaf event-in-use {
                            type boolean;
                            description
                                "If value is 'true', then the event is currently affecting the in-use priority
                                 of some virtual router.";
                        }

                        leaf hold-set-remaining {
                            type types-vrrp:event-hold-state;
                            units "seconds";
                            description
                                "The value indicates the current value of the hold-set timer i.e. the
                                 amount of time remaining before the event will transition
                                 into the cleared state.";
                        }

                        leaf hold-clear-remaining {
                            type types-vrrp:event-hold-state;
                            units "seconds";
                            description
                                "The value indicates the current value of the hold-clear timer i.e. the
                                 amount of time remaining before the cleared event will have
                                 an effect on the VRRP.";
                        }

                        leaf oper-state {
                            type types-vrrp:port-down-oper-state;
                            description "The value indicates the current operational state of the event.";
                        }

                        leaf previous-state {
                            type types-vrrp:port-down-oper-state;
                            description "The value indicates the previous operational state of the event.";
                        }

                        container statistics {
                            description "Statistics for host unreachable setup.";

                            leaf set-counter {
                                type yang:counter32;
                                description
                                    "The value indicates the number of times the event has transitioned to one of the
                                     'set' states.";
                            }

                        } // container statistics

                    } // list lag-port-down

                    list mc-ipsec-non-forwarding {
                        key "tunnel-group-id";
                        description "Enter the mc-ipsec-non-forwarding list instance";

                        leaf tunnel-group-id {
                            type uint32 {
                                range "1..16";
                            }
                            description "Multi-chassis IPSEC tunnel group whose non-forwarding state is monitored by priority control event";
                        }

                        leaf last-transition {
                            type yang:date-and-time;
                            description
                                "The value indicates the sysUpTime when the operational state of the
                                 event last changed.";
                        }

                        leaf event-in-use {
                            type boolean;
                            description
                                "If value is 'true', then the event is currently affecting the in-use priority
                                 of some virtual router.";
                        }

                        leaf hold-set-remaining {
                            type types-vrrp:event-hold-state;
                            units "seconds";
                            description
                                "The value indicates the current value of the hold-set timer i.e. the
                                 amount of time remaining before the event will transition
                                 into the cleared state.";
                        }

                        leaf hold-clear-remaining {
                            type types-vrrp:event-hold-state;
                            units "seconds";
                            description
                                "The value indicates the current value of the hold-clear timer i.e. the
                                 amount of time remaining before the cleared event will have
                                 an effect on the VRRP.";
                        }

                        leaf oper-state {
                            type types-vrrp:ip-sec-no-forwarding-oper-state;
                            description "The value indicates the current operational state of the event.";
                        }

                        leaf previous-state {
                            type types-vrrp:ip-sec-no-forwarding-oper-state;
                            description "The value indicates the previous operational state of the event.";
                        }

                        container statistics {
                            description "Statistics for host unreachable setup.";

                            leaf set-counter {
                                type yang:counter32;
                                description
                                    "The value indicates the number of times the event has transitioned to one of the
                                     'set' states.";
                            }

                        } // container statistics

                    } // list mc-ipsec-non-forwarding

                    list port-down {
                        key "port-id";
                        description "Enter the port-down list instance";

                        leaf port-id {
                            type types-sros:port;
                            description "Port ID for the reduced LAG ports";
                        }

                        leaf last-transition {
                            type yang:date-and-time;
                            description
                                "The value indicates the sysUpTime when the operational state of the
                                 event last changed.";
                        }

                        leaf event-in-use {
                            type boolean;
                            description
                                "If value is 'true', then the event is currently affecting the in-use priority
                                 of some virtual router.";
                        }

                        leaf hold-set-remaining {
                            type types-vrrp:event-hold-state;
                            units "seconds";
                            description
                                "The value indicates the current value of the hold-set timer i.e. the
                                 amount of time remaining before the event will transition
                                 into the cleared state.";
                        }

                        leaf hold-clear-remaining {
                            type types-vrrp:event-hold-state;
                            units "seconds";
                            description
                                "The value indicates the current value of the hold-clear timer i.e. the
                                 amount of time remaining before the cleared event will have
                                 an effect on the VRRP.";
                        }

                        leaf oper-state {
                            type types-vrrp:port-down-event-oper-state;
                            description "The value indicates the current operational state of the event.";
                        }

                        leaf previous-state {
                            type types-vrrp:port-down-event-oper-state;
                            description "The value indicates the previous operational state of the event.";
                        }

                        container statistics {
                            description "Statistics for host unreachable setup.";

                            leaf set-counter {
                                type yang:counter32;
                                description
                                    "The value indicates the number of times the event has transitioned to one of the
                                     'set' states.";
                            }

                        } // container statistics

                    } // list port-down

                    list route-unknown {
                        key "ip-prefix";
                        description "Enter the route-unknown list instance";

                        leaf ip-prefix {
                            type types-sros:ip-prefix;
                            description "IP prefix of the route that is monitored by this priority control event";
                        }

                        leaf last-transition {
                            type yang:date-and-time;
                            description
                                "The value indicates the sysUpTime when the operational state of the
                                 event last changed.";
                        }

                        leaf event-in-use {
                            type boolean;
                            description
                                "If value is 'true', then the event is currently affecting the in-use priority
                                 of some virtual router.";
                        }

                        leaf hold-set-remaining {
                            type types-vrrp:event-hold-state;
                            units "seconds";
                            description
                                "The value indicates the current value of the hold-set timer i.e. the
                                 amount of time remaining before the event will transition
                                 into the cleared state.";
                        }

                        leaf hold-clear-remaining {
                            type types-vrrp:event-hold-state;
                            units "seconds";
                            description
                                "The value indicates the current value of the hold-clear timer i.e. the
                                 amount of time remaining before the cleared event will have
                                 an effect on the VRRP.";
                        }

                        leaf oper-state {
                            type types-vrrp:route-unknown-event-oper-state;
                            description "The value indicates the current operational state of the event.";
                        }

                        leaf previous-state {
                            type types-vrrp:route-unknown-event-oper-state;
                            description "The value indicates the previous operational state of the event.";
                        }

                        container statistics {
                            description "Statistics for host unreachable setup.";

                            leaf set-counter {
                                type yang:counter32;
                                description
                                    "The value indicates the number of times the event has transitioned to one of the
                                     'set' states.";
                            }

                        } // container statistics

                    } // list route-unknown

                } // container priority-event

            } // list policy

        } // container vrrp

    } // grouping state-vrrp

}
