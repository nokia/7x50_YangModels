submodule nokia-conf-svc-ies {

    yang-version "1.1";

    belongs-to nokia-conf { prefix "conf"; }

    import ietf-yang-types                { prefix "yang"; }
    import nokia-sros-yang-extensions     { prefix "sros-ext"; }
    import nokia-types-eth-cfm            { prefix "types-eth-cfm"; }
    import nokia-types-ipsec              { prefix "types-ipsec"; }
    import nokia-types-qos                { prefix "types-qos"; }
    import nokia-types-router             { prefix "types-router"; }
    import nokia-types-services           { prefix "types-services"; }
    import nokia-types-sros               { prefix "types-sros"; }
    import nokia-types-subscriber-mgmt    { prefix "types-submgt"; }

    include nokia-conf-bfd;
    include nokia-conf-eth-cfm;
    include nokia-conf-filter;
    include nokia-conf-groups;
    include nokia-conf-ipsec;
    include nokia-conf-isa;
    include nokia-conf-log;
    include nokia-conf-policy-options;
    include nokia-conf-python;
    include nokia-conf-qos;
    include nokia-conf-router;
    include nokia-conf-router-dhcp-server;
    include nokia-conf-routing-options;
    include nokia-conf-service;
    include nokia-conf-submgt-local-user-db;
    include nokia-conf-subscriber-mgmt;
    include nokia-conf-svc-epipe;
    include nokia-conf-svc-ies-sub-if;
    include nokia-conf-svc-ies-vdo-if;
    include nokia-conf-system;
    include nokia-conf-system-security;
    include nokia-conf-vrrp;

    sros-ext:sros-major-release "rel19";

    organization "Nokia";

    contact
        "Nokia SR OS Support
         Web: <http://www.nokia.com>";

    description
        "Nokia YANG Data model to configure ies services on SR OS based routers.

         Copyright 2016 Nokia. All rights reserved. Reproduction of this document
         is authorized on the condition that the foregoing copyright notice is included.

         This nokia-conf-svc-ies YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-06-25";

    grouping conf-svc-ies {
        list ies {
            key "service-name";
            description "Enter the ies list instance";

            leaf service-name {
                type types-services:service-name;
                description "Service name";
            }

            leaf service-id {
                type types-services:external-service-id;
                sros-ext:immutable;
                description "Unique service ID; cannot be used by any other service, regardless of service type";
            }

            leaf description {
                type types-sros:description;
                description "Text description";
            }

            leaf customer {
                type leafref {
                    path "../../customer/customer-name";
                }
                sros-ext:immutable;
                mandatory true;
                description "Service customer ID";
            }

            leaf admin-state {
                type types-sros:admin-state;
                default "disable";
                description "Administrative state of the mirror destination service";
            }

            leaf vpn-id {
                type types-services:vpn-id;
                sros-ext:immutable;
                description "VPN identifier for the service";
            }

            leaf-list apply-groups {
                type leafref {
                    path "../../../groups/group/name";
                }
                max-elements 8;
                ordered-by user;
                description "Apply a configuration group at this level";
            }

            container eth-cfm {
                description "Enter the eth-cfm context";

                leaf-list apply-groups {
                    type leafref {
                        path "../../../../groups/group/name";
                    }
                    max-elements 8;
                    ordered-by user;
                    description "Apply a configuration group at this level";
                }

            } // container eth-cfm

            list interface {
                key "interface-name";
                description "Enter the interface list instance";

                leaf interface-name {
                    type types-sros:interface-name;
                    description "Name of the interface";
                }

                leaf description {
                    type types-sros:very-long-description;
                    description "Text description";
                }

                leaf admin-state {
                    type types-sros:admin-state;
                    default "enable";
                    description "Administrative state of the interface";
                }

                leaf radius-auth-policy {
                    type leafref {
                        path "../../../../subscriber-mgmt/radius-authentication-policy/name";
                    }
                    description "Authentication policy";
                }

                leaf tunnel {
                    type boolean;
                    sros-ext:immutable;
                    default "false";
                    description "Enable/disable tunnel interface";
                }

                leaf static-tunnel-redundant-nexthop {
                    type types-sros:ipv4-unicast-address;
                    description "IPv4 address of the redundant next-hop for static ISA tunnels on this interface";
                }

                leaf dynamic-tunnel-redundant-nexthop {
                    type types-sros:ipv4-unicast-address;
                    description "IPv4 address of the redundant next-hop for dynamic ISA tunnels on this interface";
                }

                leaf loopback {
                    type boolean;
                    default "false";
                    description "Use interface as a loopback interface";
                }

                leaf monitor-oper-group {
                    type leafref {
                        path "../../../oper-group/name";
                    }
                    description "Operational group to monitor";
                }

                leaf shcv-policy-ipv4 {
                    when "not(../tunnel = 'true')";
                    type leafref {
                        path "../../../../subscriber-mgmt/shcv-policy/name";
                    }
                    description "Host connectivity IPv4 policy";
                }

                leaf cpu-protection {
                    type leafref {
                        path "../../../../system/security/cpu-protection/policy/policy-id";
                    }
                    description "CPU protection policy";
                }

                leaf ip-mtu {
                    type types-router:ip-mtu-ext;
                    units "bytes";
                    description "Interface IP MTU";
                }

                leaf mac {
                    type types-sros:mac-unicast-address;
                    description "MAC address for the interface";
                }

                leaf tos-marking-state {
                    type types-router:tos-marking-state;
                    default "untrusted";
                    description "TOS marking state";
                }

                leaf multicast-network-domain {
                    type leafref {
                        path "../../../../router/network-domains/network-domain/domain-name";
                    }
                    description "Network domain name";
                }

                leaf ingress-stats {
                    type boolean;
                    default "false";
                    description "Collect ingress statistics";
                }

                leaf mac-accounting {
                    type boolean;
                    default "false";
                    description "Enable MAC accounting functionality";
                }

                leaf vas-if-type {
                    when "../tunnel = 'false'";
                    type types-router:vas-if-type;
                    description "VAS interface type";
                }

                leaf-list apply-groups {
                    type leafref {
                        path "../../../../groups/group/name";
                    }
                    max-elements 8;
                    ordered-by user;
                    description "Apply a configuration group at this level";
                }

                container ingress {
                    description "Enter the ingress context";

                    leaf policy-accounting {
                        type leafref {
                            path "../../../../../routing-options/policy-accounting/policy-acct-template/name";
                        }
                        description "Configure ingress policy accounting.";
                    }

                } // container ingress

                container load-balancing {
                    description "Enter the load-balancing context";

                    leaf ip-load-balancing {
                        type types-router:ip-load-balancing;
                        default "both";
                        description "Configure IP load balancing algorithm.";
                    }

                    leaf spi-load-balancing {
                        type boolean;
                        default "false";
                        description "Allow use of SPI (Security Parameter Index) in hashing for ESP/AH encrypted IPv4/IPv6 traffic";
                    }

                    leaf teid-load-balancing {
                        type boolean;
                        default "false";
                        description "Include TEID in hashing algorithm for GTP-U/C encapsulated traffic";
                    }

                } // container load-balancing

                list spoke-sdp {
                    key "sdp-bind-id";
                    max-elements 1;
                    description "Enter the spoke-sdp list instance";

                    leaf sdp-bind-id {
                        type types-services:sdp-bind-id;
                        description "SDP Binding identifier as <sdp-id>:<vc-id>. sdp-id - [1..32767] vc-id - [1..4294967295].";
                    }

                    leaf description {
                        type types-sros:description;
                        description "Text description";
                    }

                    leaf admin-state {
                        type types-sros:admin-state;
                        default "enable";
                        description "Administrative state of the SDP binding to the service";
                    }

                    leaf collect-stats {
                        type boolean;
                        default "false";
                        description "Allow agent to collect accounting statistics";
                    }

                    leaf accounting-policy {
                        type leafref {
                            path "../../../../../log/accounting-policy/policy-id";
                        }
                        description "Policy to collect accounting statistics";
                    }

                    leaf control-word {
                        type boolean;
                        default "false";
                        description "Use the control word as preferred";
                    }

                    leaf bfd-template {
                        type leafref {
                            path "../../../../../bfd/bfd-template/name";
                        }
                        description "BFD template associated with SDP binding";
                    }

                    leaf vc-type {
                        type types-services:ies-sdp-bind-vc-type;
                        sros-ext:immutable;
                        default "ether";
                        description "Type of virtual circuit (VC) associated with the SDP binding";
                    }

                    leaf-list apply-groups {
                        type leafref {
                            path "../../../../../groups/group/name";
                        }
                        max-elements 8;
                        ordered-by user;
                        description "Apply a configuration group at this level";
                    }

                    choice label {
                        case entropy {

                            leaf entropy-label {
                                type empty;
                                description "Whether the use of entropy-label is enabled or not.";
                            }

                        }
                        case hash {

                            container hash-label {
                                presence "Enable use of hash-label.";
                                description "Enter the hash-label context";

                                leaf signal-capability {
                                    type empty;
                                    description "To signal the hash label capability to the remote PE.";
                                }

                            } // container hash-label

                        }
                    }
                    container ingress {
                        description "Enter the ingress context";

                        leaf vc-label {
                            type types-services:ingress-vc-label;
                            sros-ext:auto-restart-to-modify;
                            description "Static MPLS VC label used by the far end device to send packets through this SDP";
                        }

                        container filter {
                            description "Enter the filter context";

                            leaf ip {
                                type leafref {
                                    path "../../../../../../../filter/ip-filter/filter-name";
                                }
                                description "IPv4 filter policy name";
                            }

                            leaf ipv6 {
                                type leafref {
                                    path "../../../../../../../filter/ipv6-filter/filter-name";
                                }
                                description "IPv6 filter policy name";
                            }

                        } // container filter

                        container qos {
                            description "Enter the qos context";

                            container network {
                                description "Enter the network context";

                                leaf policy-name {
                                    type leafref {
                                        path "../../../../../../../../qos/network/network-policy-name";
                                    }
                                    description "Ingress network policy name applied to this SDP binding";
                                }

                                container fp-redirect-group {
                                    description "Enter the fp-redirect-group context";

                                    leaf group-name {
                                        type leafref {
                                            path "../../../../../../../../../qos/queue-group-templates/ingress/queue-group/ingress-queue-group-name";
                                        }
                                        description "Forwarding-plane queue group policy for this SDP binding";
                                    }

                                    leaf instance {
                                        type types-services:qos-qgrp-instance-id;
                                        description "Instance of the forwarding-plane ingress Queue Group for this SDP binding";
                                    }

                                } // container fp-redirect-group

                            } // container network

                        } // container qos

                    } // container ingress

                    container egress {
                        description "Enter the egress context";

                        leaf vc-label {
                            type types-services:egress-vc-label;
                            sros-ext:auto-restart-to-modify;
                            description "Static MPLS VC label that is used to send packets to the far end device through this SDP";
                        }

                        container filter {
                            description "Enter the filter context";

                            leaf ip {
                                type leafref {
                                    path "../../../../../../../filter/ip-filter/filter-name";
                                }
                                description "IPv4 filter policy name";
                            }

                            leaf ipv6 {
                                type leafref {
                                    path "../../../../../../../filter/ipv6-filter/filter-name";
                                }
                                description "IPv6 filter policy name";
                            }

                        } // container filter

                        container qos {
                            description "Enter the qos context";

                            container network {
                                description "Enter the network context";

                                leaf policy-name {
                                    type leafref {
                                        path "../../../../../../../../qos/network/network-policy-name";
                                    }
                                    description "Egress network policy name applied to this SDP binding";
                                }

                                container port-redirect-group {
                                    description "Enter the port-redirect-group context";

                                    leaf group-name {
                                        type leafref {
                                            path "../../../../../../../../../qos/queue-group-templates/egress/queue-group/egress-queue-group-name";
                                        }
                                        description "Policy for port queue group for this SDP binding";
                                    }

                                    leaf instance {
                                        type types-services:qos-qgrp-instance-id;
                                        description "Instance of the port egress Queue Group for this SDP binding.";
                                    }

                                } // container port-redirect-group

                            } // container network

                        } // container qos

                    } // container egress

                    container cpu-protection {
                        description "Enter the cpu-protection context";

                        leaf policy-id {
                            type leafref {
                                path "../../../../../../system/security/cpu-protection/policy/policy-id";
                            }
                            description "CPM protection policy";
                        }

                        choice monitoring {
                            case mac {

                                leaf mac-monitoring {
                                    type empty;
                                    description "Monitor MAC for CPU protection";
                                }

                            }
                            case cfm {

                                container eth-cfm-monitoring {
                                    presence "Enable ETH CFM monitoring configuration.";
                                    description "Enter the eth-cfm-monitoring context";

                                    leaf aggregate {
                                        type empty;
                                        description "Apply rate limit to the sum of the per peer packet rates";
                                    }

                                    leaf car {
                                        type empty;
                                        description "Eth-CFM packets to be ignored when enforcing overall rate";
                                    }

                                } // container eth-cfm-monitoring

                            }
                            case ip {

                                leaf ip-src-monitoring {
                                    type empty;
                                    description "Enable IP source monitoring for CPU protection";
                                }

                            }
                        }
                    } // container cpu-protection

                    container bfd-liveness {
                        presence "Enable BFD liveness information.";
                        description "Enter the bfd-liveness context";

                        leaf encap {
                            type types-services:bfd-encap;
                            default "ipv4";
                            description "BFD encapsulation used on this SDP binding";
                        }

                    } // container bfd-liveness

                    container eth-cfm {
                        description "Enter the eth-cfm context";

                        leaf collect-lmm-stats {
                            type boolean;
                            default "false";
                            description "Collect statistics for loss measurement message tests";
                        }

                        leaf-list squelch-ingress-levels {
                            type uint32 {
                                range "0..7";
                            }
                            max-elements 8;
                            description "ETH-CFM PDUs to be silently discarded";
                        }

                        leaf-list apply-groups {
                            type leafref {
                                path "../../../../../../groups/group/name";
                            }
                            max-elements 8;
                            ordered-by user;
                            description "Apply a configuration group at this level";
                        }

                        container collect-lmm-fc-stats {
                            description "Enter the collect-lmm-fc-stats context";

                            leaf-list fc {
                                type types-eth-cfm:fc-type;
                                max-elements 8;
                                description "Forwarding class name for profile-unaware counter";
                            }

                            leaf-list fc-in-profile {
                                type types-eth-cfm:fc-type;
                                max-elements 8;
                                description "Forwarding class name for profile-aware counter";
                            }

                        } // container collect-lmm-fc-stats

                        list mep {
                            key "md-admin-name ma-admin-name mep-id";
                            description "Enter the mep list instance";

                            leaf md-admin-name {
                                type leafref {
                                    path "../../../../../../../eth-cfm/domain/md-admin-name";
                                }
                                description "Admin-assigned maintenance domain index value";
                            }

                            leaf ma-admin-name {
                                type leafref {
                                    path "../../../../../../../eth-cfm/domain[md-admin-name=current()/../md-admin-name]/association/ma-admin-name";
                                }
                                description "Admin-assigned maintenance association index value";
                            }

                            leaf mep-id {
                                type types-eth-cfm:mep-id-type;
                                description "MEP identifier";
                            }

                            leaf admin-state {
                                type types-sros:admin-state;
                                default "disable";
                                description "Administratively enable/disable the MEP.";
                            }

                            leaf description {
                                type types-sros:description;
                                description
                                    "Add/remove a text description for the MEP

                                     A user supplied detailed description for this ETH-CFM MEP.";
                            }

                            leaf low-priority-defect {
                                type types-eth-cfm:lowest-alarm-priority;
                                default "mac-rem-err-xcon";
                                description "Lowest priority defect that is allowed to generate a fault alarm";
                            }

                            leaf fault-propagation {
                                type types-eth-cfm:fault-propagation-type;
                                description "Fault propagation for the MEP";
                            }

                            leaf ccm {
                                type boolean;
                                default "false";
                                description "Generate CCM messages";
                            }

                            leaf ccm-ltm-priority {
                                type types-eth-cfm:frame-priority;
                                default "7";
                                description "Priority of CCM and LTM messages transmitted by the MEP";
                            }

                            leaf ccm-padding-size {
                                type uint32 {
                                    range "3..1500";
                                }
                                description "Number of octets of padding to insert in CCM packets";
                            }

                            leaf one-way-delay-threshold {
                                type uint32 {
                                    range "0..600";
                                }
                                units "seconds";
                                default "3";
                                description "Threshold time limit for one-way delay test";
                            }

                            leaf ais {
                                type boolean;
                                default "false";
                                description "Generate AIS frames from the Maintenance Entity Group (MEG).";
                            }

                            leaf-list apply-groups {
                                type leafref {
                                    path "../../../../../../../groups/group/name";
                                }
                                max-elements 8;
                                ordered-by user;
                                description "Apply a configuration group at this level";
                            }

                            container alarm-notification {

                                leaf fng-alarm-time {
                                    type int32 {
                                        range "250|500|1000";
                                    }
                                    units "centiseconds";
                                    description "The Fault Notification Generation (FNG) alarm time.";
                                }

                                leaf fng-reset-time {
                                    type int32 {
                                        range "250|500|1000";
                                    }
                                    units "centiseconds";
                                    description "The Fault Notification Generation (FNG) reset time.";
                                }

                            } // container alarm-notification

                            container csf {
                                presence "The reception of Client Signal Fail (CSF) message parameters";
                                description "Enter the csf context";

                                leaf multiplier {
                                    type decimal64 {
                                        range "0.0|2.0..30.0";
                                        fraction-digits 1;
                                    }
                                    default "3.5";
                                    description "Receive period multiplier to time out CSF";
                                }

                            } // container csf

                            container eth-test {
                                presence "Enable/disable eth-test functionality on MEP.";
                                description "Enter the eth-test context";

                                leaf bit-error-threshold {
                                    type uint32 {
                                        range "0..11840";
                                    }
                                    units "bit errors";
                                    default "1";
                                    description "Lowest priority defect allowed to generate fault alarm";
                                }

                                container test-pattern {
                                    description "Enter the test-pattern context";

                                    leaf pattern {
                                        type enumeration {
                                            enum "all-zeros"                    { value 0; }
                                            enum "all-ones"                     { value 1; }
                                        }
                                        default "all-zeros";
                                        description "Test pattern for ETH-test frames";
                                    }

                                    leaf crc-tlv {
                                        type boolean;
                                        default "false";
                                        description "Generate a CRC checksum";
                                    }

                                } // container test-pattern

                            } // container eth-test

                            container grace {
                                description "Enter the grace context";

                                container eth-ed {
                                    description "Enter the eth-ed context";

                                    leaf max-rx-defect-window {
                                        type uint32 {
                                            range "1..86400";
                                        }
                                        units "seconds";
                                        description "Maximum received ETH-ED window duration";
                                    }

                                    leaf priority {
                                        type int32 {
                                            range "0..7";
                                        }
                                        description "Transmission priority for ETH-ED PDUs";
                                    }

                                    leaf rx-eth-ed {
                                        type boolean;
                                        default "true";
                                        description "Receive and process ETH-ED ITU-T Y.1731 PDUs on the MEP";
                                    }

                                    leaf tx-eth-ed {
                                        type boolean;
                                        default "false";
                                        description "Transmit ETH-ED PDUs from the MEP";
                                    }

                                } // container eth-ed

                                container eth-vsm-grace {
                                    description "Enter the eth-vsm-grace context";

                                    leaf rx-eth-vsm-grace {
                                        type boolean;
                                        default "true";
                                        description "Receive and process Nokia ETH-CFM Grace PDU on the MEP";
                                    }

                                    leaf tx-eth-vsm-grace {
                                        type boolean;
                                        default "true";
                                        description "Transmit ETH-ED PDUs from the MEP";
                                    }

                                } // container eth-vsm-grace

                            } // container grace

                        } // list mep

                    } // container eth-cfm

                } // list spoke-sdp

                container cflowd-parameters {
                    description "Enter the cflowd-parameters context";

                    list sampling {
                        key "sampling-type";
                        description "Enter the sampling list instance";

                        leaf sampling-type {
                            type types-router:cflowd-sampling;
                            description "Unicast or multicast traffic";
                        }

                        leaf type {
                            when "not(../sampling-type = 'both')";
                            type enumeration {
                                enum "acl"                          { value 1; }
                                enum "interface"                    { value 2; }
                            }
                            mandatory true;
                            description "Type of cflowd analysis";
                        }

                        leaf direction {
                            type enumeration {
                                enum "ingress-only"                 { value 1; }
                                enum "egress-only"                  { value 2; }
                                enum "both"                         { value 3; }
                            }
                            default "ingress-only";
                            description "Direction of traffic for cflowd sampling";
                        }

                        leaf sample-profile {
                            type union {
                                type enumeration {
                                    enum "1"                            { value 1; }
                                }
                                type uint32;
                            }
                            description "Sample profile ID";
                        }

                        leaf-list apply-groups {
                            type leafref {
                                path "../../../../../../groups/group/name";
                            }
                            max-elements 8;
                            ordered-by user;
                            description "Apply a configuration group at this level";
                        }

                    } // list sampling

                } // container cflowd-parameters

                list sap {
                    key "sap-id";
                    max-elements 1;
                    description "Enter the sap list instance";

                    leaf sap-id {
                        type types-sros:sap;
                        description "SAP identifier";
                    }

                    leaf description {
                        type types-sros:long-description;
                        description "Text description";
                    }

                    leaf admin-state {
                        type types-sros:admin-state;
                        default "enable";
                        description "Administrative state of the SAP";
                    }

                    leaf accounting-policy {
                        type leafref {
                            path "../../../../../log/accounting-policy/policy-id";
                        }
                        description "Accounting policy";
                    }

                    leaf anti-spoof {
                        type types-services:anti-spoof-option;
                        description "Anti-spoof filtering";
                    }

                    leaf bandwidth {
                        type types-services:sap-bandwidth;
                        units "kilobps";
                        description "SAP bandwidth";
                    }

                    leaf calling-station-id {
                        type types-sros:string-not-all-spaces {
                            length "1..64";
                        }
                        description "Calling station ID";
                    }

                    leaf collect-stats {
                        type boolean;
                        default "false";
                        description "Collect accounting statistics";
                    }

                    leaf dist-cpu-protection {
                        type leafref {
                            path "../../../../../system/security/dist-cpu-protection/policy/policy-name";
                        }
                        description "Distributed CPU protection policy for SAP";
                    }

                    leaf host-admin-state {
                        type types-sros:admin-state;
                        default "enable";
                        description "Enable/disable administrative state of hosts";
                    }

                    leaf host-lockout-policy {
                        type leafref {
                            path "../../../../../subscriber-mgmt/host-lockout-policy/name";
                        }
                        description "Host lockout policy";
                    }

                    leaf multi-service-site {
                        type types-sros:named-item;
                        description "Multi service site name";
                    }

                    leaf-list apply-groups {
                        type leafref {
                            path "../../../../../groups/group/name";
                        }
                        max-elements 8;
                        ordered-by user;
                        description "Apply a configuration group at this level";
                    }

                    container ingress {
                        description "Enter the ingress context";

                        leaf queue-group-redirect-list {
                            type leafref {
                                path "../../../../../../qos/queue-group-redirect-list/name";
                            }
                            description "Queue group redirect list";
                        }

                        container qos {
                            description "Enter the qos context";

                            leaf match-qinq-dot1p {
                                type enumeration {
                                    enum "top"                          { value 2; }
                                    enum "bottom"                       { value 3; }
                                }
                                description "Ingress match QinQ Dot1p";
                            }

                            container sap-ingress {
                                description "Enter the sap-ingress context";

                                leaf policy-name {
                                    type leafref {
                                        path "../../../../../../../../qos/sap-ingress/sap-ingress-policy-name";
                                    }
                                    description "Policy identifier";
                                }

                                leaf queuing-type {
                                    type types-services:services-sap-queuing-type;
                                    description "Ingress queuing type";
                                }

                                container fp-redirect-group {
                                    description "Enter the fp-redirect-group context";

                                    leaf group-name {
                                        type leafref {
                                            path "../../../../../../../../../qos/queue-group-templates/ingress/queue-group/ingress-queue-group-name";
                                        }
                                        description "Forwarding-plane queue group policy";
                                    }

                                    leaf instance {
                                        type types-services:qos-qgrp-instance-id;
                                        description "Queue group instance";
                                    }

                                } // container fp-redirect-group

                                container overrides {
                                    description "Enter the overrides context";

                                    list queue {
                                        key "queue-id";
                                        description "Enter the queue list instance";

                                        leaf queue-id {
                                            type leafref {
                                                path "../../../../../../../../../../qos/sap-ingress[sap-ingress-policy-name=current()/../../../policy-name]/queue/queue-id";
                                            }
                                            description "Policer unique ID";
                                        }

                                        leaf cbs {
                                            type union {
                                                type uint32 {
                                                    range "0..1048576";
                                                }
                                                type enumeration {
                                                    enum "auto"                         { value -1; }
                                                }
                                            }
                                            units "kilobytes";
                                            description "CBS";
                                        }

                                        leaf mbs {
                                            type union {
                                                type types-qos:bytes {
                                                    range "0..1073741824";
                                                }
                                                type enumeration {
                                                    enum "auto"                         { value -1; }
                                                }
                                            }
                                            units "bytes";
                                            description "MBS";
                                        }

                                        leaf monitor-depth {
                                            type boolean;
                                            default "false";
                                            description "Monitor queue depth";
                                        }

                                        leaf-list apply-groups {
                                            type leafref {
                                                path "../../../../../../../../../../groups/group/name";
                                            }
                                            max-elements 8;
                                            ordered-by user;
                                            description "Apply a configuration group at this level";
                                        }

                                        choice queue-override-rate {
                                            case rate {

                                                container rate {
                                                    description "Enter the rate context";

                                                    leaf pir {
                                                        type types-services:sap-pir-rate-ovr;
                                                        units "kilobps";
                                                        description "PIR rate";
                                                    }

                                                    leaf cir {
                                                        type types-services:sap-cir-rate-ovr;
                                                        units "kilobps";
                                                        description "CIR rate";
                                                    }

                                                } // container rate

                                            }
                                            case percent-rate {

                                                container percent-rate {
                                                    description "Enter the percent-rate context";

                                                    leaf pir {
                                                        type decimal64 {
                                                            range "0.01..100.00";
                                                            fraction-digits 2;
                                                        }
                                                        description "PIR percent rate";
                                                    }

                                                    leaf cir {
                                                        type decimal64 {
                                                            range "0.00..100.00";
                                                            fraction-digits 2;
                                                        }
                                                        description "CIR percent rate";
                                                    }

                                                } // container percent-rate

                                            }
                                        }
                                        container adaptation-rule {
                                            description "Enter the adaptation-rule context";

                                            leaf pir {
                                                type types-qos:adaptation-rule-override;
                                                description "Constraint used when deriving the operational PIR value";
                                            }

                                            leaf cir {
                                                type types-qos:adaptation-rule-override;
                                                description "Constraint used when deriving the operational CIR value";
                                            }

                                        } // container adaptation-rule

                                        container drop-tail {
                                            description "Enter the drop-tail context";

                                            container low {
                                                description "Enter the low context";

                                                leaf percent-reduction-from-mbs {
                                                    type types-qos:burst-percent-or-default-override;
                                                    description "Percentage reduction from the MBS for a queue drop tail";
                                                }

                                            } // container low

                                        } // container drop-tail

                                        container parent {
                                            description "Enter the parent context";

                                            leaf weight {
                                                type types-qos:weight-override;
                                                description "PIR parameter that overrides parent for queue group";
                                            }

                                            leaf cir-weight {
                                                type types-qos:weight-override;
                                                description "CIR parameter that overrides parent for queue group";
                                            }

                                        } // container parent

                                    } // list queue

                                    list policer {
                                        key "policer-id";
                                        description "Enter the policer list instance";

                                        leaf policer-id {
                                            type leafref {
                                                path "../../../../../../../../../../qos/sap-ingress[sap-ingress-policy-name=current()/../../../policy-name]/policer/policer-id";
                                            }
                                            description "Policer unique ID";
                                        }

                                        leaf cbs {
                                            type union {
                                                type types-qos:bytes {
                                                    range "0..16777216";
                                                }
                                                type enumeration {
                                                    enum "auto"                         { value -1; }
                                                }
                                            }
                                            units "bytes";
                                            description "CBS";
                                        }

                                        leaf mbs {
                                            type union {
                                                type types-qos:bytes {
                                                    range "0..1073741824";
                                                }
                                                type enumeration {
                                                    enum "auto"                         { value -1; }
                                                }
                                            }
                                            description "MBS";
                                        }

                                        leaf packet-byte-offset {
                                            type types-qos:ingress-per-packet-offset-override;
                                            description "Size of each packet, handled by the policer, to be modified";
                                        }

                                        leaf stat-mode {
                                            type types-qos:ingress-policer-stat-mode;
                                            description "Mode of statistics collected by the policer";
                                        }

                                        leaf-list apply-groups {
                                            type leafref {
                                                path "../../../../../../../../../../groups/group/name";
                                            }
                                            max-elements 8;
                                            ordered-by user;
                                            description "Apply a configuration group at this level";
                                        }

                                        choice policer-override-rate {
                                            case rate {

                                                container rate {
                                                    description "Enter the rate context";

                                                    leaf pir {
                                                        type union {
                                                            type int64 {
                                                                range "1..6400000000";
                                                            }
                                                            type enumeration {
                                                                enum "max"                          { value -1; }
                                                            }
                                                        }
                                                        units "kilobps";
                                                        description "PIR rate";
                                                    }

                                                    leaf cir {
                                                        type union {
                                                            type int64 {
                                                                range "0..6400000000";
                                                            }
                                                            type enumeration {
                                                                enum "max"                          { value -1; }
                                                            }
                                                        }
                                                        units "kilobps";
                                                        description "CIR rate";
                                                    }

                                                } // container rate

                                            }
                                            case percent-rate {

                                                container percent-rate {
                                                    description "Enter the percent-rate context";

                                                    leaf pir {
                                                        type decimal64 {
                                                            range "0.01..100.00";
                                                            fraction-digits 2;
                                                        }
                                                        description "PIR percent rate";
                                                    }

                                                    leaf cir {
                                                        type decimal64 {
                                                            range "0.00..100.00";
                                                            fraction-digits 2;
                                                        }
                                                        description "CIR percent rate";
                                                    }

                                                } // container percent-rate

                                            }
                                        }
                                    } // list policer

                                } // container overrides

                            } // container sap-ingress

                            container policer-control-policy {
                                description "Enter the policer-control-policy context";

                                leaf policy-name {
                                    type leafref {
                                        path "../../../../../../../../qos/policer-control-policy/policer-control-policy-name";
                                    }
                                    description "Policer control policy name";
                                }

                                container overrides {
                                    presence "Apply a policer control policy override.";
                                    description "Enter the overrides context";

                                    leaf-list apply-groups {
                                        type leafref {
                                            path "../../../../../../../../../groups/group/name";
                                        }
                                        max-elements 8;
                                        ordered-by user;
                                        description "Apply a configuration group at this level";
                                    }

                                    container root {
                                        description "Enter the root context";

                                        leaf max-rate {
                                            type types-services:sap-max-rate-ovr;
                                            description "Maximum frame-based bandwidth limit";
                                        }

                                        container priority-mbs-thresholds {
                                            description "Enter the priority-mbs-thresholds context";

                                            leaf min-thresh-separation {
                                                type union {
                                                    type types-qos:bytes {
                                                        range "0..16777216";
                                                    }
                                                    type enumeration {
                                                        enum "auto"                         { value -1; }
                                                    }
                                                }
                                                units "bytes";
                                                description "Minimum amount of separation buffer space";
                                            }

                                            list priority {
                                                key "priority-level";
                                                description "Enter the priority list instance";

                                                leaf priority-level {
                                                    type types-qos:hierarchy-level;
                                                    description "Priority level";
                                                }

                                                leaf mbs-contribution {
                                                    type union {
                                                        type types-qos:bytes {
                                                            range "0..16777216";
                                                        }
                                                        type enumeration {
                                                            enum "auto"                         { value -1; }
                                                        }
                                                    }
                                                    units "bytes";
                                                    description "Minimum amount of cumulative buffer space allowed";
                                                }

                                                leaf-list apply-groups {
                                                    type leafref {
                                                        path "../../../../../../../../../../../../groups/group/name";
                                                    }
                                                    max-elements 8;
                                                    ordered-by user;
                                                    description "Apply a configuration group at this level";
                                                }

                                            } // list priority

                                        } // container priority-mbs-thresholds

                                    } // container root

                                } // container overrides

                            } // container policer-control-policy

                            container scheduler-policy {
                                description "Enter the scheduler-policy context";

                                leaf policy-name {
                                    type leafref {
                                        path "../../../../../../../../qos/scheduler-policy/scheduler-policy-name";
                                    }
                                    description "Scheduler policy name";
                                }

                                container overrides {
                                    description "Enter the overrides context";

                                    list scheduler {
                                        key "scheduler-name";
                                        description "Enter the scheduler list instance";

                                        leaf scheduler-name {
                                            type types-sros:named-item;
                                            description "Scheduler override policy name";
                                        }

                                        leaf-list apply-groups {
                                            type leafref {
                                                path "../../../../../../../../../../groups/group/name";
                                            }
                                            max-elements 8;
                                            ordered-by user;
                                            description "Apply a configuration group at this level";
                                        }

                                        container parent {
                                            description "Enter the parent context";

                                            leaf weight {
                                                type types-qos:weight;
                                                description "Weight to be used by the scheduler for feeding this queue";
                                            }

                                            leaf cir-weight {
                                                type types-qos:weight;
                                                description "Weight that is used by the scheduler until the committed rate for feeding this queue";
                                            }

                                        } // container parent

                                        container rate {
                                            description "Enter the rate context";

                                            leaf pir {
                                                type union {
                                                    type int64 {
                                                        range "1..6400000000";
                                                    }
                                                    type enumeration {
                                                        enum "max"                          { value -1; }
                                                    }
                                                }
                                                description "Specifies the administrative PIR";
                                            }

                                            leaf cir {
                                                type union {
                                                    type int64 {
                                                        range "0..6400000000";
                                                    }
                                                    type enumeration {
                                                        enum "sum"                          { value -3; }
                                                        enum "max"                          { value -1; }
                                                    }
                                                }
                                                description "Specifies the administrative CIR";
                                            }

                                        } // container rate

                                    } // list scheduler

                                } // container overrides

                            } // container scheduler-policy

                        } // container qos

                        container filter {
                            description "Enter the filter context";

                            leaf ip {
                                type leafref {
                                    path "../../../../../../../filter/ip-filter/filter-name";
                                }
                                description "IPv4 filter policy name";
                            }

                            leaf ipv6 {
                                type leafref {
                                    path "../../../../../../../filter/ipv6-filter/filter-name";
                                }
                                description "IPv6 filter policy name";
                            }

                        } // container filter

                    } // container ingress

                    container egress {
                        description "Enter the egress context";

                        leaf queue-group-redirect-list {
                            type leafref {
                                path "../../../../../../qos/queue-group-redirect-list/name";
                            }
                            description "Assign queue-group redirect list";
                        }

                        container qos {
                            description "Enter the qos context";

                            leaf qinq-mark-top-only {
                                type boolean;
                                default "false";
                                description "Mark top Q-tags";
                            }

                            container sap-egress {
                                description "Enter the sap-egress context";

                                leaf policy-name {
                                    type leafref {
                                        path "../../../../../../../../qos/sap-egress/sap-egress-policy-name";
                                    }
                                    description "Policy identifier";
                                }

                                container port-redirect-group {
                                    description "Enter the port-redirect-group context";

                                    leaf group-name {
                                        type leafref {
                                            path "../../../../../../../../../qos/queue-group-templates/egress/queue-group/egress-queue-group-name";
                                        }
                                        description "Policy for port redirect queue group";
                                    }

                                    leaf instance {
                                        type types-services:qos-qgrp-instance-id;
                                        description "Instance of port queue group";
                                    }

                                } // container port-redirect-group

                                container overrides {
                                    description "Enter the overrides context";

                                    leaf hs-secondary-shaper {
                                        type types-sros:named-item;
                                        description "HS Secondary Shaper";
                                    }

                                    container hsmda-queues {
                                        description "Enter the hsmda-queues context";

                                        leaf secondary-shaper {
                                            type types-sros:named-item;
                                            description "Secondary shaper for the HSMDA queue";
                                        }

                                        leaf packet-byte-offset {
                                            type types-services:egress-hsmda-queue-packet-byte-offset;
                                            description "Packet byte offset for HSMDA queue";
                                        }

                                        leaf wrr-policy {
                                            type leafref {
                                                path "../../../../../../../../../../qos/hsmda-wrr-policy/hsmda-wrr-policy-name";
                                            }
                                            description "WRR policy for the HSMDA queue";
                                        }

                                        list queue {
                                            key "queue-id";
                                            description "Enter the queue list instance";

                                            leaf queue-id {
                                                type leafref {
                                                    path "../../../../../../../../../../../qos/sap-egress[sap-egress-policy-name=current()/../../../../policy-name]/hsmda-queues/queue/queue-id";
                                                }
                                                description "Egress HSMDA queue ID";
                                            }

                                            leaf mbs {
                                                type types-qos:hsmda-queue-burst-size-override;
                                                units "bytes";
                                                description "Buffer space allowed for the queue";
                                            }

                                            leaf rate {
                                                type types-qos:hsmda-queue-pir-rate-override;
                                                description "Administrative PIR rate.";
                                            }

                                            leaf slope-policy {
                                                type leafref {
                                                    path "../../../../../../../../../../../qos/hsmda-slope-policy/hsmda-slope-policy-name";
                                                }
                                                description "Name of the slope-policy which is used to override the default slope-policy for the named buffer pool.";
                                            }

                                            leaf wrr-weight {
                                                type types-qos:hsmda-wrr-weight-override;
                                                description "Weight value for the HSMDA queue";
                                            }

                                            leaf-list apply-groups {
                                                type leafref {
                                                    path "../../../../../../../../../../../groups/group/name";
                                                }
                                                max-elements 8;
                                                ordered-by user;
                                                description "Apply a configuration group at this level";
                                            }

                                        } // list queue

                                    } // container hsmda-queues

                                    list queue {
                                        key "queue-id";
                                        description "Enter the queue list instance";

                                        leaf queue-id {
                                            type leafref {
                                                path "../../../../../../../../../../qos/sap-egress[sap-egress-policy-name=current()/../../../policy-name]/queue/queue-id";
                                            }
                                            description "Policer unique ID";
                                        }

                                        leaf avg-frame-overhead {
                                            type decimal64 {
                                                range "0.00..100.00";
                                                fraction-digits 2;
                                            }
                                            description "Average packet-to-frame encapsulation overhead";
                                        }

                                        leaf burst-limit {
                                            type union {
                                                type types-qos:bytes {
                                                    range "1..14000000";
                                                }
                                                type enumeration {
                                                    enum "auto"                         { value -1; }
                                                }
                                            }
                                            description "Explicit shaping burst size of a queue.";
                                        }

                                        leaf cbs {
                                            type union {
                                                type uint32 {
                                                    range "0..1048576";
                                                }
                                                type enumeration {
                                                    enum "auto"                         { value -1; }
                                                }
                                            }
                                            units "kilobytes";
                                            description "CBS";
                                        }

                                        leaf mbs {
                                            type union {
                                                type types-qos:bytes {
                                                    range "0..1073741824";
                                                }
                                                type enumeration {
                                                    enum "auto"                         { value -1; }
                                                }
                                            }
                                            units "bytes";
                                            description "MBS";
                                        }

                                        leaf monitor-depth {
                                            type boolean;
                                            default "false";
                                            description "Monitor queue depth";
                                        }

                                        leaf hs-wrr-weight {
                                            type types-qos:hs-wrr-weight-override;
                                            default "1";
                                            description "Weighted Round Robin (WRR) weight to parent with this queue into the scheduler";
                                        }

                                        leaf hs-class-weight {
                                            type types-qos:hs-class-weight-override;
                                            description "Scheduling class weight.";
                                        }

                                        leaf-list apply-groups {
                                            type leafref {
                                                path "../../../../../../../../../../groups/group/name";
                                            }
                                            max-elements 8;
                                            ordered-by user;
                                            description "Apply a configuration group at this level";
                                        }

                                        choice queue-override-rate {
                                            case rate {

                                                container rate {
                                                    description "Enter the rate context";

                                                    leaf pir {
                                                        type types-services:sap-pir-rate-ovr;
                                                        units "kilobps";
                                                        description "PIR rate";
                                                    }

                                                    leaf cir {
                                                        type types-services:sap-cir-rate-ovr;
                                                        units "kilobps";
                                                        description "CIR rate";
                                                    }

                                                } // container rate

                                            }
                                            case percent-rate {

                                                container percent-rate {
                                                    description "Enter the percent-rate context";

                                                    leaf pir {
                                                        type decimal64 {
                                                            range "0.01..100.00";
                                                            fraction-digits 2;
                                                        }
                                                        description "PIR percent rate";
                                                    }

                                                    leaf cir {
                                                        type decimal64 {
                                                            range "0.00..100.00";
                                                            fraction-digits 2;
                                                        }
                                                        description "CIR percent rate";
                                                    }

                                                } // container percent-rate

                                            }
                                        }
                                        container adaptation-rule {
                                            description "Enter the adaptation-rule context";

                                            leaf pir {
                                                type types-qos:adaptation-rule-override;
                                                description "Constraint used when deriving the operational PIR value";
                                            }

                                            leaf cir {
                                                type types-qos:adaptation-rule-override;
                                                description "Constraint used when deriving the operational CIR value";
                                            }

                                        } // container adaptation-rule

                                        container drop-tail {
                                            description "Enter the drop-tail context";

                                            container low {
                                                description "Enter the low context";

                                                leaf percent-reduction-from-mbs {
                                                    type types-qos:burst-percent-or-default-override;
                                                    description "Percentage reduction from the MBS for a queue drop tail";
                                                }

                                            } // container low

                                        } // container drop-tail

                                        container parent {
                                            description "Enter the parent context";

                                            leaf weight {
                                                type types-qos:weight-override;
                                                description "PIR parameter that overrides parent for queue group";
                                            }

                                            leaf cir-weight {
                                                type types-qos:weight-override;
                                                description "CIR parameter that overrides parent for queue group";
                                            }

                                        } // container parent

                                        container hs-wred-queue {
                                            description "Enter the hs-wred-queue context";

                                            leaf policy {
                                                type leafref {
                                                    path "../../../../../../../../../../../qos/slope-policy/slope-policy-name";
                                                }
                                                description "Name of slope-policy.";
                                            }

                                        } // container hs-wred-queue

                                    } // list queue

                                    list policer {
                                        key "policer-id";
                                        description "Enter the policer list instance";

                                        leaf policer-id {
                                            type leafref {
                                                path "../../../../../../../../../../qos/sap-egress[sap-egress-policy-name=current()/../../../policy-name]/policer/policer-id";
                                            }
                                            description "Policer unique ID";
                                        }

                                        leaf cbs {
                                            type union {
                                                type types-qos:bytes {
                                                    range "0..16777216";
                                                }
                                                type enumeration {
                                                    enum "auto"                         { value -1; }
                                                }
                                            }
                                            units "bytes";
                                            description "CBS";
                                        }

                                        leaf mbs {
                                            type union {
                                                type types-qos:bytes {
                                                    range "0..1073741824";
                                                }
                                                type enumeration {
                                                    enum "auto"                         { value -1; }
                                                }
                                            }
                                            description "MBS";
                                        }

                                        leaf packet-byte-offset {
                                            type types-qos:egress-per-packet-offset-override;
                                            description "Size of each packet, handled by the policer, to be modified";
                                        }

                                        leaf stat-mode {
                                            type types-qos:egress-policer-stat-mode;
                                            description "Mode of statistics collected by the policer";
                                        }

                                        leaf-list apply-groups {
                                            type leafref {
                                                path "../../../../../../../../../../groups/group/name";
                                            }
                                            max-elements 8;
                                            ordered-by user;
                                            description "Apply a configuration group at this level";
                                        }

                                        choice policer-override-rate {
                                            case rate {

                                                container rate {
                                                    description "Enter the rate context";

                                                    leaf pir {
                                                        type union {
                                                            type int64 {
                                                                range "1..6400000000";
                                                            }
                                                            type enumeration {
                                                                enum "max"                          { value -1; }
                                                            }
                                                        }
                                                        units "kilobps";
                                                        description "PIR rate";
                                                    }

                                                    leaf cir {
                                                        type union {
                                                            type int64 {
                                                                range "0..6400000000";
                                                            }
                                                            type enumeration {
                                                                enum "max"                          { value -1; }
                                                            }
                                                        }
                                                        units "kilobps";
                                                        description "CIR rate";
                                                    }

                                                } // container rate

                                            }
                                            case percent-rate {

                                                container percent-rate {
                                                    description "Enter the percent-rate context";

                                                    leaf pir {
                                                        type decimal64 {
                                                            range "0.01..100.00";
                                                            fraction-digits 2;
                                                        }
                                                        description "PIR percent rate";
                                                    }

                                                    leaf cir {
                                                        type decimal64 {
                                                            range "0.00..100.00";
                                                            fraction-digits 2;
                                                        }
                                                        description "CIR percent rate";
                                                    }

                                                } // container percent-rate

                                            }
                                        }
                                    } // list policer

                                    list hs-wrr-group {
                                        key "group-id";
                                        description "Enter the hs-wrr-group list instance";

                                        leaf group-id {
                                            type leafref {
                                                path "../../../../../../../../../../qos/sap-egress[sap-egress-policy-name=current()/../../../policy-name]/hs-wrr-group/group-id";
                                            }
                                            description "HS WRR group identifier";
                                        }

                                        leaf hs-class-weight {
                                            type types-qos:hs-class-weight-override;
                                            description "Weight of scheduling class.";
                                        }

                                        leaf-list apply-groups {
                                            type leafref {
                                                path "../../../../../../../../../../groups/group/name";
                                            }
                                            max-elements 8;
                                            ordered-by user;
                                            description "Apply a configuration group at this level";
                                        }

                                        choice rate-or-percent-rate {
                                            case rate {

                                                leaf rate {
                                                    type union {
                                                        type uint32 {
                                                            range "1..2000000000";
                                                        }
                                                        type enumeration {
                                                            enum "max"                          { value -1; }
                                                        }
                                                    }
                                                    units "kilobps";
                                                    description "Administrative PIR.";
                                                }

                                            }
                                            case percent-rate {

                                                leaf percent-rate {
                                                    type decimal64 {
                                                        range "0.01..100.00";
                                                        fraction-digits 2;
                                                    }
                                                    description "Administrative PIR percent.";
                                                }

                                            }
                                        }
                                    } // list hs-wrr-group

                                } // container overrides

                            } // container sap-egress

                            container policer-control-policy {
                                description "Enter the policer-control-policy context";

                                leaf policy-name {
                                    type leafref {
                                        path "../../../../../../../../qos/policer-control-policy/policer-control-policy-name";
                                    }
                                    description "Policer control policy name";
                                }

                                container overrides {
                                    presence "Apply a policer control policy override.";
                                    description "Enter the overrides context";

                                    leaf-list apply-groups {
                                        type leafref {
                                            path "../../../../../../../../../groups/group/name";
                                        }
                                        max-elements 8;
                                        ordered-by user;
                                        description "Apply a configuration group at this level";
                                    }

                                    container root {
                                        description "Enter the root context";

                                        leaf max-rate {
                                            type types-services:sap-max-rate-ovr;
                                            description "Maximum frame-based bandwidth limit";
                                        }

                                        container priority-mbs-thresholds {
                                            description "Enter the priority-mbs-thresholds context";

                                            leaf min-thresh-separation {
                                                type union {
                                                    type types-qos:bytes {
                                                        range "0..16777216";
                                                    }
                                                    type enumeration {
                                                        enum "auto"                         { value -1; }
                                                    }
                                                }
                                                units "bytes";
                                                description "Minimum amount of separation buffer space";
                                            }

                                            list priority {
                                                key "priority-level";
                                                description "Enter the priority list instance";

                                                leaf priority-level {
                                                    type types-qos:hierarchy-level;
                                                    description "Priority level";
                                                }

                                                leaf mbs-contribution {
                                                    type union {
                                                        type types-qos:bytes {
                                                            range "0..16777216";
                                                        }
                                                        type enumeration {
                                                            enum "auto"                         { value -1; }
                                                        }
                                                    }
                                                    units "bytes";
                                                    description "Minimum amount of cumulative buffer space allowed";
                                                }

                                                leaf-list apply-groups {
                                                    type leafref {
                                                        path "../../../../../../../../../../../../groups/group/name";
                                                    }
                                                    max-elements 8;
                                                    ordered-by user;
                                                    description "Apply a configuration group at this level";
                                                }

                                            } // list priority

                                        } // container priority-mbs-thresholds

                                    } // container root

                                } // container overrides

                            } // container policer-control-policy

                            container scheduler-policy {
                                description "Enter the scheduler-policy context";

                                leaf policy-name {
                                    type leafref {
                                        path "../../../../../../../../qos/scheduler-policy/scheduler-policy-name";
                                    }
                                    description "Scheduler policy name";
                                }

                                container overrides {
                                    description "Enter the overrides context";

                                    list scheduler {
                                        key "scheduler-name";
                                        description "Enter the scheduler list instance";

                                        leaf scheduler-name {
                                            type types-sros:named-item;
                                            description "Scheduler override policy name";
                                        }

                                        leaf-list apply-groups {
                                            type leafref {
                                                path "../../../../../../../../../../groups/group/name";
                                            }
                                            max-elements 8;
                                            ordered-by user;
                                            description "Apply a configuration group at this level";
                                        }

                                        container parent {
                                            description "Enter the parent context";

                                            leaf weight {
                                                type types-qos:weight;
                                                description "Weight to be used by the scheduler for feeding this queue";
                                            }

                                            leaf cir-weight {
                                                type types-qos:weight;
                                                description "Weight that is used by the scheduler until the committed rate for feeding this queue";
                                            }

                                        } // container parent

                                        container rate {
                                            description "Enter the rate context";

                                            leaf pir {
                                                type union {
                                                    type int64 {
                                                        range "1..6400000000";
                                                    }
                                                    type enumeration {
                                                        enum "max"                          { value -1; }
                                                    }
                                                }
                                                description "Specifies the administrative PIR";
                                            }

                                            leaf cir {
                                                type union {
                                                    type int64 {
                                                        range "0..6400000000";
                                                    }
                                                    type enumeration {
                                                        enum "sum"                          { value -3; }
                                                        enum "max"                          { value -1; }
                                                    }
                                                }
                                                description "Specifies the administrative CIR";
                                            }

                                        } // container rate

                                    } // list scheduler

                                } // container overrides

                            } // container scheduler-policy

                            container vlan-qos-policy {
                                description "Enter the vlan-qos-policy context";

                                leaf policy-name {
                                    type leafref {
                                        path "../../../../../../../../qos/vlan-qos-policy/vlan-qos-policy-name";
                                    }
                                    description "Egress vlan-qos-policy name";
                                }

                            } // container vlan-qos-policy

                            container egress-remark-policy {
                                description "Enter the egress-remark-policy context";

                                leaf policy-name {
                                    type leafref {
                                        path "../../../../../../../../qos/egress-remark-policy/egress-remark-policy-name";
                                    }
                                    description "Egress-remark-policy name";
                                }

                            } // container egress-remark-policy

                        } // container qos

                        container filter {
                            description "Enter the filter context";

                            leaf ip {
                                type leafref {
                                    path "../../../../../../../filter/ip-filter/filter-name";
                                }
                                description "IPv4 filter policy name";
                            }

                            leaf ipv6 {
                                type leafref {
                                    path "../../../../../../../filter/ipv6-filter/filter-name";
                                }
                                description "IPv6 filter policy name";
                            }

                        } // container filter

                        container agg-rate {
                            description "Enter the agg-rate context";

                            leaf limit-unused-bandwidth {
                                type boolean;
                                default "false";
                                description "Enable aggregate rate overrun protection";
                            }

                            leaf rate {
                                type types-services:agg-rate-rate;
                                description "Maximum total rate of all egress queues in kbps.";
                            }

                            leaf queue-frame-based-accounting {
                                type boolean;
                                default "false";
                                description "Enable frame-based accounting on all policers and queues associated with context";
                            }

                            leaf cir {
                                type union {
                                    type int32 {
                                        range "0..100000000";
                                    }
                                    type enumeration {
                                        enum "max"                          { value -1; }
                                    }
                                }
                                units "kilobps";
                                default "0";
                                description "Specifies the administrative CIR.";
                            }

                        } // container agg-rate

                    } // container egress

                    container cpu-protection {
                        description "Enter the cpu-protection context";

                        leaf policy-id {
                            type leafref {
                                path "../../../../../../system/security/cpu-protection/policy/policy-id";
                            }
                            description "CPM protection policy";
                        }

                        choice monitoring {
                            case mac {

                                leaf mac-monitoring {
                                    type empty;
                                    description "Monitor MAC for CPU protection";
                                }

                            }
                            case cfm {

                                container eth-cfm-monitoring {
                                    presence "Enable ETH CFM monitoring configuration.";
                                    description "Enter the eth-cfm-monitoring context";

                                    leaf aggregate {
                                        type empty;
                                        description "Apply rate limit to the sum of the per peer packet rates";
                                    }

                                    leaf car {
                                        type empty;
                                        description "Eth-CFM packets to be ignored when enforcing overall rate";
                                    }

                                } // container eth-cfm-monitoring

                            }
                            case ip {

                                leaf ip-src-monitoring {
                                    type empty;
                                    description "Enable IP source monitoring for CPU protection";
                                }

                            }
                        }
                    } // container cpu-protection

                    container lag {
                        description "Enter the lag context";

                        leaf link-map-profile {
                            type types-services:link-map-profile-id;
                            description "LAG link map profile applied to a SAP or network interface";
                        }

                        container per-link-hash {
                            description "Enter the per-link-hash context";

                            leaf class {
                                type types-services:sap-lag-per-link-hash-class;
                                default "1";
                                description "Class used on LAG egress when using weighted per-link-hash";
                            }

                            leaf weight {
                                type types-services:sap-lag-per-link-hash-weight;
                                default "1";
                                description "Weight used on LAG egress when using weighted per-link-hash";
                            }

                        } // container per-link-hash

                    } // container lag

                    container fwd-wholesale {
                        description "Enter the fwd-wholesale context";

                        leaf pppoe-service {
                            type leafref {
                                path "../../../../../epipe/service-name";
                            }
                            description "PPPoE service name";
                        }

                    } // container fwd-wholesale

                    container eth-cfm {
                        description "Enter the eth-cfm context";

                        leaf collect-lmm-stats {
                            type boolean;
                            default "false";
                            description "Collect statistics for loss measurement message tests";
                        }

                        leaf-list squelch-ingress-levels {
                            type uint32 {
                                range "0..7";
                            }
                            max-elements 8;
                            description "ETH-CFM PDUs to be silently discarded";
                        }

                        leaf-list apply-groups {
                            type leafref {
                                path "../../../../../../groups/group/name";
                            }
                            max-elements 8;
                            ordered-by user;
                            description "Apply a configuration group at this level";
                        }

                        container collect-lmm-fc-stats {
                            description "Enter the collect-lmm-fc-stats context";

                            leaf-list fc {
                                type types-eth-cfm:fc-type;
                                max-elements 8;
                                description "Forwarding class name for profile-unaware counter";
                            }

                            leaf-list fc-in-profile {
                                type types-eth-cfm:fc-type;
                                max-elements 8;
                                description "Forwarding class name for profile-aware counter";
                            }

                        } // container collect-lmm-fc-stats

                        list mep {
                            key "md-admin-name ma-admin-name mep-id";
                            description "Enter the mep list instance";

                            leaf md-admin-name {
                                type leafref {
                                    path "../../../../../../../eth-cfm/domain/md-admin-name";
                                }
                                description "Admin-assigned maintenance domain index value";
                            }

                            leaf ma-admin-name {
                                type leafref {
                                    path "../../../../../../../eth-cfm/domain[md-admin-name=current()/../md-admin-name]/association/ma-admin-name";
                                }
                                description "Admin-assigned maintenance association index value";
                            }

                            leaf mep-id {
                                type types-eth-cfm:mep-id-type;
                                description "MEP identifier";
                            }

                            leaf admin-state {
                                type types-sros:admin-state;
                                default "disable";
                                description "Administratively enable/disable the MEP.";
                            }

                            leaf description {
                                type types-sros:description;
                                description
                                    "Add/remove a text description for the MEP

                                     A user supplied detailed description for this ETH-CFM MEP.";
                            }

                            leaf low-priority-defect {
                                type types-eth-cfm:lowest-alarm-priority;
                                default "mac-rem-err-xcon";
                                description "Lowest priority defect that is allowed to generate a fault alarm";
                            }

                            leaf fault-propagation {
                                type types-eth-cfm:fault-propagation-type;
                                description "Fault propagation for the MEP";
                            }

                            leaf ccm {
                                type boolean;
                                default "false";
                                description "Generate CCM messages";
                            }

                            leaf ccm-ltm-priority {
                                type types-eth-cfm:frame-priority;
                                default "7";
                                description "Priority of CCM and LTM messages transmitted by the MEP";
                            }

                            leaf ccm-padding-size {
                                type uint32 {
                                    range "3..1500";
                                }
                                description "Number of octets of padding to insert in CCM packets";
                            }

                            leaf one-way-delay-threshold {
                                type uint32 {
                                    range "0..600";
                                }
                                units "seconds";
                                default "3";
                                description "Threshold time limit for one-way delay test";
                            }

                            leaf ais {
                                type boolean;
                                default "false";
                                description "Generate AIS frames from the Maintenance Entity Group (MEG).";
                            }

                            leaf-list apply-groups {
                                type leafref {
                                    path "../../../../../../../groups/group/name";
                                }
                                max-elements 8;
                                ordered-by user;
                                description "Apply a configuration group at this level";
                            }

                            container alarm-notification {

                                leaf fng-alarm-time {
                                    type int32 {
                                        range "250|500|1000";
                                    }
                                    units "centiseconds";
                                    description "The Fault Notification Generation (FNG) alarm time.";
                                }

                                leaf fng-reset-time {
                                    type int32 {
                                        range "250|500|1000";
                                    }
                                    units "centiseconds";
                                    description "The Fault Notification Generation (FNG) reset time.";
                                }

                            } // container alarm-notification

                            container csf {
                                presence "The reception of Client Signal Fail (CSF) message parameters";
                                description "Enter the csf context";

                                leaf multiplier {
                                    type decimal64 {
                                        range "0.0|2.0..30.0";
                                        fraction-digits 1;
                                    }
                                    default "3.5";
                                    description "Receive period multiplier to time out CSF";
                                }

                            } // container csf

                            container eth-test {
                                presence "Enable/disable eth-test functionality on MEP.";
                                description "Enter the eth-test context";

                                leaf bit-error-threshold {
                                    type uint32 {
                                        range "0..11840";
                                    }
                                    units "bit errors";
                                    default "1";
                                    description "Lowest priority defect allowed to generate fault alarm";
                                }

                                container test-pattern {
                                    description "Enter the test-pattern context";

                                    leaf pattern {
                                        type enumeration {
                                            enum "all-zeros"                    { value 0; }
                                            enum "all-ones"                     { value 1; }
                                        }
                                        default "all-zeros";
                                        description "Test pattern for ETH-test frames";
                                    }

                                    leaf crc-tlv {
                                        type boolean;
                                        default "false";
                                        description "Generate a CRC checksum";
                                    }

                                } // container test-pattern

                            } // container eth-test

                            container grace {
                                description "Enter the grace context";

                                container eth-ed {
                                    description "Enter the eth-ed context";

                                    leaf max-rx-defect-window {
                                        type uint32 {
                                            range "1..86400";
                                        }
                                        units "seconds";
                                        description "Maximum received ETH-ED window duration";
                                    }

                                    leaf priority {
                                        type int32 {
                                            range "0..7";
                                        }
                                        description "Transmission priority for ETH-ED PDUs";
                                    }

                                    leaf rx-eth-ed {
                                        type boolean;
                                        default "true";
                                        description "Receive and process ETH-ED ITU-T Y.1731 PDUs on the MEP";
                                    }

                                    leaf tx-eth-ed {
                                        type boolean;
                                        default "false";
                                        description "Transmit ETH-ED PDUs from the MEP";
                                    }

                                } // container eth-ed

                                container eth-vsm-grace {
                                    description "Enter the eth-vsm-grace context";

                                    leaf rx-eth-vsm-grace {
                                        type boolean;
                                        default "true";
                                        description "Receive and process Nokia ETH-CFM Grace PDU on the MEP";
                                    }

                                    leaf tx-eth-vsm-grace {
                                        type boolean;
                                        default "true";
                                        description "Transmit ETH-ED PDUs from the MEP";
                                    }

                                } // container eth-vsm-grace

                            } // container grace

                        } // list mep

                    } // container eth-cfm

                    list ip-tunnel {
                        key "tunnel-name";
                        max-elements 1;
                        description "Enter the ip-tunnel list instance";

                        leaf tunnel-name {
                            type types-sros:interface-name;
                            description "IP tunnel name";
                        }

                        leaf admin-state {
                            type types-sros:admin-state;
                            default "disable";
                            description "Administrative state of the tunnel";
                        }

                        leaf description {
                            type types-sros:description;
                            sros-ext:auto-restart-to-modify;
                            description "Text description";
                        }

                        leaf clear-df-bit {
                            type boolean;
                            sros-ext:auto-restart-to-modify;
                            default "false";
                            description "Clear the Do-not-Fragment bit";
                        }

                        leaf delivery-service {
                            type types-services:service-name;
                            sros-ext:auto-restart-to-modify;
                            description "Delivery service name";
                        }

                        leaf dscp {
                            type types-qos:dscp-name;
                            sros-ext:auto-restart-to-modify;
                            description "Differentiated Services Code Point (DSCP) name";
                        }

                        leaf encapsulated-ip-mtu {
                            type uint32 {
                                range "512..9000";
                            }
                            units "bytes";
                            sros-ext:auto-restart-to-modify;
                            description "Encapsulated IP MTU of this tunnel";
                        }

                        leaf ip-mtu {
                            type uint32 {
                                range "512..9000";
                            }
                            units "bytes";
                            sros-ext:auto-restart-to-modify;
                            description "IP MTU of this tunnel";
                        }

                        leaf public-tcp-mss-adjust {
                            type union {
                                type uint32 {
                                    range "512..9000";
                                }
                                type enumeration {
                                    enum "auto"                         { value 0; }
                                }
                            }
                            units "bytes";
                            sros-ext:auto-restart-to-modify;
                            description "TCP maximum segment size (MSS) on private network";
                        }

                        leaf private-tcp-mss-adjust {
                            type int32 {
                                range "512..9000";
                            }
                            units "bytes";
                            sros-ext:auto-restart-to-modify;
                            description "TCP maximum segment size (MSS) on private network";
                        }

                        leaf reassembly {
                            type union {
                                type int32 {
                                    range "1..5000";
                                }
                                type enumeration {
                                    enum "use-tunnel-group-setting"     { value -1; }
                                    enum "none"                         { value 0; }
                                }
                            }
                            units "milliseconds";
                            sros-ext:auto-restart-to-modify;
                            description "Reassembly wait time";
                        }

                        leaf remote-ip-address {
                            type types-sros:ip-address;
                            sros-ext:auto-restart-to-modify;
                            description "Remote IP address of this tunnel";
                        }

                        leaf backup-remote-ip-address {
                            type types-sros:ip-address;
                            sros-ext:auto-restart-to-modify;
                            description "Backup remote IP address that is applied to this tunnel";
                        }

                        leaf local-ip-address {
                            type types-sros:ip-address;
                            sros-ext:auto-restart-to-modify;
                            description "Local IP address of this tunnel";
                        }

                        leaf-list apply-groups {
                            type leafref {
                                path "../../../../../../groups/group/name";
                            }
                            max-elements 8;
                            ordered-by user;
                            sros-ext:auto-restart-to-modify;
                            description "Apply a configuration group at this level";
                        }

                        container icmp6-generation {
                            sros-ext:auto-restart-to-modify;
                            description "Enter the icmp6-generation context";

                            container packet-too-big {
                                sros-ext:auto-restart-to-modify;
                                description "Enter the packet-too-big context";

                                leaf admin-state {
                                    type types-sros:admin-state;
                                    sros-ext:auto-restart-to-modify;
                                    description "Administrative state of sending Packet Too Big messages";
                                }

                                leaf number {
                                    type uint32 {
                                        range "10..1000";
                                    }
                                    sros-ext:auto-restart-to-modify;
                                    default "100";
                                    description "Number of packet-too-big ICMPv6 messages issued in a specified time frame";
                                }

                                leaf seconds {
                                    type uint32 {
                                        range "1..60";
                                    }
                                    units "seconds";
                                    sros-ext:auto-restart-to-modify;
                                    default "10";
                                    description "Time frame to limit the number of packet-too-big ICMPv6 messages";
                                }

                            } // container packet-too-big

                        } // container icmp6-generation

                        container gre-header {
                            sros-ext:auto-restart-to-modify;
                            description "Enter the gre-header context";

                            leaf admin-state {
                                type types-sros:admin-state;
                                sros-ext:auto-restart-to-modify;
                                description "Administrative state of the GRE header in the tunnel";
                            }

                            container key {
                                sros-ext:auto-restart-to-modify;
                                description "Enter the key context";

                                leaf admin-state {
                                    type types-sros:admin-state;
                                    sros-ext:auto-restart-to-modify;
                                    default "disable";
                                    description "Administrative state of the keys in the GRE header";
                                }

                                leaf send {
                                    type uint32;
                                    sros-ext:auto-restart-to-modify;
                                    default "0";
                                    description "Send key of a GRE header";
                                }

                                leaf receive {
                                    type uint32;
                                    sros-ext:auto-restart-to-modify;
                                    default "0";
                                    description "Receive key of a GRE header";
                                }

                            } // container key

                        } // container gre-header

                        list dest-ip {
                            key "dest-ip-address";
                            sros-ext:auto-restart-to-modify;
                            description "Add a list entry for dest-ip";

                            leaf dest-ip-address {
                                type types-sros:ip-address;
                                description "Destination IP address of the tunnel";
                            }

                        } // list dest-ip

                    } // list ip-tunnel

                    list ipsec-gateway {
                        key "name";
                        max-elements 1;
                        description "Enter the ipsec-gateway list instance";

                        leaf name {
                            type types-sros:named-item;
                            description "IPsec gateway name.";
                        }

                        leaf admin-state {
                            type types-sros:admin-state;
                            default "disable";
                            description "Administrative state of the IPsec gateway.";
                        }

                        leaf default-tunnel-template {
                            type leafref {
                                path "../../../../../../ipsec/tunnel-template/id";
                            }
                            description "The IPsec tunnel template ID.";
                        }

                        leaf ike-policy {
                            type leafref {
                                path "../../../../../../ipsec/ike-policy/id";
                            }
                            description "IKE policy ID.";
                        }

                        leaf pre-shared-key {
                            type types-sros:encrypted-leaf {
                                length "1..115";
                            }
                            description "The pre-shared key used for authentication by two peers forming the tunnel for the IPSec gateway.";
                        }

                        leaf ts-list {
                            type leafref {
                                path "../../../../../../ipsec/ts-list/name";
                            }
                            description "The name of Traffic Selector (TS) list, used for IKEv2 TS negotiation.";
                        }

                        leaf-list apply-groups {
                            type leafref {
                                path "../../../../../../groups/group/name";
                            }
                            max-elements 8;
                            ordered-by user;
                            description "Apply a configuration group at this level";
                        }

                        container dhcp-address-assignment {
                            description "Enter the dhcp-address-assignment context";

                            container dhcpv4 {
                                presence "DHCPv4 server information.";
                                description "Enter the dhcpv4 context";

                                leaf admin-state {
                                    type types-sros:admin-state;
                                    default "disable";
                                    description "Administrative state of the IPsec DHCPv4 server.";
                                }

                                leaf gi-address {
                                    type types-sros:ipv4-unicast-address;
                                    description "The giaddr of relayed DHCPv4 header.";
                                }

                                leaf send-release {
                                    type boolean;
                                    default "true";
                                    description "Send DHCPv4 release messages.";
                                }

                                leaf-list apply-groups {
                                    type leafref {
                                        path "../../../../../../../../groups/group/name";
                                    }
                                    max-elements 8;
                                    ordered-by user;
                                    description "Apply a configuration group at this level";
                                }

                                container server {
                                    description "Enter the server context";

                                    leaf-list address {
                                        type types-sros:ipv4-unicast-address;
                                        max-elements 8;
                                        description "The DHCPv4 server addresses.";
                                    }

                                    leaf router-instance {
                                        type types-sros:router-instance-base-vprn-loose;
                                        description "Router instance to reach the DHCPv4 server.";
                                    }

                                } // container server

                            } // container dhcpv4

                            container dhcpv6 {
                                presence "DHCPv6 server information.";
                                description "Enter the dhcpv6 context";

                                leaf admin-state {
                                    type types-sros:admin-state;
                                    default "disable";
                                    description "Administrative state of the IPsec DHCPv6 server.";
                                }

                                leaf link-address {
                                    type types-sros:ipv6-unicast-address;
                                    description "The link-address in DHCPv6 relay packet.";
                                }

                                leaf send-release {
                                    type boolean;
                                    default "true";
                                    description "Send DHCPv6 release messages when a tunnel is down.";
                                }

                                leaf-list apply-groups {
                                    type leafref {
                                        path "../../../../../../../../groups/group/name";
                                    }
                                    max-elements 8;
                                    ordered-by user;
                                    description "Apply a configuration group at this level";
                                }

                                container server {
                                    description "Enter the server context";

                                    leaf-list address {
                                        type types-sros:ipv6-unicast-address;
                                        max-elements 8;
                                        description "The DHCPv6 server addresses.";
                                    }

                                    leaf router-instance {
                                        type types-sros:router-instance-base-vprn-loose;
                                        description "Router instance to reach the DHCPv6 server.";
                                    }

                                } // container server

                            } // container dhcpv6

                        } // container dhcp-address-assignment

                        container cert {
                            description "Enter the cert context";

                            leaf cert-profile {
                                type leafref {
                                    path "../../../../../../../ipsec/cert-profile/name";
                                }
                                description "Certificate profile name.";
                            }

                            leaf trust-anchor-profile {
                                type leafref {
                                    path "../../../../../../../ipsec/trust-anchor-profile/name";
                                }
                                description "Trust anchor profile.";
                            }

                            container status-verify {
                                description "Enter the status-verify context";

                                leaf default-result {
                                    type enumeration {
                                        enum "revoked"                      { value 0; }
                                        enum "good"                         { value 1; }
                                    }
                                    default "revoked";
                                    description "The default result of Certificate Status Verification (CSV).";
                                }

                                leaf primary {
                                    type types-ipsec:cert-revocation-status;
                                    default "crl";
                                    description "The primary method used to verify the peer certificate's revocation status.";
                                }

                                leaf secondary {
                                    type types-ipsec:cert-revocation-status-with-none;
                                    default "none";
                                    description "The secondary method used to verify the peer certificate's revocation status.";
                                }

                            } // container status-verify

                        } // container cert

                        container client-db {
                            presence "IPsec client database.";
                            description "Enter the client-db context";

                            leaf name {
                                type leafref {
                                    path "../../../../../../../ipsec/client-db/name";
                                }
                                mandatory true;
                                description "IPsec client database name.";
                            }

                            leaf fallback {
                                type boolean;
                                default "true";
                                description "Fall back to the tunnel authentication and creation attribute as if client-db is not configured when IPsec database client matching has failed.";
                            }

                        } // container client-db

                        container default-secure-service {
                            presence "The default security service used by this IPsec gateway.";
                            description "Enter the default-secure-service context";

                            leaf service-name {
                                type types-services:service-name;
                                sros-ext:auto-restart-to-modify;
                                description "Name of the default security service used by this IPsec gateway";
                            }

                            leaf interface {
                                type types-sros:interface-name;
                                sros-ext:auto-restart-to-modify;
                                description "The name of the default interface used by this IPsec gateway.";
                            }

                        } // container default-secure-service

                        container local {
                            description "Enter the local context";

                            leaf gateway-address {
                                type types-sros:ip-address;
                                sros-ext:auto-restart-to-modify;
                                description "The IPsec gateway address.";
                            }

                            container address-assignment {
                                presence "Local address assignment information.";
                                description "Enter the address-assignment context";

                                leaf admin-state {
                                    type types-sros:admin-state;
                                    default "disable";
                                    description "Administrative state of local address assignments";
                                }

                                leaf-list apply-groups {
                                    type leafref {
                                        path "../../../../../../../../groups/group/name";
                                    }
                                    max-elements 8;
                                    ordered-by user;
                                    description "Apply a configuration group at this level";
                                }

                                container ipv4 {
                                    presence "Local DHCPv4 server and pool information.";
                                    description "Enter the ipv4 context";

                                    leaf router-instance {
                                        type types-sros:router-instance-base-vprn-loose;
                                        mandatory true;
                                        description "Router instance hosting the DHCPv4 connection.";
                                    }

                                    leaf dhcp-server {
                                        type types-sros:named-item;
                                        mandatory true;
                                        description "Local DHCPv4 server name";
                                    }

                                    leaf pool {
                                        type types-sros:named-item;
                                        mandatory true;
                                        description "Name of the pool defined in the specified DHCPv4 server";
                                    }

                                    leaf secondary-pool {
                                        type types-sros:named-item;
                                        description "Name of the secondary pool defined in the DHCPv4 server";
                                    }

                                } // container ipv4

                                container ipv6 {
                                    presence "DHCPv6 server and pool information.";
                                    description "Enter the ipv6 context";

                                    leaf router-instance {
                                        type types-sros:router-instance-base-vprn-loose;
                                        mandatory true;
                                        description "Router instance hosting the DHCPv6 connection.";
                                    }

                                    leaf dhcp-server {
                                        type types-sros:named-item;
                                        mandatory true;
                                        description "Local DHCPv6 server name";
                                    }

                                    leaf pool {
                                        type types-sros:named-item;
                                        mandatory true;
                                        description "Name of the secondary pool defined in the DHCPv6 server";
                                    }

                                } // container ipv6

                            } // container address-assignment

                            container id {
                                description "Enter the id context";

                                choice id {
                                    default "auto";
                                    case auto {

                                        leaf auto {
                                            type empty;
                                            sros-ext:auto-restart-to-modify;
                                            description "System picks a local ID automatically based on auth-method configured in ike-policy.";
                                        }

                                    }
                                    case ipv4 {

                                        leaf ipv4 {
                                            type types-sros:ipv4-unicast-address;
                                            sros-ext:auto-restart-to-modify;
                                            description "The IPv4 Local ID.";
                                        }

                                    }
                                    case ipv6 {

                                        leaf ipv6 {
                                            type types-sros:ip-address;
                                            sros-ext:auto-restart-to-modify;
                                            description "The IPv6 Local ID.";
                                        }

                                    }
                                    case fqdn {

                                        leaf fqdn {
                                            type types-sros:fully-qualified-domain-name;
                                            sros-ext:auto-restart-to-modify;
                                            description "The Fully Qualified Domain Name (FQDN) Local ID.";
                                        }

                                    }
                                }
                            } // container id

                        } // container local

                        container radius {
                            description "Enter the radius context";

                            leaf accounting-policy {
                                type leafref {
                                    path "../../../../../../../ipsec/radius/accounting-policy/name";
                                }
                                description "RADIUS accounting policy.";
                            }

                            leaf authentication-policy {
                                type leafref {
                                    path "../../../../../../../ipsec/radius/authentication-policy/name";
                                }
                                description "RADIUS authentication policy.";
                            }

                        } // container radius

                        container max-history-key-records {
                            description "Enter the max-history-key-records context";

                            leaf ike {
                                type uint32 {
                                    range "1..3";
                                }
                                description "The maximum number of historical IKE keys which can be recorded by the system.";
                            }

                            leaf esp {
                                type uint32 {
                                    range "1..48";
                                }
                                description "The maximum number of historical ESP keys which can be recorded by the system.";
                            }

                        } // container max-history-key-records

                    } // list ipsec-gateway

                    container static-host {
                        description "Enter the static-host context";

                        list ipv4 {
                            key "ip mac";
                            description "Enter the ipv4 list instance";

                            leaf ip {
                                type types-sros:ipv4-address;
                                description "IP address";
                            }

                            leaf mac {
                                type types-sros:mac-unicast-address;
                                description "MAC address";
                            }

                            leaf admin-state {
                                type types-sros:admin-state;
                                default "disable";
                                description "Administrative state of the static host";
                            }

                            leaf sub-profile {
                                type leafref {
                                    path "../../../../../../../subscriber-mgmt/sub-profile/name";
                                }
                                description "Sub-profile name";
                            }

                            leaf sla-profile {
                                type leafref {
                                    path "../../../../../../../subscriber-mgmt/sla-profile/name";
                                }
                                description "SLA profile name";
                            }

                            leaf ancp-string {
                                type types-submgt:ancp-string;
                                description "ANCP string";
                            }

                            leaf int-dest-id {
                                type types-submgt:int-dest-id;
                                description "Intermediate destination ID";
                            }

                            leaf-list apply-groups {
                                type leafref {
                                    path "../../../../../../../groups/group/name";
                                }
                                max-elements 8;
                                ordered-by user;
                                description "Apply a configuration group at this level";
                            }

                            container subscriber-id {
                                description "Enter the subscriber-id context";

                                choice subscriber-id {
                                    case string {

                                        leaf string {
                                            type types-submgt:subscriber-id;
                                            description "Subscriber identification";
                                        }

                                    }
                                    case use-sap-id {

                                        leaf use-sap-id {
                                            type empty;
                                            description "Use the SAP id as subscriber ID";
                                        }

                                    }
                                }
                            } // container subscriber-id

                        } // list ipv4

                    } // container static-host

                } // list sap

                list vpls {
                    when "../tunnel = 'false'";
                    key "vpls-name";
                    max-elements 1;
                    description "Enter the vpls list instance";

                    leaf vpls-name {
                        type types-sros:named-item-64;
                        description "VPLS service";
                    }

                    leaf-list apply-groups {
                        type leafref {
                            path "../../../../../groups/group/name";
                        }
                        max-elements 8;
                        ordered-by user;
                        description "Apply a configuration group at this level";
                    }

                    container evpn {
                        description "Enter the evpn context";

                        container arp {
                            description "Enter the arp context";

                            leaf learn-dynamic {
                                type boolean;
                                default "true";
                                description "Enable/disable dynamic entries learning.";
                            }

                            leaf flood-garp-and-unknown-req {
                                type boolean;
                                default "true";
                                description "Enable/disable flooding GARP and unknown requests.";
                            }

                            list advertise {
                                key "route-type";
                                description "Enter the advertise list instance";

                                leaf route-type {
                                    type enumeration {
                                        enum "static"                       { value 1; }
                                        enum "dynamic"                      { value 2; }
                                    }
                                    description "Type of ARP or ND entries that generate host routes";
                                }

                                leaf route-tag {
                                    type uint32 {
                                        range "0..255";
                                    }
                                    sros-ext:immutable;
                                    description "Configure tag to use with the host route generated from an ARP or ND entry.";
                                }

                                leaf-list apply-groups {
                                    type leafref {
                                        path "../../../../../../../../groups/group/name";
                                    }
                                    max-elements 8;
                                    ordered-by user;
                                    description "Apply a configuration group at this level";
                                }

                            } // list advertise

                        } // container arp

                    } // container evpn

                    container egress {
                        description "Enter the egress context";

                        leaf reclassify-using-qos {
                            type leafref {
                                path "../../../../../../qos/sap-egress/sap-egress-policy-name";
                            }
                            description "Egress QoS policy";
                        }

                        container routed-override-filter {
                            description "Enter the routed-override-filter context";

                            leaf ip {
                                type leafref {
                                    path "../../../../../../../filter/ip-filter/filter-name";
                                }
                                description "IPv4 filter policy name";
                            }

                            leaf ipv6 {
                                type leafref {
                                    path "../../../../../../../filter/ipv6-filter/filter-name";
                                }
                                description "IPv6 filter policy name";
                            }

                        } // container routed-override-filter

                    } // container egress

                    container ingress {
                        description "Enter the ingress context";

                        container routed-override-filter {
                            description "Enter the routed-override-filter context";

                            leaf ip {
                                type leafref {
                                    path "../../../../../../../filter/ip-filter/filter-name";
                                }
                                description "IPv4 filter policy name";
                            }

                            leaf ipv6 {
                                type leafref {
                                    path "../../../../../../../filter/ipv6-filter/filter-name";
                                }
                                description "IPv6 filter policy name";
                            }

                        } // container routed-override-filter

                    } // container ingress

                } // list vpls

                container hold-time {
                    when "../tunnel = 'false' or ../loopback = 'true'";
                    description "Enter the hold-time context";

                    container ipv4 {
                        description "Enter the ipv4 context";

                        container up {
                            description "Enter the up context";

                            leaf seconds {
                                type types-router:hold-time-seconds;
                                units "seconds";
                                description "Up hold time for the IP interface";
                            }

                        } // container up

                        container down {
                            description "Enter the down context";

                            leaf seconds {
                                type types-router:hold-time-seconds;
                                units "seconds";
                                description "Down hold time for the IP interface";
                            }

                            leaf init-only {
                                type boolean;
                                default "false";
                                description "Apply delay only at interface configuration or reboot";
                            }

                        } // container down

                    } // container ipv4

                    container ipv6 {
                        description "Enter the ipv6 context";

                        container up {
                            description "Enter the up context";

                            leaf seconds {
                                type types-router:hold-time-seconds;
                                units "seconds";
                                description "Up hold time for the IP interface";
                            }

                        } // container up

                        container down {
                            description "Enter the down context";

                            leaf seconds {
                                type types-router:hold-time-seconds;
                                units "seconds";
                                description "Down hold time for the IP interface";
                            }

                            leaf init-only {
                                type boolean;
                                default "false";
                                description "Apply delay only at interface configuration or reboot";
                            }

                        } // container down

                    } // container ipv6

                } // container hold-time

                container ipv4 {
                    description "Enter the ipv4 context";

                    leaf tcp-mss {
                        type types-router:ipv4-tcp-mss-ext;
                        description "TCP maximum segment size for the interface";
                    }

                    leaf allow-directed-broadcasts {
                        type boolean;
                        default "false";
                        description "Forward directed broadcasts";
                    }

                    leaf local-dhcp-server {
                        when "../../tunnel = 'false'";
                        type leafref {
                            path "../../../../../router/dhcp-server/dhcpv4/name";
                        }
                        description "DHCP server for the interface";
                    }

                    leaf qos-route-lookup {
                        type types-router:qos-route-lookup;
                        description "QoS Route lookup";
                    }

                    leaf ip-helper-address {
                        type types-sros:ipv4-unicast-address;
                        description "Gateway address";
                    }

                    container icmp {
                        description "Enter the icmp context";

                        leaf mask-reply {
                            type boolean;
                            default "true";
                            description "Allow responses to ICMP mask requests";
                        }

                        container redirects {
                            description "Enter the redirects context";

                            leaf admin-state {
                                type types-sros:admin-state;
                                default "enable";
                                description "Administrative state of sending ICMP redirects";
                            }

                            leaf number {
                                type uint16 {
                                    range "10..1000";
                                }
                                default "100";
                                description "Maximum number of ICMP redirect messages to send";
                            }

                            leaf seconds {
                                type uint16 {
                                    range "1..60";
                                }
                                units "seconds";
                                default "10";
                                description "Time used to limit the number of ICMP redirect messages";
                            }

                        } // container redirects

                        container ttl-expired {
                            description "Enter the ttl-expired context";

                            leaf admin-state {
                                type types-sros:admin-state;
                                default "enable";
                                description "Administrative state of sending TTL expired messages";
                            }

                            leaf number {
                                type uint16 {
                                    range "10..2000";
                                }
                                default "100";
                                description "Maximum number of TTL-expired messages to send";
                            }

                            leaf seconds {
                                type uint16 {
                                    range "1..60";
                                }
                                units "seconds";
                                default "10";
                                description "Time used to limit the number of TTL-expired messages";
                            }

                        } // container ttl-expired

                        container unreachables {
                            description "Enter the unreachables context";

                            leaf admin-state {
                                type types-sros:admin-state;
                                default "enable";
                                description "Administrative state of sending unreachable messages";
                            }

                            leaf number {
                                type uint16 {
                                    range "10..2000";
                                }
                                default "100";
                                description "Maximum number of unreachable messages to send";
                            }

                            leaf seconds {
                                type uint16 {
                                    range "1..60";
                                }
                                units "seconds";
                                default "10";
                                description "Time to limit the number of ICMP unreachable messages";
                            }

                        } // container unreachables

                        container param-problem {
                            description "Enter the param-problem context";

                            leaf admin-state {
                                type types-sros:admin-state;
                                default "enable";
                                description "Administrative state of sent Parameter Problem messages";
                            }

                            leaf number {
                                type uint32 {
                                    range "10..1000";
                                }
                                default "100";
                                description "Maximum number of parameter problem messages to send";
                            }

                            leaf seconds {
                                type uint32 {
                                    range "1..60";
                                }
                                units "seconds";
                                default "10";
                                description "Time used to limit number of parameter problem messages";
                            }

                        } // container param-problem

                    } // container icmp

                    container unnumbered {
                        description "Enter the unnumbered context";

                        choice source {
                            case ip-address {

                                leaf ip-address {
                                    type types-sros:ipv4-unicast-address;
                                    description "IP address of the interface";
                                }

                            }
                            case ip-int-name {

                                leaf ip-int-name {
                                    type types-sros:interface-name;
                                    description "Name of the interface";
                                }

                            }
                            case ip-int-system {

                                leaf system {
                                    type empty;
                                    description "IP interface as an unnumbered interface";
                                }

                            }
                        }
                    } // container unnumbered

                    container urpf-check {
                        presence "Enable unicast RPF check on this interface.";
                        description "Enter the urpf-check context";

                        leaf ignore-default {
                            type boolean;
                            default "false";
                            description "Ignore default route when performing a uRPF check";
                        }

                        leaf mode {
                            type types-router:urpf-check-mode;
                            default "strict";
                            description "Unicast RPF check mode";
                        }

                    } // container urpf-check

                    container bfd {
                        description "Enter the bfd context";

                        leaf admin-state {
                            type types-sros:admin-state;
                            default "disable";
                            description "Administrative state of BFD sessions";
                        }

                        leaf transmit-interval {
                            type uint32 {
                                range "10..100000";
                            }
                            units "milliseconds";
                            default "100";
                            description "BFD transmit interval over this interface";
                        }

                        leaf receive {
                            type uint32 {
                                range "10..100000";
                            }
                            units "milliseconds";
                            default "100";
                            description "BFD receive interval over this interface";
                        }

                        leaf multiplier {
                            type uint32 {
                                range "3..20";
                            }
                            default "3";
                            description "Number of consecutive BFD messages missed from the peer";
                        }

                        leaf echo-receive {
                            type uint32 {
                                range "100..100000";
                            }
                            units "milliseconds";
                            description "Minimum echo interval over this interface";
                        }

                        leaf type {
                            type enumeration {
                                enum "cpm-np"                       { value 1; }
                                enum "auto"                         { value 2; }
                                enum "fp"                           { value 3; }
                            }
                            default "auto";
                            description "Local termination point for BFD session";
                        }

                    } // container bfd

                    container primary {
                        presence "Primary IPv4 address for this ies interface.";
                        description "Enter the primary context";

                        leaf address {
                            type types-sros:ipv4-unicast-address;
                            mandatory true;
                            description "Primary IPv4 address assigned to the interface";
                        }

                        leaf prefix-length {
                            type uint32 {
                                range "0..32";
                            }
                            mandatory true;
                            description "IPv4 address prefix length";
                        }

                        leaf broadcast {
                            type types-services:broadcast-address-format;
                            default "host-ones";
                            description "Broadcast address format";
                        }

                        leaf track-srrp {
                            type uint32 {
                                range "1..4294967295";
                            }
                            description "SRRP instance whose state is tracked on this IP address";
                        }

                        leaf-list apply-groups {
                            type leafref {
                                path "../../../../../../groups/group/name";
                            }
                            max-elements 8;
                            ordered-by user;
                            description "Apply a configuration group at this level";
                        }

                    } // container primary

                    list secondary {
                        key "address";
                        description "Enter the secondary list instance";

                        leaf address {
                            type types-sros:ipv4-unicast-address;
                            description "Secondary IPv4 address assigned to the interface";
                        }

                        leaf prefix-length {
                            type uint32 {
                                range "0..32";
                            }
                            mandatory true;
                            description "IPv4 address prefix length";
                        }

                        leaf igp-inhibit {
                            type boolean;
                            default "false";
                            description "Secondary IP address that is not recognized as local interface by the running IGP";
                        }

                        leaf broadcast {
                            type types-services:broadcast-address-format;
                            default "host-ones";
                            description "Broadcast address format";
                        }

                        leaf track-srrp {
                            type uint32 {
                                range "1..4294967295";
                            }
                            description "SRRP instance whose state is tracked on this IP address";
                        }

                        leaf-list apply-groups {
                            type leafref {
                                path "../../../../../../groups/group/name";
                            }
                            max-elements 8;
                            ordered-by user;
                            description "Apply a configuration group at this level";
                        }

                    } // list secondary

                    container addresses {
                        description "Enter the addresses context";

                        list address {
                            key "ipv4-address";
                            description "Enter the address list instance";

                            leaf ipv4-address {
                                type types-sros:ipv4-unicast-address;
                                description "IPv4 address for the interface";
                            }

                            leaf prefix-length {
                                type uint32 {
                                    range "0..32";
                                }
                                mandatory true;
                                description "IPv4 address prefix length";
                            }

                            leaf-list apply-groups {
                                type leafref {
                                    path "../../../../../../../groups/group/name";
                                }
                                max-elements 8;
                                ordered-by user;
                                description "Apply a configuration group at this level";
                            }

                        } // list address

                    } // container addresses

                    container neighbor-discovery {
                        when "../../tunnel = 'false'";
                        description "Enter the neighbor-discovery context";

                        leaf timeout {
                            type uint32 {
                                range "0..65535";
                            }
                            units "seconds";
                            default "14400";
                            description "Timeout for an ARP entry learned on the interface";
                        }

                        leaf retry-timer {
                            type uint32 {
                                range "1..300";
                            }
                            units "deciseconds";
                            default "50";
                            description "ARP retry interval";
                        }

                        leaf learn-unsolicited {
                            type boolean;
                            default "false";
                            description "Learn new entries from any received NA message";
                        }

                        leaf proactive-refresh {
                            type boolean;
                            default "false";
                            description "Send a single refresh message with no retries 30 seconds prior to entry timeout";
                        }

                        leaf populate {
                            type boolean;
                            default "false";
                            description "Allow static and dynamic hosts to be populated in system ARP cache";
                        }

                        leaf populate-host {
                            status deprecated;
                            type boolean;
                            default "false";
                            description "Allow addition or deletion of host routes in route table derived from ARP entries in ARP cache";
                        }

                        leaf route-tag {
                            status deprecated;
                            type types-router:route-tag;
                            description "ARP route tag";
                        }

                        leaf local-proxy-arp {
                            type boolean;
                            default "false";
                            description "Enable local proxy ARP on interface";
                        }

                        leaf remote-proxy-arp {
                            type boolean;
                            default "false";
                            description "Enable remote proxy ARP on interface";
                        }

                        leaf-list proxy-arp-policy {
                            type leafref {
                                path "../../../../../../policy-options/policy-statement/name";
                            }
                            max-elements 5;
                            ordered-by user;
                            description "Proxy ARP policy name";
                        }

                        container host-route {
                            description "Enter the host-route context";

                            list populate {
                                key "route-type";
                                description "Enter the populate list instance";

                                leaf route-type {
                                    type enumeration {
                                        enum "static"                       { value 1; }
                                        enum "dynamic"                      { value 2; }
                                        enum "evpn"                         { value 3; }
                                    }
                                    description "Type of ARP or ND entries that generate host routes";
                                }

                                leaf route-tag {
                                    type uint32 {
                                        range "1..255";
                                    }
                                    sros-ext:immutable;
                                    description "Route tag added to route table for ARP/ND host routes";
                                }

                                leaf-list apply-groups {
                                    type leafref {
                                        path "../../../../../../../../groups/group/name";
                                    }
                                    max-elements 8;
                                    ordered-by user;
                                    description "Apply a configuration group at this level";
                                }

                            } // list populate

                        } // container host-route

                        container limit {
                            description "Enter the limit context";

                            leaf max-entries {
                                type types-router:ipv4-neighbor-limit;
                                description "Maximum number of entries that can be learned";
                            }

                            leaf log-only {
                                type boolean;
                                default "false";
                                description "Apply the limit to log entries only";
                            }

                            leaf threshold {
                                type uint32 {
                                    range "1..100";
                                }
                                units "percent";
                                default "90";
                                description "Threshold value that triggers a warning message";
                            }

                        } // container limit

                        container static-neighbor-unnumbered {
                            presence "IP-to-MAC address mapping on the unnumbered interface.";
                            description "Enter the static-neighbor-unnumbered context";

                            leaf mac-address {
                                type yang:mac-address;
                                mandatory true;
                                description "Media-dependent physical address";
                            }

                        } // container static-neighbor-unnumbered

                        list static-neighbor {
                            key "ipv4-address";
                            description "Enter the static-neighbor list instance";

                            leaf ipv4-address {
                                type types-sros:ipv4-address;
                                description "IPv4 address corresponding to the media-dependent physical address";
                            }

                            leaf mac-address {
                                type yang:mac-address;
                                mandatory true;
                                description "Media-dependent physical address";
                            }

                            leaf-list apply-groups {
                                type leafref {
                                    path "../../../../../../../groups/group/name";
                                }
                                max-elements 8;
                                ordered-by user;
                                description "Apply a configuration group at this level";
                            }

                        } // list static-neighbor

                    } // container neighbor-discovery

                    container dhcp {
                        description "Enter the dhcp context";

                        leaf admin-state {
                            type types-sros:admin-state;
                            default "disable";
                            description "Administrative state of DHCP";
                        }

                        leaf description {
                            type types-sros:description;
                            description "Text description";
                        }

                        leaf python-policy {
                            when "../../../tunnel = 'false'";
                            type leafref {
                                path "../../../../../../python/python-policy/name";
                            }
                            description "Python policy";
                        }

                        leaf-list server {
                            type types-sros:ipv4-unicast-address;
                            max-elements 8;
                            ordered-by user;
                            description "IP addresses for DHCP server requests";
                        }

                        leaf trusted {
                            type boolean;
                            default "false";
                            description "Relay untrusted packets";
                        }

                        leaf gi-address {
                            type types-sros:ipv4-unicast-address;
                            description "Gateway interface address for the DHCP relay";
                        }

                        leaf src-ip-addr {
                            type enumeration {
                                enum "auto"                         { value 0; }
                                enum "gi-address"                   { value 1; }
                            }
                            default "auto";
                            description "Type of source address to use for DHCP relay";
                        }

                        leaf relay-plain-bootp {
                            when "../../../tunnel = 'false'";
                            type boolean;
                            default "false";
                            description "Enable/disable relaying of plain BOOTP packets.";
                        }

                        leaf use-arp {
                            when "../../../tunnel = 'false'";
                            type boolean;
                            default "false";
                            description "Enable/disable the use of ARP to determine the destination Hw address.";
                        }

                        leaf-list apply-groups {
                            type leafref {
                                path "../../../../../../groups/group/name";
                            }
                            max-elements 8;
                            ordered-by user;
                            description "Apply a configuration group at this level";
                        }

                        container proxy-server {
                            description "Enter the proxy-server context";

                            leaf admin-state {
                                type types-sros:admin-state;
                                default "disable";
                                description "Administrative state of the DHCP proxy server";
                            }

                            leaf emulated-server {
                                type types-sros:ipv4-unicast-address;
                                description "The address used as source and siaddr when emulating a DHCP server.";
                            }

                            container lease-time {
                                description "Enter the lease-time context";

                                leaf value {
                                    type types-sros:time-duration {
                                        range "300..315446399";
                                    }
                                    units "seconds";
                                    description "DHCP lease time";
                                }

                                leaf radius-override {
                                    type boolean;
                                    default "false";
                                    description "Use lease time information provided by RADIUS server";
                                }

                            } // container lease-time

                        } // container proxy-server

                        container option-82 {
                            description "Enter the option-82 context";

                            leaf action {
                                type enumeration {
                                    enum "replace"                      { value 1; }
                                    enum "drop"                         { value 2; }
                                    enum "keep"                         { value 3; }
                                }
                                default "keep";
                                description "Action to take with received DHCP Option 82";
                            }

                            container circuit-id {
                                description "Enter the circuit-id context";

                                choice circuit-id {
                                    default "ascii-tuple";
                                    case none {

                                        leaf none {
                                            type empty;
                                            description "Do not include the circuit-id.";
                                        }

                                    }
                                    case ifindex {

                                        leaf ifindex {
                                            type empty;
                                            description "Use the interface index for the Circuit ID";
                                        }

                                    }
                                    case ascii-tuple {

                                        leaf ascii-tuple {
                                            type empty;
                                            description "Use the ASCII-encoded tuple for the Circuit ID";
                                        }

                                    }
                                    case sap-id {

                                        leaf sap-id {
                                            type empty;
                                            description "Use SAP ID in the option.";
                                        }

                                    }
                                    case vlan-ascii-tuple {

                                        leaf vlan-ascii-tuple {
                                            type empty;
                                            description "Include the VLAN ID and dot1p bits in the ASCII tuple";
                                        }

                                    }
                                }
                            } // container circuit-id

                            container remote-id {
                                description "Enter the remote-id context";

                                choice remote-id {
                                    default "none";
                                    case none {

                                        leaf none {
                                            type empty;
                                            description "Do not include the Remote ID";
                                        }

                                    }
                                    case mac {

                                        leaf mac {
                                            type empty;
                                            description "Use the MAC address for the Remote ID";
                                        }

                                    }
                                    case ascii-string {

                                        leaf ascii-string {
                                            type types-sros:string-not-all-spaces {
                                                length "1..32";
                                            }
                                            description "User-defined ASCII string for the Remote ID";
                                        }

                                    }
                                }
                            } // container remote-id

                            container vendor-specific-option {
                                description "Enter the vendor-specific-option context";

                                leaf system-id {
                                    type boolean;
                                    default "false";
                                    description "Send the system ID in the Vendor Specific Option";
                                }

                                leaf client-mac-address {
                                    type boolean;
                                    default "false";
                                    description "Send the MAC address in the Vendor Specific Option";
                                }

                                leaf pool-name {
                                    type boolean;
                                    default "false";
                                    description "Send the pool name in the Vendor Specific Option";
                                }

                                leaf service-id {
                                    type boolean;
                                    default "false";
                                    description "Send the service ID in the Vendor Specific Option";
                                }

                                leaf sap-id {
                                    type boolean;
                                    default "false";
                                    description "Send the SAP ID in the Nokia vendor specific suboption.";
                                }

                                leaf string {
                                    type types-sros:string-not-all-spaces {
                                        length "1..32";
                                    }
                                    description "User-defined ASCII string for Vendor Specific Option";
                                }

                            } // container vendor-specific-option

                        } // container option-82

                        container lease-populate {
                            description "Enter the lease-populate context";

                            leaf max-leases {
                                type uint32 {
                                    range "0..511999";
                                }
                                default "0";
                                description "The maximum number of DHCPv4 leases.";
                            }

                        } // container lease-populate

                        container relay-proxy {
                            presence
                                "Enable/disable relaying of unicast DHCP client messages and optional DHCP
                                 server ip address hiding.";
                            description "Enter the relay-proxy context";

                            leaf release-update-src-ip {
                                type boolean;
                                default "false";
                                description "Specify whether or not to relay release messages.";
                            }

                            leaf siaddr-override {
                                type types-sros:ipv4-unicast-address;
                                description "Specify the IP address to use.";
                            }

                        } // container relay-proxy

                    } // container dhcp

                    list vrrp {
                        key "virtual-router-id";
                        description "Enter the vrrp list instance";

                        leaf virtual-router-id {
                            type int32 {
                                range "1..255";
                            }
                            description "Virtual Router Identifier (VRID) for the VRRP virtual router instance";
                        }

                        leaf authentication-key {
                            type types-sros:encrypted-leaf {
                                length "1..38";
                            }
                            description "Password for simple text authentication";
                        }

                        leaf-list backup {
                            type types-sros:ipv4-unicast-address;
                            max-elements 16;
                            description "Virtual router IP addresses for the interface";
                        }

                        leaf message-interval {
                            type uint32 {
                                range "1..2559";
                            }
                            units "deciseconds";
                            default "10";
                            description "Interval for sending VRRP Advertisement messages";
                        }

                        leaf owner {
                            type boolean;
                            sros-ext:immutable;
                            default "false";
                            description "Designate virtual router instance as owning the virtual router IP addresses";
                        }

                        leaf passive {
                            type boolean;
                            sros-ext:immutable;
                            default "false";
                            description "Suppress the transmission and reception of VRRP advertisement messages";
                        }

                        leaf init-delay {
                            type uint32 {
                                range "1..65535";
                            }
                            units "seconds";
                            description "VRRP initialization delay timer";
                        }

                        leaf mac {
                            type types-sros:mac-unicast-address;
                            description "MAC address used by virtual router instance overriding the VRRP default derived from the VRID";
                        }

                        leaf priority {
                            type uint32 {
                                range "1..255";
                            }
                            description "Base priority for the VRRP";
                        }

                        leaf admin-state {
                            type types-sros:admin-state;
                            default "enable";
                            description "Administrative state of VRRP";
                        }

                        leaf master-int-inherit {
                            type boolean;
                            default "false";
                            description "Allow the master instance to dictate the master down timer";
                        }

                        leaf ping-reply {
                            type boolean;
                            default "false";
                            description "Allow non-owner master to reply to ICMP echo requests";
                        }

                        leaf policy {
                            type leafref {
                                path "../../../../../../vrrp/policy/policy-id";
                            }
                            description "VRRP priority control policy associated with the virtual router instance";
                        }

                        leaf preempt {
                            type boolean;
                            default "true";
                            description "Allow the VRRP to override an existing non-owner master";
                        }

                        leaf telnet-reply {
                            type boolean;
                            default "false";
                            description "Allow non-owner master to reply to Telnet requests";
                        }

                        leaf traceroute-reply {
                            type boolean;
                            default "false";
                            description "Allow non-owner master to reply to traceroute requests";
                        }

                        leaf standby-forwarding {
                            type boolean;
                            default "false";
                            description "Allow the forwarding of packets by a standby router";
                        }

                        leaf ssh-reply {
                            type boolean;
                            default "false";
                            description "Allow non-owner master to reply to SSH requests";
                        }

                        leaf oper-group {
                            type leafref {
                                path "../../../../../oper-group/name";
                            }
                            description "Operational group name associated with VRRP";
                        }

                        leaf-list apply-groups {
                            type leafref {
                                path "../../../../../../groups/group/name";
                            }
                            max-elements 8;
                            ordered-by user;
                            description "Apply a configuration group at this level";
                        }

                        container bfd-liveness {
                            presence "Enable bfd on this vrrp.";
                            description "Enter the bfd-liveness context";

                            leaf dest-ip {
                                type types-sros:ipv4-address;
                                sros-ext:immutable;
                                mandatory true;
                                description "Destination IP address to be used for BFD session";
                            }

                            leaf service-name {
                                type types-services:service-name;
                                sros-ext:immutable;
                                description "Service name of interface running BFD";
                            }

                            leaf interface-name {
                                type types-sros:interface-name;
                                sros-ext:immutable;
                                mandatory true;
                                description "Name of interface running BFD";
                            }

                            leaf-list apply-groups {
                                type leafref {
                                    path "../../../../../../../groups/group/name";
                                }
                                max-elements 8;
                                ordered-by user;
                                description "Apply a configuration group at this level";
                            }

                        } // container bfd-liveness

                    } // list vrrp

                } // container ipv4

                container ipv6 {
                    presence "Enables/configures IPv6 related objects for an interface.";
                    description "Enter the ipv6 context";

                    leaf qos-route-lookup {
                        type types-router:qos-route-lookup;
                        description "QoS Route lookup";
                    }

                    leaf forward-ipv4-packets {
                        type boolean;
                        default "false";
                        description "Forward unencapsulated IPv4 packets";
                    }

                    leaf tcp-mss {
                        type types-router:ipv6-tcp-mss-ext;
                        description "TCP maximum segment size for the interface";
                    }

                    leaf duplicate-address-detection {
                        type boolean;
                        default "true";
                        description "Enable/disable Duplicate Address Detection";
                    }

                    leaf local-dhcp-server {
                        when "../../tunnel = 'false'";
                        type leafref {
                            path "../../../../../router/dhcp-server/dhcpv6/name";
                        }
                        description "DHCP server for the interface";
                    }

                    container urpf-check {
                        presence "Enable uRPF information.";
                        description "Enter the urpf-check context";

                        leaf ignore-default {
                            type boolean;
                            default "false";
                            description "Ignore default route when performing a uRPF check";
                        }

                        leaf mode {
                            type types-router:urpf-check-mode;
                            default "strict";
                            description "Unicast RPF check mode";
                        }

                    } // container urpf-check

                    container icmp6 {
                        description "Enter the icmp6 context";

                        container packet-too-big {
                            description "Enter the packet-too-big context";

                            leaf admin-state {
                                type types-sros:admin-state;
                                default "enable";
                                description "Administrative state of packet-too-big messages";
                            }

                            leaf number {
                                type uint16 {
                                    range "10..1000";
                                }
                                default "100";
                                description "Number of packet-too-big messages";
                            }

                            leaf seconds {
                                type uint16 {
                                    range "1..60";
                                }
                                default "10";
                                description "Time to limit packet-too-big messages";
                            }

                        } // container packet-too-big

                        container param-problem {
                            description "Enter the param-problem context";

                            leaf admin-state {
                                type types-sros:admin-state;
                                default "enable";
                                description "Administrative state of param-problem messages";
                            }

                            leaf number {
                                type uint16 {
                                    range "10..1000";
                                }
                                default "100";
                                description "Number of parameter-problem messages";
                            }

                            leaf seconds {
                                type uint16 {
                                    range "1..60";
                                }
                                default "10";
                                description "Time to limit parameter problem messages";
                            }

                        } // container param-problem

                        container redirects {
                            description "Enter the redirects context";

                            leaf admin-state {
                                type types-sros:admin-state;
                                default "enable";
                                description "Administrative state of the redirect messages";
                            }

                            leaf number {
                                type uint16 {
                                    range "10..1000";
                                }
                                default "100";
                                description "Number of redirect messages";
                            }

                            leaf seconds {
                                type uint16 {
                                    range "1..60";
                                }
                                default "10";
                                description "Time to limit redirect messages";
                            }

                        } // container redirects

                        container time-exceeded {
                            description "Enter the time-exceeded context";

                            leaf admin-state {
                                type types-sros:admin-state;
                                default "enable";
                                description "Administrative state of the time-exceeded messages";
                            }

                            leaf number {
                                type uint16 {
                                    range "10..2000";
                                }
                                default "100";
                                description "Number of time-exceeded messages";
                            }

                            leaf seconds {
                                type uint16 {
                                    range "1..60";
                                }
                                default "10";
                                description "Time to limit time-exceeded messages";
                            }

                        } // container time-exceeded

                        container unreachables {
                            description "Enter the unreachables context";

                            leaf admin-state {
                                type types-sros:admin-state;
                                default "enable";
                                description "Administrative state of the unreachable messages";
                            }

                            leaf number {
                                type uint16 {
                                    range "10..2000";
                                }
                                default "100";
                                description "Number of unreachable messages";
                            }

                            leaf seconds {
                                type uint16 {
                                    range "1..60";
                                }
                                default "10";
                                description "Time to limit unreachable messages";
                            }

                        } // container unreachables

                    } // container icmp6

                    container link-local-address {
                        description "Enter the link-local-address context";

                        leaf address {
                            type types-sros:ipv6-address;
                            description "Link-local IPv6 address of this router interface";
                        }

                        leaf duplicate-address-detection {
                            type boolean;
                            default "true";
                            description "Enable/disable Duplicate Address Detection.";
                        }

                    } // container link-local-address

                    container bfd {
                        description "Enter the bfd context";

                        leaf admin-state {
                            type types-sros:admin-state;
                            default "disable";
                            description "Administrative state of BFD sessions";
                        }

                        leaf transmit-interval {
                            type uint32 {
                                range "10..100000";
                            }
                            units "milliseconds";
                            default "100";
                            description "BFD transmit interval over this interface";
                        }

                        leaf receive {
                            type uint32 {
                                range "10..100000";
                            }
                            units "milliseconds";
                            default "100";
                            description "BFD receive interval over this interface";
                        }

                        leaf multiplier {
                            type uint32 {
                                range "3..20";
                            }
                            default "3";
                            description "Number of consecutive BFD messages missed from the peer";
                        }

                        leaf echo-receive {
                            type uint32 {
                                range "100..100000";
                            }
                            units "milliseconds";
                            description "Minimum echo interval over this interface";
                        }

                        leaf type {
                            type enumeration {
                                enum "cpm-np"                       { value 1; }
                                enum "auto"                         { value 2; }
                                enum "fp"                           { value 3; }
                            }
                            default "auto";
                            description "Local termination point for BFD session";
                        }

                    } // container bfd

                    list address {
                        key "ipv6-address";
                        description "Enter the address list instance";

                        leaf ipv6-address {
                            type types-sros:ipv6-address;
                            description "IPv6 address assigned to the interface";
                        }

                        leaf prefix-length {
                            type uint32 {
                                range "4..128";
                            }
                            mandatory true;
                            description "IPv6 address prefix length";
                        }

                        leaf eui-64 {
                            type boolean;
                            sros-ext:immutable;
                            default "false";
                            description "Form complete IPv6 address from supplied prefix and 64-bit interface identifier";
                        }

                        leaf duplicate-address-detection {
                            type boolean;
                            sros-ext:immutable;
                            default "true";
                            description "Enable/disable Duplicate Address Detection.";
                        }

                        leaf primary-preference {
                            type uint32 {
                                range "1..4294967295";
                            }
                            description "Index assigned to the IPv6 address of the interface";
                        }

                        leaf-list apply-groups {
                            type leafref {
                                path "../../../../../../groups/group/name";
                            }
                            max-elements 8;
                            ordered-by user;
                            description "Apply a configuration group at this level";
                        }

                    } // list address

                    container dhcp6 {
                        when "../../tunnel = 'false'";
                        description "Enter the dhcp6 context";

                        leaf-list apply-groups {
                            type leafref {
                                path "../../../../../../groups/group/name";
                            }
                            max-elements 8;
                            ordered-by user;
                            description "Apply a configuration group at this level";
                        }

                        container relay {
                            description "Enter the relay context";

                            leaf description {
                                type types-sros:description;
                                description "Text description";
                            }

                            leaf admin-state {
                                type types-sros:admin-state;
                                default "disable";
                                description "Administrative state of DHCPv6 relay";
                            }

                            leaf link-address {
                                type types-sros:ipv6-address;
                                description "Link address of the DHCPv6 relay messages";
                            }

                            leaf neighbor-resolution {
                                type boolean;
                                default "false";
                                description "Enable neighbor resolution via DHCPv6 relay";
                            }

                            leaf python-policy {
                                type leafref {
                                    path "../../../../../../../python/python-policy/name";
                                }
                                description "Python policy name";
                            }

                            leaf source-address {
                                type types-sros:ipv6-unicast-or-linklocal-address;
                                description "Source IPv6 address of the DHCPv6 relay messages";
                            }

                            leaf user-db {
                                type leafref {
                                    path "../../../../../../../subscriber-mgmt/local-user-db/name";
                                }
                                description "Local user database for authentication";
                            }

                            leaf-list server {
                                type types-sros:ipv6-address-with-zone;
                                max-elements 8;
                                ordered-by user;
                                description "DHCPv6 server to which the DHCPv6 requests are forwarded";
                            }

                            leaf-list apply-groups {
                                type leafref {
                                    path "../../../../../../../groups/group/name";
                                }
                                max-elements 8;
                                ordered-by user;
                                description "Apply a configuration group at this level";
                            }

                            container lease-populate {
                                description "Enter the lease-populate context";

                                leaf max-nbr-of-leases {
                                    type int32 {
                                        range "0..32767";
                                    }
                                    default "0";
                                    description "Maximum number of lease states allocated by the DHCPv6 relay function, allowed on interface";
                                }

                                container route-populate {
                                    description "Enter the route-populate context";

                                    leaf na {
                                        type boolean;
                                        default "false";
                                        description "Create route based on IA_NA prefix option in relay-reply message";
                                    }

                                    leaf ta {
                                        type boolean;
                                        default "false";
                                        description "Create route based on IA_TA prefix option in relay-reply message";
                                    }

                                    container pd {
                                        presence
                                            "Specifies whether or not route-population PD via DHCP6 Relay
                                             must be enabled on this interface.";
                                        description "Enter the pd context";

                                        leaf exclude {
                                            type boolean;
                                            default "false";
                                            description "Create back hole route based on prefix exclude option in relay-reply message";
                                        }

                                    } // container pd

                                } // container route-populate

                            } // container lease-populate

                            container option {
                                description "Enter the option context";

                                leaf remote-id {
                                    type boolean;
                                    default "false";
                                    description "Allow remote ID option to be sent in the DHCPv6 relay packet";
                                }

                                leaf-list apply-groups {
                                    type leafref {
                                        path "../../../../../../../../groups/group/name";
                                    }
                                    max-elements 8;
                                    ordered-by user;
                                    description "Apply a configuration group at this level";
                                }

                                container interface-id {
                                    description "Enter the interface-id context";

                                    choice interface-id {
                                        case ascii-tuple {

                                            leaf ascii-tuple {
                                                type empty;
                                                description "Use ASCII-encoded concatenated tuple in interface ID option in DHCPv6 relay packet";
                                            }

                                        }
                                        case sap-id {

                                            leaf sap-id {
                                                type empty;
                                                description "Use SAP ID in interface ID option in DHCPv6 relay packet";
                                            }

                                        }
                                        case if-index {

                                            leaf if-index {
                                                type empty;
                                                description "Use interface index in interface ID option in DHCPv6 relay packet";
                                            }

                                        }
                                        case string {

                                            leaf string {
                                                type types-sros:string-not-all-spaces {
                                                    length "1..80";
                                                }
                                                description "String for interface ID option in DHCPv6 relay packet";
                                            }

                                        }
                                    }
                                } // container interface-id

                            } // container option

                        } // container relay

                        container server {
                            description "Enter the server context";

                            leaf max-nbr-of-leases {
                                type int32 {
                                    range "0..8000";
                                }
                                default "8000";
                                description "DHCPv6 leases allowed";
                            }

                            leaf-list apply-groups {
                                type leafref {
                                    path "../../../../../../../groups/group/name";
                                }
                                max-elements 8;
                                ordered-by user;
                                description "Apply a configuration group at this level";
                            }

                            container prefix-delegation {
                                description "Enter the prefix-delegation context";

                                leaf admin-state {
                                    type types-sros:admin-state;
                                    default "disable";
                                    description "Administrative state of the prefix delegation";
                                }

                                list prefix {
                                    key "ipv6-prefix";
                                    description "Enter the prefix list instance";

                                    leaf ipv6-prefix {
                                        type types-sros:ipv6-prefix;
                                        description "IPv6 prefix to be delegated";
                                    }

                                    leaf preferred-lifetime {
                                        type types-services:ipv6-prefix-lifetime;
                                        units "seconds";
                                        default "604800";
                                        description "IPv6 prefix/mask preferred life time";
                                    }

                                    leaf valid-lifetime {
                                        type types-services:ipv6-prefix-lifetime;
                                        units "seconds";
                                        default "2592000";
                                        description "IPv6 prefix/mask valid life time";
                                    }

                                    leaf-list apply-groups {
                                        type leafref {
                                            path "../../../../../../../../../groups/group/name";
                                        }
                                        max-elements 8;
                                        ordered-by user;
                                        description "Apply a configuration group at this level";
                                    }

                                    container client-id {
                                        description "Enter the client-id context";

                                        leaf duid {
                                            type string {
                                                length "1..130";
                                            }
                                            description "Requesting router ID";
                                        }

                                        leaf iaid {
                                            type uint32 {
                                                range "1..4294967295";
                                            }
                                            description "IAID from the requesting router that matches to delegate the prefix";
                                        }

                                    } // container client-id

                                } // list prefix

                            } // container prefix-delegation

                        } // container server

                    } // container dhcp6

                    container neighbor-discovery {
                        when "../../tunnel = 'false'";
                        description "Enter the neighbor-discovery context";

                        leaf reachable-time {
                            type types-router:neighbor-discovery-reachable-time;
                            description "Timer for neighbor reachability detection";
                        }

                        leaf stale-time {
                            type types-router:neighbor-discovery-stale-time;
                            description "Time during which a neighbor discovery cache entry remains stale";
                        }

                        leaf learn-unsolicited {
                            type types-router:ipv6-address-type-selection;
                            description "Type of entries learned from unsolicited NA messages";
                        }

                        leaf proactive-refresh {
                            type types-router:ipv6-address-type-selection;
                            description "Neighbor entries to be refreshed proactively";
                        }

                        leaf populate-host {
                            status deprecated;
                            type boolean;
                            default "false";
                            description "Allow addition or deletion of host routes in route table derived from ARP entries in ARP cache";
                        }

                        leaf route-tag {
                            status deprecated;
                            type types-router:route-tag;
                            description "ARP route tag";
                        }

                        leaf local-proxy-nd {
                            type boolean;
                            default "false";
                            description "Enable neighbor discovery on interface";
                        }

                        leaf-list proxy-nd-policy {
                            type leafref {
                                path "../../../../../../policy-options/policy-statement/name";
                            }
                            max-elements 5;
                            ordered-by user;
                            description "Name of the proxy Neighbor Discovery policies for the interface";
                        }

                        container secure-nd {
                            description "Enter the secure-nd context";

                            leaf allow-unsecured-msgs {
                                type boolean;
                                default "true";
                                description "Accept unsecured messages";
                            }

                            leaf public-key-min-bits {
                                type uint32 {
                                    range "512..1024";
                                }
                                default "1024";
                                description "Minimum acceptable key length for public keys";
                            }

                            leaf security-parameter {
                                type uint32 {
                                    range "0..1";
                                }
                                default "1";
                                description "Security parameter in the generation of a cryptographical address";
                            }

                            leaf admin-state {
                                type types-sros:admin-state;
                                default "disable";
                                description "Administrative state of secure neighbor discovery";
                            }

                        } // container secure-nd

                        container limit {
                            description "Enter the limit context";

                            leaf max-entries {
                                type types-router:ipv6-neighbor-limit;
                                description "Maximum number of entries that can be learned on an IP interface";
                            }

                            leaf log-only {
                                type boolean;
                                default "false";
                                description "Log warning messages at threshold or when limit is exceeded, however entries are learned above limit";
                            }

                            leaf threshold {
                                type uint32 {
                                    range "1..100";
                                }
                                units "percent";
                                default "90";
                                description "Threshold value that triggers a warning message to be sent";
                            }

                        } // container limit

                        list static-neighbor {
                            key "ipv6-address";
                            description "Enter the static-neighbor list instance";

                            leaf ipv6-address {
                                type types-sros:ipv6-address;
                                description "IPv6 address corresponding to the media-dependent physical address";
                            }

                            leaf mac-address {
                                type yang:mac-address;
                                mandatory true;
                                description "Media-dependent physical address";
                            }

                            leaf-list apply-groups {
                                type leafref {
                                    path "../../../../../../../groups/group/name";
                                }
                                max-elements 8;
                                ordered-by user;
                                description "Apply a configuration group at this level";
                            }

                        } // list static-neighbor

                    } // container neighbor-discovery

                    list vrrp {
                        key "virtual-router-id";
                        max-elements 1;
                        description "Enter the vrrp list instance";

                        leaf virtual-router-id {
                            type int32 {
                                range "1..255";
                            }
                            description "Virtual Router Identifier (VRID) for the VRRP virtual router instance";
                        }

                        leaf-list backup {
                            type types-sros:ipv6-address;
                            max-elements 4;
                            description "Virtual router IP addresses for the interface";
                        }

                        leaf message-interval {
                            type uint32 {
                                range "10..4095";
                            }
                            units "centiseconds";
                            default "100";
                            description "Interval for sending VRRP Advertisement messages";
                        }

                        leaf owner {
                            type boolean;
                            sros-ext:immutable;
                            default "false";
                            description "Designate virtual router instance as owning the virtual router IP addresses";
                        }

                        leaf passive {
                            type boolean;
                            sros-ext:immutable;
                            default "false";
                            description "Suppress the transmission and reception of VRRP advertisement messages";
                        }

                        leaf init-delay {
                            type uint32 {
                                range "1..65535";
                            }
                            units "seconds";
                            description "VRRP initialization delay timer";
                        }

                        leaf mac {
                            type types-sros:mac-unicast-address;
                            description "MAC address used by virtual router instance overriding the VRRP default derived from the VRID";
                        }

                        leaf priority {
                            type uint32 {
                                range "1..255";
                            }
                            description "Base priority for the VRRP";
                        }

                        leaf admin-state {
                            type types-sros:admin-state;
                            default "enable";
                            description "Administrative state of VRRP";
                        }

                        leaf master-int-inherit {
                            type boolean;
                            default "true";
                            description "Allow the master instance to dictate the master down timer";
                        }

                        leaf ping-reply {
                            type boolean;
                            default "false";
                            description "Allow non-owner master to reply to ICMP echo requests";
                        }

                        leaf policy {
                            type leafref {
                                path "../../../../../../vrrp/policy/policy-id";
                            }
                            description "VRRP priority control policy associated with the virtual router instance";
                        }

                        leaf preempt {
                            type boolean;
                            default "true";
                            description "Allow the VRRP to override an existing non-owner master";
                        }

                        leaf telnet-reply {
                            type boolean;
                            default "false";
                            description "Allow non-owner master to reply to Telnet requests";
                        }

                        leaf traceroute-reply {
                            type boolean;
                            default "false";
                            description "Allow non-owner master to reply to traceroute requests";
                        }

                        leaf standby-forwarding {
                            type boolean;
                            default "false";
                            description "Allow the forwarding of packets by a standby router";
                        }

                        leaf oper-group {
                            type leafref {
                                path "../../../../../oper-group/name";
                            }
                            description "Operational group name associated with VRRP";
                        }

                        leaf-list apply-groups {
                            type leafref {
                                path "../../../../../../groups/group/name";
                            }
                            max-elements 8;
                            ordered-by user;
                            description "Apply a configuration group at this level";
                        }

                        container bfd-liveness {
                            presence "Enable bfd on this vrrp.";
                            description "Enter the bfd-liveness context";

                            leaf dest-ip {
                                type types-sros:ipv6-address;
                                sros-ext:immutable;
                                mandatory true;
                                description "ip-address.";
                            }

                            leaf service-name {
                                type types-services:service-name;
                                sros-ext:immutable;
                                description "Service name of interface running BFD";
                            }

                            leaf interface-name {
                                type types-sros:interface-name;
                                sros-ext:immutable;
                                mandatory true;
                                description "Name of interface running BFD";
                            }

                            leaf-list apply-groups {
                                type leafref {
                                    path "../../../../../../../groups/group/name";
                                }
                                max-elements 8;
                                ordered-by user;
                                description "Apply a configuration group at this level";
                            }

                        } // container bfd-liveness

                    } // list vrrp

                } // container ipv6

                container if-attribute {
                    description "Enter the if-attribute context";

                    leaf-list admin-group {
                        type leafref {
                            path "../../../../../routing-options/if-attribute/admin-group/group-name";
                        }
                        max-elements 32;
                        description "Names of the admin group memberships of the interface";
                    }

                    list srlg-group {
                        key "name";
                        description "Add a list entry for srlg-group";

                        leaf name {
                            type leafref {
                                path "../../../../../../routing-options/if-attribute/srlg-group/name";
                            }
                            description "Shared Risk Link Group (SRLG) name.";
                        }

                    } // list srlg-group

                } // container if-attribute

            } // list interface

            list redundant-interface {
                key "interface-name";
                description "Enter the redundant-interface list instance";

                leaf interface-name {
                    type types-sros:interface-name;
                    description "Name of the interface";
                }

                leaf description {
                    type types-sros:very-long-description;
                    description "Text description";
                }

                leaf admin-state {
                    type types-sros:admin-state;
                    default "enable";
                    description "Administrative state of the interface";
                }

                leaf ip-mtu {
                    type types-router:ip-mtu-ext;
                    units "bytes";
                    description "Interface IP MTU";
                }

                leaf-list apply-groups {
                    type leafref {
                        path "../../../../groups/group/name";
                    }
                    max-elements 8;
                    ordered-by user;
                    description "Apply a configuration group at this level";
                }

                container hold-time {
                    description "Enter the hold-time context";

                    container ipv4 {
                        description "Enter the ipv4 context";

                        container up {
                            description "Enter the up context";

                            leaf seconds {
                                type types-router:hold-time-seconds;
                                units "seconds";
                                description "Up hold time for the IP interface";
                            }

                        } // container up

                        container down {
                            description "Enter the down context";

                            leaf seconds {
                                type types-router:hold-time-seconds;
                                units "seconds";
                                description "Down hold time for the IP interface";
                            }

                            leaf init-only {
                                type boolean;
                                default "false";
                                description "Apply delay only at interface configuration or reboot";
                            }

                        } // container down

                    } // container ipv4

                } // container hold-time

                list spoke-sdp {
                    key "sdp-bind-id";
                    max-elements 1;
                    description "Enter the spoke-sdp list instance";

                    leaf sdp-bind-id {
                        type types-services:sdp-bind-id;
                        description "SDP Binding identifier as <sdp-id>:<vc-id>. sdp-id - [1..32767] vc-id - [1..4294967295].";
                    }

                    leaf description {
                        type types-sros:description;
                        description "Text description";
                    }

                    leaf admin-state {
                        type types-sros:admin-state;
                        default "enable";
                        description "Administrative state of the SDP binding to the service";
                    }

                    leaf control-word {
                        type boolean;
                        default "false";
                        description "Use the control word as preferred";
                    }

                    leaf-list apply-groups {
                        type leafref {
                            path "../../../../../groups/group/name";
                        }
                        max-elements 8;
                        ordered-by user;
                        description "Apply a configuration group at this level";
                    }

                    container ingress {
                        description "Enter the ingress context";

                        leaf vc-label {
                            type types-services:ingress-vc-label;
                            sros-ext:auto-restart-to-modify;
                            description "Static MPLS VC label used by the far end device to send packets through this SDP";
                        }

                        container filter {
                            description "Enter the filter context";

                            leaf ip {
                                type leafref {
                                    path "../../../../../../../filter/ip-filter/filter-name";
                                }
                                description "IPv4 filter policy name";
                            }

                        } // container filter

                    } // container ingress

                    container egress {
                        description "Enter the egress context";

                        leaf vc-label {
                            type types-services:egress-vc-label;
                            sros-ext:auto-restart-to-modify;
                            description "Static MPLS VC label that is used to send packets to the far end device through this SDP";
                        }

                        container filter {
                            description "Enter the filter context";

                            leaf ip {
                                type leafref {
                                    path "../../../../../../../filter/ip-filter/filter-name";
                                }
                                description "IPv4 filter policy name";
                            }

                        } // container filter

                    } // container egress

                } // list spoke-sdp

                container ipv4 {
                    description "Enter the ipv4 context";

                    container primary {
                        presence "Assigns an IP address/IP subnet format and a remote IP.";
                        description "Enter the primary context";

                        leaf address {
                            type types-sros:ipv4-unicast-address;
                            mandatory true;
                            description "IPv4 address to be assigned to the interface";
                        }

                        leaf prefix-length {
                            type uint32 {
                                range "0..32";
                            }
                            mandatory true;
                            description "The prefix length 0..32 for IPv4 Address.";
                        }

                        leaf remote-ip {
                            type types-sros:ipv4-unicast-address;
                            description "IP address of the remote redundant interface.";
                        }

                        leaf-list apply-groups {
                            type leafref {
                                path "../../../../../../groups/group/name";
                            }
                            max-elements 8;
                            ordered-by user;
                            description "Apply a configuration group at this level";
                        }

                    } // container primary

                } // container ipv4

            } // list redundant-interface

            container igmp-host-tracking {
                description "Enter the igmp-host-tracking context";

                leaf admin-state {
                    type types-sros:admin-state;
                    default "disable";
                    description "Administrative state of IGMP host tracking";
                }

                leaf expiry-time {
                    type types-sros:time-duration {
                        range "1..65535";
                    }
                    units "seconds";
                    default "260";
                    description "Time during which the system continues to track inactive hosts";
                }

                leaf-list apply-groups {
                    type leafref {
                        path "../../../../groups/group/name";
                    }
                    max-elements 8;
                    ordered-by user;
                    description "Apply a configuration group at this level";
                }

            } // container igmp-host-tracking

            uses conf-svc-ies-sub-if-subscriber-interface;
            uses conf-svc-ies-vdo-if-video-interface;
        } // list ies

    } // grouping conf-svc-ies

}
