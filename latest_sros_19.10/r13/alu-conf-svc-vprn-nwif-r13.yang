module alu-conf-svc-vprn-nwif-r13 {
  yang-version "1";

  namespace "urn:alcatel-lucent.com:sros:ns:yang:conf-svc-vprn-nwif-r13";

  prefix "conf-svc-vprn-nwif-r13";

  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure network interfaces for VPRN 
       services on SR OS based routers. 
       
       Copyright 2014-2015 Alcatel-Lucent, 2016 Nokia. All rights reserved. 
       Reproduction of this document is authorized on the condition that the 
       foregoing copyright notice is included. 
       
       This alu-conf-svc-vprn-nwif-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-10-09";

  grouping alu-conf-svc-vprn-nwif-r13 {
    list network-interface {
      key "interface-name";
      description
          "Configure network interfaces for VPRN services";
      leaf interface-name {
        type string {
          length "1..32";
        }
        description
            "[32 chars max] (must start with a letter)";
      } //interface-name

      container address {
        description
            "Assigns an IP address/IP subnet/broadcast address format to the interface";
        leaf ip-address-mask {
          type string;
          description
              "ip-address a.b.c.d 
               mask [1..32]";
        } //ip-address-mask

        leaf netmask {
          type string;
          description
              "a.b.c.d (network bits all 1 and host bits all 0)";
        } //netmask

        leaf broadcast {
          type enumeration {
            enum all-ones;
            enum host-ones;
          }
          description
              "keywords";
        } //broadcast

      } //container address

      leaf allow-directed-broadcasts {
        type boolean;
        description
            "Enable/disable forwarding of directed broadcasts on the interface";
      }

      container arp-retry-timer {
        description
            "Configures ARP retry interval on the interface";
        leaf t100s-of-milliseconds {
          type uint32 {
            range "1..300";
          }
          default 50;
          description
              "[1..300] Default: 50";
        } //t100s-of-milliseconds

      } //container arp-retry-timer

      container arp-timeout {
        description
            "Configures timeout for an ARP entry learned on the interface";
        leaf seconds {
          type uint32 {
            range "0..65535";
          }
          default 14400;
        } //seconds

      } //container arp-timeout

      container bfd {
        description
            "Configure BFD parameters";
        leaf transmit-interval {
          type uint32 {
            range "10..100000";
          }
          description
              "[10..100000] in milliseconds";
        } //transmit-interval

        leaf receive {
          type uint32 {
            range "10..100000";
          }
          description
              "[10..100000] in milliseconds";
        } //receive

        leaf multiplier {
          type string;
          description
              "[3..20]";
        } //multiplier

        leaf echo-receive {
          type uint32 {
            range "100..100000";
          }
          description
              "[100..100000] in milliseconds";
        } //echo-receive

        leaf type {
          type enumeration {
            enum cpm-np;
          }
          description
              "keyword - use CPM network processor";
        } //type

      } //container bfd

      container cpu-protection {
        description
            "Assign a CPU protection policy for the interface";
        leaf policy-id {
          type uint32 {
            range "1..255";
          }
          default 255;
          description
              "[1..255] - Default: 255";
        } //policy-id

      } //container cpu-protection

      container delayed-enable {
        status "obsolete";
        description
            "Delays making interface operational by the specified number of seconds";
        leaf seconds {
          type uint32 {
            range "1..65535";
          }
        } //seconds

        leaf init-only {
          type boolean;
        } //init-only

      } //container delayed-enable

      container description {
        description
            "Description for the interface";
        leaf long-description-string {
          type string {
            length "1..255";
          }
        } //long-description-string

      } //container description

      container dist-cpu-protection {
        description
            "Assign Distributed CPU protection policy for the interface";
        leaf policy-name {
          type string;
        } //policy-name

      } //container dist-cpu-protection

      leaf enable-ingress-stats {
        type boolean;
        description
            "Enable/disable the gathering of ingress interface statistics";
      }

      container ip-mtu {
        description
            "Configure the interface IP MTU";
        leaf octets {
          type uint32 {
            range "512..9000";
          }
        } //octets

        leaf octets-1 {
          type uint32 {
            range "512..9786";
          }
        } //octets-1

      } //container ip-mtu

      container lag {
        description
            "Bind the interface to a Link Aggregation Group (LAG)";
        leaf lag-id-encap-val {
          type string {
            length "1..16";
          }
          description
              "Attribute lag-id[:encap-val] for lag";
        } //lag-id-encap-val

      } //container lag

      container lag-link-map-profile {
        description
            "Configure lag link profile";
        leaf link-map-profile-id {
          type string;
          description
              "Attribute link-map-profile-id for lag-link-map-profile";
        } //link-map-profile-id

      } //container lag-link-map-profile

      container lag-per-link-hash {
        description
            "Configure per-link-hash information";
        leaf class {
          type enumeration {
            enum 1;
            enum 2;
            enum 3;
          }
        } //class

        leaf weight {
          type uint32 {
            range "1..1024";
          }
        } //weight

      } //container lag-per-link-hash

      leaf loopback {
        type boolean;
        description
            "Configure the interface as a loopback interface";
      }

      container mac {
        description
            "Assign a MAC address to the interface";
        leaf ieee-address {
          type string;
          description
              "xx:xx:xx:xx:xx:xx or xx-xx-xx-xx-xx-xx";
        } //ieee-address

      } //container mac

      leaf ntp-broadcast {
        type boolean;
        status "obsolete";
        description
            "Enable/disable receiving of NTP/SNTP broadcasts on the interface";
      }

      container port {
        description
            "Bind the interface to a physical port";
        leaf port-name {
          type string;
          description
              "<port-id>[:encap-val] 
               encap-val - 0 for null 
               - [0..4094] for dot1q 
               - [0..4094].* or 
               [1..4094].[0..4094] for qinq 
               ";
        } //port-name

        leaf port-id {
          type string {
            length "1..64";
          }
          description
              "Attribute port-id for port";
        } //port-id

      } //container port

      container qos {
        description
            "Associate a network Quality of Service (QoS) policy with the interface";
        leaf network-policy-id {
          type uint32 {
            range "1..65535";
          }
        } //network-policy-id

        leaf egress-port-redirect-group {
          type string {
            length "1..32";
          }
        } //egress-port-redirect-group

        leaf egress-instance {
          type uint16 {
            range "1..65535";
          }
        } //egress-instance

        leaf ingress-fp-redirect-group {
          type string {
            length "1..32";
          }
        } //ingress-fp-redirect-group

        leaf ingress-instance {
          type uint16 {
            range "1..65535";
          }
        } //ingress-instance

      } //container qos

      list secondary {
        key "ip-address-mask netmask";
        description
            "Assigns a secondary IP address/IP subnet/broadcast address format to the 
             interface";
        leaf ip-address-mask {
          type string;
          description
              "ip-address a.b.c.d 
               mask [0..32]";
        } //ip-address-mask

        leaf netmask {
          type string;
          description
              "a.b.c.d (network bits all 1 and host bits all 0)";
        } //netmask

        leaf broadcast {
          type enumeration {
            enum all-ones;
            enum host-ones;
          }
          description
              "keywords";
        } //broadcast

        leaf igp-inhibit {
          type boolean;
          description
              "secondary ip-address should not be recognized as a local interface by the 
               running IGP";
        } //igp-inhibit

      } //list secondary

      leaf shutdown {
        type boolean;
        description
            "Administratively enable/disable the interface";
      }

      list static-arp {
        key "ip-address";
        description
            "Configure a static ARP entry for the interface";
        leaf ip-address {
          type inet:ip-address;
        } //ip-address

        leaf ieee-address {
          type string;
          description
              "xx:xx:xx:xx:xx:xx or xx-xx-xx-xx-xx-xx";
        } //ieee-address

      } //list static-arp

      container tcp-mss {
        description
            "Configure TCP maximum segment size for the interface";
        leaf mss-value {
          type uint32 {
            range "384..9158";
          }
        } //mss-value

        leaf mss-value-1 {
          type uint32 {
            range "384..9746";
          }
        } //mss-value-1

      } //container tcp-mss

      container tos-marking-state {
        description
            "Specify TOS marking state";
        leaf trusted-untrusted {
          type enumeration {
            enum trusted;
            enum untrusted;
          }
          description
              "keywords";
        } //trusted-untrusted

      } //container tos-marking-state

      container cflowd-parameters {
        description
            "Configure Cflowd parameters on the interface";
        list sampling {
          key "sampling-id";
          description
              "Configure the Cflowd sampling parameters";
          leaf sampling-id {
            type enumeration {
              enum unicast;
              enum multicast;
              enum both;
            }
          } //sampling-id

          leaf type {
            type enumeration {
              enum acl;
              enum interface;
            }
          } //type

          leaf direction {
            type enumeration {
              enum ingress-only;
              enum egress-only;
              enum both;
            }
            default "ingress-only";
            description
                "keywords - Default: ingress-only";
          } //direction

          leaf sample-profile {
            type uint32 {
              range "1..5";
            }
            default 1;
          } //sample-profile

        } //list sampling

      } //container cflowd-parameters

      container egress {
        description
            "Configure egress network filter policies for the interface.";
        list filter {
          key "ip";
          description
              "IP filter policy associated with the interface";
          leaf ip {
            type string;
            description
                "[1..65535]|<name:64 char max>";
          } //ip

        } //list filter

      } //container egress

      container hold-time {
        description
            "Configure the hold times (up/down) for the interface";
        list down {
          key "ip";
          description
              "Configure the hold time when the interface is coming up";
          leaf ip {
            type boolean;
          } //ip

          leaf seconds {
            type uint32 {
              range "1..1200";
            }
          } //seconds

          leaf init-only {
            type boolean;
          } //init-only

        } //list down

        list up {
          key "ip";
          description
              "Configure the hold time when the interface is going down";
          leaf ip {
            type boolean;
          } //ip

          leaf seconds {
            type uint32 {
              range "1..1200";
            }
          } //seconds

        } //list up

      } //container hold-time

      container icmp {
        description
            "Configure ICMP parameters for the interface";
        leaf mask-reply {
          type boolean;
          description
              "Enable/disable responses to ICMP mask requests";
        }

        container param-problem {
          description
              "Configures rate for ICMP param-problem messages";
          leaf-list number-seconds {
            type uint16 {
              range "1..1000";
            }
            max-elements 2;
            description
                "number [10..1000] 
                 seconds [1..60]";
          } //number-seconds

        } //container param-problem

        container redirects {
          description
              "Configures rate for ICMP redirect messages";
          leaf-list number-seconds {
            type uint16 {
              range "1..1000";
            }
            max-elements 2;
            description
                "number [10..1000] 
                 seconds [1..60]";
          } //number-seconds

        } //container redirects

        container ttl-expired {
          description
              "Configures rate for ICMP TTL expired messages";
          leaf-list number-seconds {
            type uint16 {
              range "1..2000";
            }
            max-elements 2;
            description
                "number [10..2000] 
                 seconds [1..60]";
          } //number-seconds

        } //container ttl-expired

        container unreachables {
          description
              "Configures rate for ICMP unreachable messages";
          leaf-list number-seconds {
            type uint16 {
              range "1..2000";
            }
            max-elements 2;
            description
                "number [10..2000] 
                 seconds [1..60]";
          } //number-seconds

        } //container unreachables

      } //container icmp

      container ingress {
        description
            "Configure ingress network filter policies for the interface.";
        list filter {
          key "ip";
          description
              "IP filter policy associated with the interface";
          leaf ip {
            type string;
            description
                "[1..65535]|<name:64 char max>";
          } //ip

        } //list filter

        leaf flowspec {
          type boolean;
          status "obsolete";
          description
              "Enable/disable IPv4 Flowspec on the interface";
        }

      } //container ingress

      container load-balancing {
        description
            "Context to configure hashing commands";
        container egr-ip-load-balancing {
          description
              "Configure egr-ip-load-balancing for the interface";
          leaf algorithm {
            type enumeration {
              enum source;
              enum destination;
              enum inner-ip;
            }
          } //algorithm

        } //container egr-ip-load-balancing

        container lsr-load-balancing {
          description
              "Configure the LSR Load Balancing algorithm for the interface";
          leaf hashing-algorithm {
            type enumeration {
              enum lbl-ip;
              enum lbl-only;
              enum ip-only;
              enum eth-encap-ip;
              enum lbl-ip-l4-teid;
            }
            description
                "lbl-only | lbl-ip | ip-only | eth-encap-ip | lbl-ip-l4-teid 
                 Default: use system configuration";
          } //hashing-algorithm

        } //container lsr-load-balancing

        leaf spi-load-balancing {
          type boolean;
          description
              "Enable/disable SPI use in hashing for the interface";
        }

        leaf teid-load-balancing {
          type boolean;
          description
              "Enable/disable TEID load balancing for the interface";
        }

      } //container load-balancing

      container urpf-check {
        presence
            "Enables/Configures unicast RPF check for an interface";
        leaf ignore-default {
          type boolean;
          description
              "Enable/Disable default route when performing a uRPF check.";
        }

        container mode {
          description
              "Configure unicast RPF check mode";
          leaf strict-loose-strict-no-ecmp {
            type enumeration {
              enum strict;
              enum loose;
              enum strict-no-ecmp;
            }
            description
                "keywords";
          } //strict-loose-strict-no-ecmp

        } //container mode

      } //container urpf-check

    } //list network-interface

  } //grouping alu-conf-svc-vprn-nwif-r13

} //module  alu-conf-svc-vprn-nwif-r13
