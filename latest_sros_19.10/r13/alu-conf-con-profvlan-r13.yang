module alu-conf-con-profvlan-r13 {
  yang-version "1";

  namespace "urn:alcatel-lucent.com:sros:ns:yang:conf-con-profvlan-r13";

  prefix "conf-con-profvlan-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure Connection Profiles Ethernet 
       Specific VLAN on SR OS based routers. 
       
       Copyright 2014-2015 Alcatel-Lucent, 2016 Nokia. All rights reserved. 
       Reproduction of this document is authorized on the condition that the 
       foregoing copyright notice is included. 
       
       This alu-conf-con-profvlan-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-con-profvlan-r13 {
    list connection-profile-vlan {
      key "conn-prof-id";
      description
          "Configure Connection Profiles Ethernet Specific VLAN";
      leaf conn-prof-id {
        type uint32 {
          range "1..8000";
        }
      } //conn-prof-id

      container description {
        description
            "Configure a connection profile VLAN description";
        leaf description-string {
          type string {
            length "1..80";
          }
        } //description-string

      } //container description

      list vlan-range {
        key "from";
        description
            "Configure a connection profile vlan range";
        leaf from {
          type int32 {
            range "1..4094";
          }
        } //from

        leaf to {
          type int32 {
            range "1..4094";
          }
        } //to

      } //list vlan-range

    } //list connection-profile-vlan

  } //grouping alu-conf-con-profvlan-r13

} //module  alu-conf-con-profvlan-r13
