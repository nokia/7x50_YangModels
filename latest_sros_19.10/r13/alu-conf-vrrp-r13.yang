module alu-conf-vrrp-r13 {
  yang-version "1";

  namespace "urn:alcatel-lucent.com:sros:ns:yang:conf-vrrp-r13";

  prefix "conf-vrrp-r13";

  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure VRRP Policies on SR OS based 
       routers. 
       
       Copyright 2014-2015 Alcatel-Lucent, 2016 Nokia. All rights reserved. 
       Reproduction of this document is authorized on the condition that the 
       foregoing copyright notice is included. 
       
       This alu-conf-vrrp-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-vrrp-r13 {
    container vrrp {
      description
          "Configure VRRP Policies";
      list policy {
        key "policy-id";
        description
            "Context to configure a VRRP policy";
        leaf policy-id {
          type uint32 {
            range "1..9999";
          }
        } //policy-id

        leaf context {
          type boolean;
        } //context

        leaf policy-id-1 {
          type uint32 {
            range "1..2147483647";
          }
        } //policy-id-1

        leaf name {
          type string;
          description
              "64-char max";
        } //name

        container delta-in-use-limit {
          description
              "Configure the limit on the in-use priority derived from delta priority control 
               events";
          leaf limit {
            type int64 {
              range "1..254";
            }
          } //limit

        } //container delta-in-use-limit

        container description {
          description
              "Textual description for the policy";
          leaf description-string {
            type string {
              length "1..80";
            }
          } //description-string

        } //container description

        leaf shutdown {
          type boolean;
          description
              "Administratively enable/disable the policy";
        }

        container priority-event {
          presence
              "Context to configure priority control events for the policy";
          container host-unreachable {
            description
                "Configure a Host Unreachable priority control event";
            leaf ip-address {
              type inet:ip-address;
            } //ip-address

            leaf ipv6-address {
              type inet:ipv6-address;
              description
                  "Attribute ipv6-address for host-unreachable";
            } //ipv6-address

            container drop-count {
              description
                  "Configure limit on number of consecutive ICMP Echo Request transmit failures";
              leaf count {
                type uint32 {
                  range "1..60";
                }
              } //count

            } //container drop-count

            container hold-clear {
              description
                  "Configure hold clear time for the event";
              leaf seconds {
                type int32 {
                  range "0..86400";
                }
              } //seconds

            } //container hold-clear

            container hold-set {
              description
                  "Configure hold set time for the event";
              leaf seconds {
                type int32 {
                  range "0..86400";
                }
              } //seconds

            } //container hold-set

            container interval {
              description
                  "Configure time interval between consecutive ICMP Echo Requests";
              leaf seconds {
                type uint32 {
                  range "1..60";
                }
              } //seconds

            } //container interval

            container padding-size {
              description
                  "Configure packet length padding of the ICMP packet";
              leaf size {
                type uint32 {
                  range "0..16384";
                }
              } //size

            } //container padding-size

            container priority {
              description
                  "Configure priority level and type for the event";
              leaf priority-level {
                type uint8 {
                  range "0..254";
                }
              } //priority-level

              leaf delta-explicit {
                type enumeration {
                  enum delta;
                  enum explicit;
                }
                default "delta";
                description
                    "keywords - type of control event (Default - delta)";
              } //delta-explicit

            } //container priority

            container timeout {
              description
                  "Configure timeout for ICMP Echo Request messages";
              leaf seconds {
                type uint32 {
                  range "1..60";
                }
              } //seconds

            } //container timeout

          } //container host-unreachable

          list lag-port-down {
            key "lag-id";
            description
                "Configure a LAG Port Down priority control event";
            leaf lag-id {
              type string;
              description
                  "Attribute lag-id for lag-port-down";
            } //lag-id

            container hold-clear {
              description
                  "Configure hold clear time for the event";
              leaf seconds {
                type int32 {
                  range "0..86400";
                }
              } //seconds

            } //container hold-clear

            container hold-set {
              description
                  "Configure hold set time for the event";
              leaf seconds {
                type int32 {
                  range "0..86400";
                }
              } //seconds

            } //container hold-set

            list number-down {
              key "number-of-lag-ports-down";
              description
                  "Configuration context based on number of LAG ports that are down";
              leaf number-of-lag-ports-down {
                type string;
                description
                    "Attribute number-of-lag-ports-down for number-down";
              } //number-of-lag-ports-down

              container priority {
                description
                    "Configure priority level and type for the event";
                leaf priority-level {
                  type uint8 {
                    range "0..254";
                  }
                } //priority-level

                leaf delta-explicit {
                  type enumeration {
                    enum delta;
                    enum explicit;
                  }
                  default "delta";
                  description
                      "keywords - type of control event (Default - delta)";
                } //delta-explicit

              } //container priority

            } //list number-down

            list weight-down {
              key "lag-ports-down-weight";
              description
                  "Configuration context based on weight of LAG ports that are down";
              leaf lag-ports-down-weight {
                type string;
                description
                    "Attribute lag-ports-down-weight for weight-down";
              } //lag-ports-down-weight

              container priority {
                description
                    "Configure priority level and type for the event";
                leaf priority-level {
                  type uint8 {
                    range "0..254";
                  }
                } //priority-level

                leaf delta-explicit {
                  type enumeration {
                    enum delta;
                    enum explicit;
                  }
                  default "delta";
                  description
                      "keywords - type of control event (Default - delta)";
                } //delta-explicit

              } //container priority

            } //list weight-down

          } //list lag-port-down

          list mc-ipsec-non-forwarding {
            key "tunnel-grp-id";
            description
                "Configure multi-chassis IPsec non-forwarding event";
            leaf tunnel-grp-id {
              type uint32 {
                range "1..16";
              }
            } //tunnel-grp-id

            container hold-clear {
              description
                  "Configure hold clear time for the event";
              leaf seconds {
                type int32 {
                  range "0..86400";
                }
              } //seconds

            } //container hold-clear

            container hold-set {
              description
                  "Configure hold set time for the event";
              leaf seconds {
                type int32 {
                  range "0..86400";
                }
              } //seconds

            } //container hold-set

            container priority {
              description
                  "Configure priority level and type for the event";
              leaf priority-level {
                type uint8 {
                  range "0..254";
                }
              } //priority-level

              leaf explicit {
                type boolean;
              } //explicit

            } //container priority

          } //list mc-ipsec-non-forwarding

          list port-down {
            key "port-id";
            description
                "Configure a Port Down priority control event";
            leaf port-id {
              type string {
                length "1..64";
              }
              description
                  "Attribute port-id for port-down";
            } //port-id

            container hold-clear {
              description
                  "Configure hold clear time for the event";
              leaf seconds {
                type int32 {
                  range "0..86400";
                }
              } //seconds

            } //container hold-clear

            container hold-set {
              description
                  "Configure hold set time for the event";
              leaf seconds {
                type int32 {
                  range "0..86400";
                }
              } //seconds

            } //container hold-set

            container priority {
              description
                  "Configure priority level and type for the event";
              leaf priority-level {
                type uint8 {
                  range "0..254";
                }
              } //priority-level

              leaf delta-explicit {
                type enumeration {
                  enum delta;
                  enum explicit;
                }
                default "delta";
                description
                    "keywords - type of control event (Default - delta)";
              } //delta-explicit

            } //container priority

          } //list port-down

          container route-unknown {
            description
                "Configure a Route Unknown priority control event";
            leaf ip-prefix-mask {
              type inet:ip-prefix;
              description
                  "ip-prefix a.b.c.d (host bits must be 0) 
                   mask [0..32]";
            } //ip-prefix-mask

            leaf ipv6-address-prefix-length {
              type string;
              description
                  "ipv6-address x:x:x:x:x:x:x:x (eight 16-bit pieces) 
                   x [0..FFFF]H 
                   prefix-length [1..128]";
            } //ipv6-address-prefix-length

            container hold-clear {
              description
                  "Configure hold clear time for the event";
              leaf seconds {
                type int32 {
                  range "0..86400";
                }
              } //seconds

            } //container hold-clear

            container hold-set {
              description
                  "Configure hold set time for the event";
              leaf seconds {
                type int32 {
                  range "0..86400";
                }
              } //seconds

            } //container hold-set

            container less-specific {
              description
                  "Allow match on routes with less specific prefix";
              leaf allow-default {
                type boolean;
                description
                    "keyword - match on default route";
              } //allow-default

            } //container less-specific

            container next-hop {
              description
                  "Configure next-hop IP address as match criteria";
              leaf ip-address {
                type inet:ip-address;
              } //ip-address

              leaf ipv6-address {
                type inet:ipv6-address;
                description
                    "Attribute ipv6-address for next-hop";
              } //ipv6-address

            } //container next-hop

            container priority {
              description
                  "Configure priority level and type for the event";
              leaf priority-level {
                type uint8 {
                  range "0..254";
                }
              } //priority-level

              leaf delta-explicit {
                type enumeration {
                  enum delta;
                  enum explicit;
                }
                default "delta";
                description
                    "keywords - type of control event (Default - delta)";
              } //delta-explicit

            } //container priority

            list protocol {
              key "protocol";
              description
                  "Configure a routing protocol as a match criteria";
              leaf protocol {
                type enumeration {
                  enum bgp;
                  enum bgp-vpn;
                  enum ospf;
                  enum isis;
                  enum rip;
                  enum static;
                }
              } //protocol

            } //list protocol

          } //container route-unknown

        } //container priority-event

      } //list policy

    } //container vrrp

  } //grouping alu-conf-vrrp-r13

} //module  alu-conf-vrrp-r13
