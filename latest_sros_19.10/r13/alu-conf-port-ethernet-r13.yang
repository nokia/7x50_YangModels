module alu-conf-port-ethernet-r13 {
  yang-version "1";

  namespace "urn:alcatel-lucent.com:sros:ns:yang:conf-port-ethernet-r13";

  prefix "conf-port-ethernet-r13";

  import alu-types {
    prefix "alu";
  }
  import ietf-yang-types {
    prefix "yang";
  }

  alu:alu-major-release "rel19";

  organization "Alcatel-Lucent";

  contact
      "Alcatel-Lucent SR OS Support 
       Web: <http://www.alcatel-lucent.com>";

  description
      "Alcatel-Lucent YANG Data model to configure ethernet parameters for a port on 
       SR OS based routers. 
       
       Copyright 2014-2015 Alcatel-Lucent, 2016 Nokia. All rights reserved. 
       Reproduction of this document is authorized on the condition that the 
       foregoing copyright notice is included. 
       
       This alu-conf-port-ethernet-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-01-31";

  grouping alu-conf-port-ethernet-r13 {
    container ethernet {
      description
          "Configure ethernet parameters for a port";
      container accounting-policy {
        description
            "Configure the accounting policy which applies to the ethernet port";
        leaf policy-id {
          type uint32 {
            range "1..99";
          }
        } //policy-id

      } //container accounting-policy

      container autonegotiate {
        description
            "Enable/disable speed and duplex autonegotiation on an ethernet port";
        leaf limited {
          type boolean;
        } //limited

      } //container autonegotiate

      leaf collect-stats {
        type boolean;
        description
            "Enable/disable the collection of statistical data";
      }

      container dot1q-etype {
        description
            "Configure the ethertype used for dot1q encapsulation";
        leaf t0x0600..0xffff {
          type string;
          description
              "[1536..65535] - accepts in decimal or hex";
        } //t0x0600..0xffff

      } //container dot1q-etype

      container down-on-internal-error {
        description
            "Configure the behavior of port-state when an internal error is detected.";
        leaf tx-disable {
          type boolean;
          description
              "keyword - disable remote laser on error";
        } //tx-disable

      } //container down-on-internal-error

      container duplex {
        description
            "Configure duplex of an ethernet port";
        leaf full-half {
          type enumeration {
            enum full;
            enum half;
          }
          description
              "keywords";
        } //full-half

      } //container duplex

      container egress-port-qos-policy {
        description
            "Configure an egress port qos policy";
        leaf port-qos-policy-name {
          type string;
        } //port-qos-policy-name

      } //container egress-port-qos-policy

      container egress-rate {
        description
            "Specify the egress-rate";
        leaf sub-rate {
          type uint32 {
            range "1..400000000";
          }
          description
              "[1..400000000] - kbps";
        } //sub-rate

      } //container egress-rate

      container egress-scheduler-policy {
        description
            "Configure an egress scheduler policy";
        leaf port-sched-plcy-name {
          type string {
            length "1..32";
          }
        } //port-sched-plcy-name

        leaf hsmda-sched-plcy-name {
          type string {
            length "1..32";
          }
        } //hsmda-sched-plcy-name

      } //container egress-scheduler-policy

      container encap-type {
        description
            "Configure encapsulation method";
        leaf dot1q-null-qinq {
          type enumeration {
            enum dot1q;
            enum null;
            enum qinq;
          }
          description
              "keywords";
        } //dot1q-null-qinq

      } //container encap-type

      leaf eth-bn-egress-rate-changes {
        type boolean;
        description
            "Enable/Disable rate changes received in Eth-BN messages to update the egress 
             rate used on the port";
      }

      container hold-time {
        description
            "Configure port link dampening timers";
        leaf up {
          type uint32 {
            range "0..3600000";
          }
          description
              "[0..36000] in seconds 
               [0|10..3600000] in centiseconds in 5 centisecond increments";
        } //up

        leaf down {
          type uint32 {
            range "0..3600000";
          }
          description
              "[0..36000] in seconds 
               [0|10..3600000] in centiseconds in 5 centisecond increments";
        } //down

        leaf hold-time-id {
          type enumeration {
            enum seconds;
            enum centiseconds;
          }
        } //hold-time-id

      } //container hold-time

      container ingress-rate {
        description
            "Configure the maximum amount of ingress bandwidth that this port can receive";
        leaf ingress-rate {
          type uint32 {
            range "1..400000";
          }
          description
              "[1..400000] mbps";
        } //ingress-rate

      } //container ingress-rate

      leaf lacp-tunnel {
        type boolean;
        description
            "Enable/disable LACP tunnel";
      }

      container load-balancing-algorithm {
        description
            "Configure Load Balancing Algorithm";
        leaf option {
          type enumeration {
            enum include-l4;
            enum exclude-l4;
          }
        } //option

      } //container load-balancing-algorithm

      container loopback {
        description
            "Configure the Ethernet port loopback";
        leaf line-internal {
          type enumeration {
            enum line;
            enum internal;
          }
          description
              "keywords";
        } //line-internal

        leaf swap-src-dst-mac {
          type boolean;
          description
              "Swap source and destination MAC addresses";
        } //swap-src-dst-mac

      } //container loopback

      container mac {
        description
            "Assign a specific MAC address to an ethernet port";
        leaf ieee-address {
          type alu:ieee-address;
          description
              "xx:xx:xx:xx:xx:xx or xx-xx-xx-xx-xx-xx";
        } //ieee-address

      } //container mac

      container min-frame-length {
        description
            "Configure the minimum transmitted frame length";
        leaf byte-length {
          type enumeration {
            enum 64;
            enum 68;
          }
          description
              "64|68 - Default: 64 Bytes";
        } //byte-length

      } //container min-frame-length

      container mode {
        description
            "Configure an ethernet port for access or network mode";
        leaf access-network-hybrid {
          type enumeration {
            enum access;
            enum network;
            enum hybrid;
          }
          description
              "keywords";
        } //access-network-hybrid

      } //container mode

      leaf monitor-egress-scheduler {
        type boolean;
        description
            "Enable/Disable monitoring of egress scheduler";
      }

      container mtu {
        description
            "Configure the maximum payload MTU size for an ethernet port";
        leaf mtu-bytes {
          type uint32 {
            range "512..9800";
          }
          description
              "Attribute mtu-bytes for mtu";
        } //mtu-bytes

      } //container mtu

      container pbb-etype {
        description
            "Configure the ethertype used for pbb";
        leaf t0x0600..0xffff {
          type string;
          description
              "[1536..65535] - accepts in decimal or hex";
        } //t0x0600..0xffff

      } //container pbb-etype

      container ptp-asymmetry {
        description
            "Configure the PTP asymmetry delay delta";
        leaf nanoseconds {
          type int32;
        } //nanoseconds

      } //container ptp-asymmetry

      container qinq-etype {
        description
            "Configure the ethertype used for qinq encapsulation";
        leaf t0x0600..0xffff {
          type string;
          description
              "[1536..65535] - accepts in decimal or hex";
        } //t0x0600..0xffff

        leaf dot1q-etype {
          type string;
          description
              "[1536..65535] - accepts in decimal or hex";
        } //dot1q-etype

      } //container qinq-etype

      container report-alarm {
        description
            "Enable/disable logging of alarms on ethernet port";
        leaf signal-fail {
          type boolean;
        } //signal-fail

        leaf remote {
          type boolean;
        } //remote

        leaf local {
          type boolean;
        } //local

        leaf no-frame-lock {
          type boolean;
        } //no-frame-lock

        leaf high-ber {
          type boolean;
        } //high-ber

        leaf no-block-lock {
          type boolean;
        } //no-block-lock

        leaf no-am-lock {
          type boolean;
        } //no-am-lock

        leaf duplicate-lane {
          type boolean;
        } //duplicate-lane

      } //container report-alarm

      container rs-fec-mode {
        description
            "Configure the RS FEC mode of the port";
        leaf RS-FEC-mode {
          type enumeration {
            enum cl91-514-528;
            enum cl74;
            enum cl108;
          }
          description
              "cl91-514-528 | cl74 | cl108";
        } //RS-FEC-mode

      } //container rs-fec-mode

      leaf sflow {
        type boolean;
        description
            "Configure this port as an sFlow counter poller";
      }

      leaf single-fiber {
        type boolean;
        description
            "Enable/disable single fiber";
      }

      container speed {
        description
            "Configure the speed of an ethernet port";
        leaf t10-100-1000-10000-25000-40000-50000-100000 {
          type enumeration {
            enum 10;
            enum 100;
            enum 1000;
            enum 10000;
            enum 25000;
            enum 40000;
            enum 50000;
            enum 100000;
          }
          description
              "keywords";
        } //t10-100-1000-10000-25000-40000-50000-100000

      } //container speed

      container util-stats-interval {
        description
            "Configure the interval used to calculate the utilization statistics.";
        leaf seconds {
          type uint32 {
            range "30..600";
          }
          default 300;
          description
              "[30..600] seconds - Default: 300";
        } //seconds

      } //container util-stats-interval

      container xgig {
        description
            "Configure LAN or WAN mode";
        leaf lan-wan {
          type enumeration {
            enum lan;
            enum wan;
          }
          description
              "keywords";
        } //lan-wan

      } //container xgig

      container access {
        description
            "Configure ethernet access port parameters";
        container accounting-policy {
          description
              "Configure the accounting policy which applies to the ethernet access port";
          leaf policer-id {
            type uint32 {
              range "1..99";
            }
          } //policer-id

        } //container accounting-policy

        container bandwidth {
          description
              "Configure Bandwidth";
          leaf bandwidth-in-kbps {
            type string;
            description
                "[1..6400000000]";
          } //bandwidth-in-kbps

        } //container bandwidth

        container booking-factor {
          description
              "Configure Booking Factor";
          leaf percent-of-port-bandwidth {
            type uint16 {
              range "1..1000";
            }
          } //percent-of-port-bandwidth

        } //container booking-factor

        leaf collect-stats {
          type boolean;
          description
              "Enable/disable the collection of statistical data";
        }

        container egress {
          description
              "Configure ethernet access egress port parameters";
          list queue-group {
            key "queue-group-name instance";
            description
                "Configure ethernet port egress queue-group";
            leaf queue-group-name {
              type string {
                length "1..32";
              }
            } //queue-group-name

            leaf instance {
              type uint16 {
                range "1..65535";
              }
              description
                  "[1..65535]";
            } //instance

            container accounting-policy {
              description
                  "Configure accounting policy for the ethernet port egress queue-group";
              leaf acct-policy-id {
                type uint64 {
                  range "1..99";
                }
              } //acct-policy-id

            } //container accounting-policy

            leaf collect-stats {
              type boolean;
              description
                  "Enable/Disable collection of statistics on this queue-group";
            }

            container description {
              description
                  "Configure description for the port queue-group";
              leaf description-string {
                type string {
                  length "1..80";
                }
              } //description-string

            } //container description

            list host-match {
              key "dest";
              description
                  "Configure host matching for the ethernet port egress queue-group";
              leaf dest {
                type string {
                  length "1..32";
                }
              } //dest

            } //list host-match

            leaf hs-turbo {
              type boolean;
              description
                  "Enable/Disable HS Turbo";
            }

            container scheduler-policy {
              description
                  "Configure scheduler-policy for the QoS egress queue-group";
              leaf scheduler-policy-name {
                type string {
                  length "1..32";
                }
              } //scheduler-policy-name

            } //container scheduler-policy

            container agg-rate {
              presence
                  "Configure aggregate rate limit";
              leaf limit-unused-bandwidth {
                type boolean;
                description
                    "Specify whether to enable limit unused bandwidth";
              }

              leaf queue-frame-based-accounting {
                type boolean;
                description
                    "Specify whether to enable queue frame based accounting";
              }

              container rate {
                description
                    "Specify rate limit for agg-rate";
                leaf kilobits-per-second {
                  type string;
                  description
                      "[1..3200000000|max] Kbps";
                } //kilobits-per-second

              } //container rate

            } //container agg-rate

            container hsmda-queue-override {
              presence
                  "Configure HSMDA egress queue overrides";
              container packet-byte-offset {
                description
                    "Specify a packet offset for HSMDA queue accounting";
                leaf add {
                  type uint32 {
                    range "0..31";
                  }
                } //add

                leaf subtract {
                  type string;
                  description
                      "Attribute sub-bytes for packet-byte-offset";
                } //subtract

              } //container packet-byte-offset

              container secondary-shaper {
                description
                    "Configure a HSMDA egress secondary shaper";
                leaf secondary-shaper-name {
                  type string {
                    length "1..32";
                  }
                } //secondary-shaper-name

              } //container secondary-shaper

              container wrr-policy {
                description
                    "Configure a HSMDA egress wrr-policy";
                leaf policy-name {
                  type string {
                    length "1..32";
                  }
                } //policy-name

              } //container wrr-policy

              list queue {
                key "queue-id";
                description
                    "Configure overrides for a HSMDA egress queue";
                leaf queue-id {
                  type uint32 {
                    range "1..8";
                  }
                } //queue-id

                container mbs {
                  description
                      "Specify MBS rate";
                  leaf mbs-string {
                    type string;
                  } //mbs-string

                  leaf mbs-id-2 {
                    type enumeration {
                      enum bytes;
                      enum kilobytes;
                    }
                  } //mbs-id-2

                } //container mbs

                container rate {
                  description
                      "Specify rate (PIR)";
                  leaf pir-rate {
                    type string;
                    description
                        "[1..100000000|max]";
                  } //pir-rate

                } //container rate

                container slope-policy {
                  description
                      "Specify slope policy";
                  leaf hsmda-slope-policy-name {
                    type string {
                      length "1..32";
                    }
                  } //hsmda-slope-policy-name

                } //container slope-policy

                container wrr-weight {
                  description
                      "Specify wrr-weight";
                  leaf weight {
                    type int32 {
                      range "1..32";
                    }
                    description
                        "Attribute weight for wrr-weight";
                  } //weight

                } //container wrr-weight

              } //list queue

            } //container hsmda-queue-override

            container queue-overrides {
              description
                  "Configure queue over-rides";
              list queue {
                key "queue-id";
                description
                    "Configure a queue";
                leaf queue-id {
                  type int32 {
                    range "1..8";
                  }
                } //queue-id

                container adaptation-rule {
                  description
                      "Specify the CIR and PIR adaptation rules";
                  leaf pir {
                    type enumeration {
                      enum max;
                      enum min;
                      enum closest;
                    }
                  } //pir

                  leaf cir {
                    type enumeration {
                      enum max;
                      enum min;
                      enum closest;
                    }
                  } //cir

                } //container adaptation-rule

                container burst-limit {
                  description
                      "Specify burst limit";
                  leaf size {
                    type string;
                    description
                        "Attribute size for burst-limit";
                  } //size

                  leaf bytes-kilobytes {
                    type enumeration {
                      enum bytes;
                      enum kilobytes;
                    }
                  } //bytes-kilobytes

                } //container burst-limit

                container cbs {
                  description
                      "Specify CBS rate";
                  leaf size-in-kbytes {
                    type string;
                    description
                        "Attribute size-in-kbytes for cbs";
                  } //size-in-kbytes

                } //container cbs

                container high-prio-only {
                  status "obsolete";
                  description
                      "Specify high priority only burst size";
                  leaf percent {
                    type string;
                    description
                        "[0..100 | default]";
                  } //percent

                } //container high-prio-only

                container mbs {
                  description
                      "Specify MBS rate";
                  leaf size {
                    type string;
                    description
                        "Attribute size for mbs";
                  } //size

                  leaf bytes-kilobytes {
                    type enumeration {
                      enum bytes;
                      enum kilobytes;
                    }
                    description
                        "keyword";
                  } //bytes-kilobytes

                } //container mbs

                leaf monitor-depth {
                  type boolean;
                  description
                      "Enable/Disable queue-depth monitoring";
                }

                container parent {
                  description
                      "Specify Overriding parent parameter for queue-group queue";
                  leaf weight {
                    type uint32 {
                      range "0..100";
                    }
                  } //weight

                  leaf cir-weight {
                    type uint32 {
                      range "0..100";
                    }
                  } //cir-weight

                } //container parent

                container percent-rate {
                  description
                      "Specify Percent rates (CIR and PIR)";
                  leaf pir-percent {
                    type string;
                    description
                        "[0.01..100.00]";
                  } //pir-percent

                  leaf cir {
                    type string;
                    description
                        "[0.00..100.00]";
                  } //cir

                } //container percent-rate

                container rate {
                  description
                      "Specify rates (CIR and PIR)";
                  leaf pir-rate {
                    type string;
                    description
                        "Attribute pir-rate for rate";
                  } //pir-rate

                  leaf cir {
                    type string;
                    description
                        "Attribute cir-rate for rate";
                  } //cir

                } //container rate

                container drop-tail {
                  description
                      "Specify drop tail";
                  container low {
                    description
                        "Specify low drop-tail";
                    container percent-reduction-from-mbs {
                      description
                          "Specify low drop tail percent reduction from MBS";
                      leaf percent {
                        type string;
                        description
                            "[0..100|default]";
                      } //percent

                    } //container percent-reduction-from-mbs

                  } //container low

                } //container drop-tail

              } //list queue

            } //container queue-overrides

            container scheduler-override {
              presence
                  "Apply a scheduler override";
              list scheduler {
                key "scheduler-name";
                description
                    "Configure a scheduler override";
                leaf scheduler-name {
                  type string {
                    length "1..32";
                  }
                } //scheduler-name

                container parent {
                  description
                      "Specify the override weights for the scheduler";
                  leaf weight {
                    type uint32 {
                      range "0..100";
                    }
                  } //weight

                  leaf cir-weight {
                    type uint32 {
                      range "0..100";
                    }
                  } //cir-weight

                } //container parent

                container rate {
                  description
                      "Specify rates (CIR and PIR)";
                  leaf pir-rate {
                    type string;
                    description
                        "[1..6400000000|max] Kbps";
                  } //pir-rate

                  leaf cir {
                    type string;
                    description
                        "[0..6400000000|sum|max] Kbps";
                  } //cir

                } //container rate

              } //list scheduler

            } //container scheduler-override

          } //list queue-group

          list vport {
            key "name";
            description
                "Configure virtual port";
            leaf name {
              type string {
                length "1..32";
              }
            } //name

            container description {
              description
                  "Add/remove a text description for the virtual port";
              leaf description-string {
                type string {
                  length "1..80";
                }
              } //description-string

            } //container description

            leaf egress-rate-modify {
              type boolean;
              description
                  "Enable/disable the egress rate modification";
            }

            list host-match {
              key "dest";
              description
                  "Configure host matching for the ethernet port egress vport";
              leaf dest {
                type string {
                  length "1..32";
                }
              } //dest

            } //list host-match

            leaf monitor-port-scheduler {
              type boolean;
              description
                  "Enable/Disable monitoring of port scheduler";
            }

            container port-scheduler-policy {
              description
                  "Configure port scheduler policy";
              leaf port-scheduler-policy-name {
                type string {
                  length "1..32";
                }
              } //port-scheduler-policy-name

            } //container port-scheduler-policy

            container scheduler-policy {
              description
                  "Apply an egress scheduler policy";
              leaf scheduler-policy-name {
                type string {
                  length "1..32";
                }
              } //scheduler-policy-name

            } //container scheduler-policy

            container agg-rate {
              presence
                  "Configure aggregate rate limit";
              leaf limit-unused-bandwidth {
                type boolean;
                description
                    "Specify whether to enable limit unused bandwidth";
              }

              container rate {
                description
                    "Specify rate limit for agg-rate";
                leaf kilobits-per-second {
                  type string;
                  description
                      "[1..6400000000|max] Kbps";
                } //kilobits-per-second

              } //container rate

            } //container agg-rate

          } //list vport

        } //container egress

        container ingress {
          description
              "Configure ethernet port ingress queue groups";
          container queue-group {
            description
                "Configure QoS ingress queue-group";
            leaf queue-group-name {
              type string {
                length "1..32";
              }
            } //queue-group-name

            container accounting-policy {
              description
                  "Configure accounting policy for the ethernet port ingress queue-group";
              leaf acct-policy-id {
                type uint64 {
                  range "1..99";
                }
              } //acct-policy-id

            } //container accounting-policy

            leaf collect-stats {
              type boolean;
              description
                  "Enable/Disable collection of statistics on this queue-group";
            }

            container description {
              description
                  "Configure description for the port queue-group";
              leaf description-string {
                type string {
                  length "1..80";
                }
              } //description-string

            } //container description

            container scheduler-policy {
              description
                  "Configure scheduler policy for the ethernet port ingress queue-group";
              leaf scheduler-policy-name {
                type string {
                  length "1..32";
                }
              } //scheduler-policy-name

            } //container scheduler-policy

            container queue-overrides {
              description
                  "Configure queue over-rides";
              list queue {
                key "queue-id";
                description
                    "Configure a queue override";
                leaf queue-id {
                  type int32 {
                    range "1..32";
                  }
                } //queue-id

                container adaptation-rule {
                  description
                      "Specify the CIR and PIR adaptation rules";
                  leaf pir {
                    type enumeration {
                      enum max;
                      enum min;
                      enum closest;
                    }
                  } //pir

                  leaf cir {
                    type enumeration {
                      enum max;
                      enum min;
                      enum closest;
                    }
                  } //cir

                } //container adaptation-rule

                container cbs {
                  description
                      "Specify CBS";
                  leaf size-in-kbytes {
                    type string;
                    description
                        "Attribute size-in-kbytes for cbs";
                  } //size-in-kbytes

                } //container cbs

                container high-prio-only {
                  status "obsolete";
                  description
                      "Specify high priority only burst size";
                  leaf percent {
                    type string;
                    description
                        "[0..100 | default]";
                  } //percent

                } //container high-prio-only

                container mbs {
                  description
                      "Specify MBS";
                  leaf size {
                    type string;
                    description
                        "Attribute size for mbs";
                  } //size

                  leaf bytes-kilobytes {
                    type enumeration {
                      enum bytes;
                      enum kilobytes;
                    }
                    description
                        "keyword";
                  } //bytes-kilobytes

                } //container mbs

                leaf monitor-depth {
                  type boolean;
                  description
                      "Enable/Disable queue-depth monitoring";
                }

                container rate {
                  description
                      "Specify rates (CIR and PIR)";
                  leaf pir-rate {
                    type string;
                    description
                        "Attribute pir-rate for rate";
                  } //pir-rate

                  leaf cir {
                    type string;
                    description
                        "Attribute cir-rate for rate";
                  } //cir

                } //container rate

                container drop-tail {
                  description
                      "Specify drop tail";
                  container low {
                    description
                        "Specify low drop-tail";
                    container percent-reduction-from-mbs {
                      description
                          "Specify low drop tail percent reduction from MBS";
                      leaf percent {
                        type string;
                        description
                            "[0..100|default]";
                      } //percent

                    } //container percent-reduction-from-mbs

                  } //container low

                } //container drop-tail

              } //list queue

            } //container queue-overrides

            container scheduler-override {
              presence
                  "Apply a scheduler override";
              list scheduler {
                key "scheduler-name";
                description
                    "Configure a scheduler override";
                leaf scheduler-name {
                  type string {
                    length "1..32";
                  }
                } //scheduler-name

                container parent {
                  description
                      "Specify the override weights for the scheduler";
                  leaf weight {
                    type uint32 {
                      range "0..100";
                    }
                  } //weight

                  leaf cir-weight {
                    type uint32 {
                      range "0..100";
                    }
                  } //cir-weight

                } //container parent

                container rate {
                  description
                      "Specify rates (CIR and PIR)";
                  leaf pir-rate {
                    type string;
                    description
                        "[1..6400000000|max] Kbps";
                  } //pir-rate

                  leaf cir {
                    type string;
                    description
                        "[0..6400000000|sum|max] Kbps";
                  } //cir

                } //container rate

              } //list scheduler

            } //container scheduler-override

          } //container queue-group

        } //container ingress

      } //container access

      container crc-monitor {
        description
            "Configure Ethernet CRC Monitoring parameters";
        container sd-threshold {
          description
              "Configure the Signal Degradation (SD) threshold";
          leaf threshold {
            type uint32 {
              range "1..9";
            }
          } //threshold

          leaf multiplier {
            type uint32 {
              range "1..9";
            }
          } //multiplier

        } //container sd-threshold

        container sf-threshold {
          description
              "Configure the Signal Failure (SF) threshold";
          leaf threshold {
            type uint32 {
              range "1..9";
            }
          } //threshold

          leaf multiplier {
            type uint32 {
              range "1..9";
            }
          } //multiplier

        } //container sf-threshold

        container window-size {
          description
              "Configure the crc-monitor window size";
          leaf seconds {
            type uint32 {
              range "5..60";
            }
            default 10;
            description
                "[5..60] - Default: 10 seconds";
          } //seconds

        } //container window-size

      } //container crc-monitor

      container dampening {
        description
            "Configure Exponential Port Dampening";
        container half-life {
          description
              "Configure the half-life decay time, and max-suppress-time, the maximum period 
               of time for which the port-up state can be suppressed";
          leaf half-life {
            type uint32 {
              range "1..2000";
            }
            default 5;
            description
                "[1..2000] seconds - Default: 5";
          } //half-life

          leaf max-suppress-time {
            type uint32 {
              range "1..43200";
            }
            default 20;
            description
                "[1..43200] seconds - Default: 20";
          } //max-suppress-time

        } //container half-life

        leaf shutdown {
          type boolean;
          description
              "Administratively enable/disable Exponential Port Dampening on the port";
        }

        container suppress-threshold {
          description
              "Configure the penalties threshold above which the port-up state is suppressed, 
               and the reuse-threshold, which no longer suppresses the port-up state if the 
               penalties fall below the value";
          leaf suppress-penalties {
            type uint32 {
              range "1..20000";
            }
            description
                "[1..20000] - Default 2000";
          } //suppress-penalties

          leaf reuse-threshold {
            type uint32 {
              range "1..20000";
            }
            description
                "[1..20000] - Default 1000";
          } //reuse-threshold

        } //container suppress-threshold

      } //container dampening

      container dot1x {
        description
            "Configure 802.1x Authentication";
        container max-auth-req {
          description
              "Configure the maxreq used by auth state machine";
          leaf max-auth-request {
            type uint64 {
              range "1..10";
            }
          } //max-auth-request

        } //container max-auth-req

        container port-control {
          description
              "Configure controlled port Port Control";
          leaf auto-force-auth-force-unauth {
            type enumeration {
              enum auto;
              enum force-auth;
              enum force-unauth;
            }
            description
                "keyword";
          } //auto-force-auth-force-unauth

        } //container port-control

        container quiet-period {
          description
              "Configure quiet period";
          leaf seconds {
            type uint64 {
              range "1..3600";
            }
          } //seconds

        } //container quiet-period

        container radius-plcy {
          description
              "Configure an authentication server policy";
          leaf name {
            type string {
              length "1..32";
            }
          } //name

        } //container radius-plcy

        container re-auth-period {
          description
              "Configure re-authentication period";
          leaf seconds {
            type uint64 {
              range "1..9000";
            }
            description
                "[1..9000]";
          } //seconds

        } //container re-auth-period

        leaf re-authentication {
          type boolean;
          description
              "Enable/disable re-authentication";
        }

        container server-timeout {
          description
              "Configure server timeout value";
          leaf seconds {
            type uint64 {
              range "1..300";
            }
          } //seconds

        } //container server-timeout

        container supplicant-timeout {
          description
              "Configure supplicant timeout value";
          leaf seconds {
            type uint64 {
              range "1..300";
            }
          } //seconds

        } //container supplicant-timeout

        container transmit-period {
          description
              "Configure transmit period";
          leaf seconds {
            type uint64 {
              range "1..3600";
            }
          } //seconds

        } //container transmit-period

        leaf tunneling {
          type boolean;
          description
              "Enable/disable dot1x tunneling";
        }

        container macsec {
          description
              "Configure macsec settings on this port";
          container ca-name {
            status "obsolete";
            description
                "Configure the connectivity association to be used for this port";
            leaf ca-name {
              type string {
                length "1..32";
              }
            } //ca-name

          } //container ca-name

          container eapol-destination-address {
            status "obsolete";
            description
                "Configure the eapol destination address";
            leaf eapol-destination-address-id {
              type yang:mac-address;
            } //eapol-destination-address-id

          } //container eapol-destination-address

          container exclude-mac-policy {
            description
                "Configure the policy of mac addresses to be excluded";
            leaf mac-policy-id {
              type uint32;
            } //mac-policy-id

          } //container exclude-mac-policy

          container exclude-protocol {
            description
                "Configure excluded protocols for MACsec";
            leaf lacp {
              type boolean;
            } //lacp

            leaf lldp {
              type boolean;
            } //lldp

            leaf cdp {
              type boolean;
            } //cdp

            leaf eapol-start {
              type boolean;
            } //eapol-start

            leaf efm-oam {
              type boolean;
            } //efm-oam

            leaf eth-cfm {
              type boolean;
            } //eth-cfm

            leaf ptp {
              type boolean;
            } //ptp

            leaf ubfd {
              type boolean;
            } //ubfd

          } //container exclude-protocol

          container max-peer {
            status "obsolete";
            description
                "Configure the max number of peers supported on this port";
            leaf num-peers {
              type uint32 {
                range "0..32";
              }
              description
                  "[0..32]";
            } //num-peers

          } //container max-peer

          leaf rx-must-be-encrypted {
            type boolean;
            description
                "Configure if encryption is expected on Rx traffic at port level";
          }

          leaf shutdown {
            type boolean;
            status "obsolete";
            description
                "Administratively enable/disable MACsec on this port";
          }

          list sub-port {
            key "port-id";
            description
                "Configure macsec settings on this port";
            leaf port-id {
              type uint32 {
                range "1..1023";
              }
              description
                  "1..1023";
            } //port-id

            container ca-name {
              description
                  "Configure the connectivity association to be used for this port";
              leaf ca-name {
                type string {
                  length "1..32";
                }
              } //ca-name

            } //container ca-name

            container eapol-destination-address {
              description
                  "Configure the eapol destination address";
              leaf eapol-destination-address-id {
                type yang:mac-address;
              } //eapol-destination-address-id

            } //container eapol-destination-address

            container encap-match {
              description
                  "Configure encap-match for this sub-port";
              leaf all-encap {
                type boolean;
              } //all-encap

              leaf untagged {
                type boolean;
              } //untagged

              leaf single-tag {
                type boolean;
              } //single-tag

              leaf double-tag {
                type boolean;
              } //double-tag

              leaf encap-value {
                type string {
                }
                description
                    "Attribute encap-value for encap-match";
              } //encap-value

            } //container encap-match

            container max-peer {
              description
                  "Configure the max number of peers supported on this port";
              leaf num-peers {
                type uint32 {
                  range "0..32";
                }
                description
                    "[0..32]";
              } //num-peers

            } //container max-peer

            leaf shutdown {
              type boolean;
              description
                  "Administratively enable/disable MACsec on this port";
            }

          } //list sub-port

        } //container macsec

      } //container dot1x

      container down-when-looped {
        description
            "Configure ethernet loop detection attributes";
        container keep-alive {
          description
              "Configure the time interval between keep-alive PDUs";
          leaf time {
            type uint32 {
              range "1..120";
            }
            description
                "[1..120] in seconds";
          } //time

        } //container keep-alive

        container retry-timeout {
          description
              "Minimum wait time before re-enabling port after loop detection";
          leaf timeout {
            type string;
            description
                "[0|10..160] in seconds";
          } //timeout

        } //container retry-timeout

        leaf shutdown {
          type boolean;
          description
              "Administratively enable/disable physical loop detection";
        }

        leaf use-broadcast-address {
          type boolean;
          description
              "Use broadcast mac address for destination mac address";
        }

      } //container down-when-looped

      container efm-oam {
        description
            "Configure EFM OAM attributes";
        leaf accept-remote-loopback {
          type boolean;
          description
              "Enable/disable reaction to loopback control OAMPDUs";
        }

        leaf dying-gasp-tx-on-reset {
          type boolean;
          description
              "Enable/Disable EFM OAM dying gasp messages on reset";
        }

        leaf grace-tx-enable {
          type boolean;
          description
              "Enable/Disable EFM OAM grace period messages";
        }

        container grace-vendor-oui {
          description
              "Configure the EFM OAM grace vendor Organizationally Unique Identifier";
          leaf oui {
            type string {
              length "1..8";
            }
            description
                "hex value in range 00:00:00 to FF:FF:FF";
          } //oui

        } //container grace-vendor-oui

        container hold-time {
          description
              "Configure the EFM OAM hold-time";
          leaf time-value {
            type uint16 {
              range "0..50";
            }
            description
                "[0..50] seconds - Default 0";
          } //time-value

        } //container hold-time

        leaf ignore-efm-state {
          type boolean;
          description
              "Suppress port operational state changes due to EFM OAM";
        }

        container mode {
          description
              "Configure EFM OAM DTE mode";
          leaf active-passive {
            type enumeration {
              enum active;
              enum passive;
            }
            description
                "keywords";
          } //active-passive

        } //container mode

        leaf shutdown {
          type boolean;
          description
              "Enable/disable EFM OAM operation";
        }

        container transmit-interval {
          description
              "Configure transmit interval of OAMPDUs";
          leaf interval {
            type uint32 {
              range "1..600";
            }
            description
                "in 100 milliseconds [1..600]";
          } //interval

          leaf multiplier {
            type uint32 {
              range "2..5";
            }
            description
                "multiplier for transmit-interval to set local link down timer [2..5]";
          } //multiplier

        } //container transmit-interval

        container trigger-fault {
          description
              "Configure which EFM OAM fault to trigger";
          leaf trigger-fault-id {
            type enumeration {
              enum dying-gasp;
              enum critical-event;
            }
          } //trigger-fault-id

        } //container trigger-fault

        leaf tunneling {
          type boolean;
          description
              "Enable/disable EFM OAM PDU tunneling";
        }

        container discovery {
          description
              "Configure EFM OAM discovery parameters";
          container advertise-capabilities {
            description
                "Configure capabilities to advertise to a peer";
            leaf link-monitoring {
              type boolean;
              description
                  "Configure whether or not link monitoring capabilities are advertised to a peer";
            }

          } //container advertise-capabilities

        } //container discovery

        container link-monitoring {
          description
              "Configure the EFM OAM link monitoring parameters";
          leaf shutdown {
            type boolean;
            description
                "Enable/disable link monitoring";
          }

          container errored-frame {
            description
                "Configure the Errored Frame parameters";
            leaf event-notification {
              type boolean;
              description
                  "Configure if Event Notification OAMPDUs are transmitted with Errored Frame 
                   Event TLVs";
            }

            container sd-threshold {
              description
                  "Configure the Errored Frame signal degrade threshold";
              leaf errored-frames {
                type uint32 {
                  range "1..1000000";
                }
              } //errored-frames

            } //container sd-threshold

            container sf-threshold {
              description
                  "Configure the Errored Frame signal failure threshold";
              leaf errored-frames {
                type uint32 {
                  range "1..1000000";
                }
                default 1;
                description
                    "[1..1000000] - Default: 1";
              } //errored-frames

            } //container sf-threshold

            leaf shutdown {
              type boolean;
              description
                  "Enable/disable Errored Frame link monitoring on the port";
            }

            container window {
              description
                  "Configure the Errored Frame window";
              leaf deciseconds {
                type uint32 {
                  range "10..600";
                }
                default 10;
                description
                    "[10..600] increments of 10 only - Default: 10";
              } //deciseconds

            } //container window

          } //container errored-frame

          container errored-frame-period {
            description
                "Configure the Errored Frame Period parameters";
            leaf event-notification {
              type boolean;
              description
                  "Configure if Event Notification OAMPDUs are transmitted with Errored Frame 
                   Period Event TLVs";
            }

            container sd-threshold {
              description
                  "Configure the Errored Frame Period signal degrade threshold";
              leaf errored-frames {
                type uint32 {
                  range "1..1000000";
                }
              } //errored-frames

            } //container sd-threshold

            container sf-threshold {
              description
                  "Configure the Errored Frame Period signal failure threshold";
              leaf errored-frames {
                type uint32 {
                  range "1..1000000";
                }
                default 1;
                description
                    "[1..1000000] - Default: 1";
              } //errored-frames

            } //container sf-threshold

            leaf shutdown {
              type boolean;
              description
                  "Enable/disable Errored Frame Period link monitoring on the port";
            }

            container window {
              description
                  "Configure the Errored Frame Period window";
              leaf packets {
                type uint32 {
                  range "1..4294967295";
                }
                default 1488095;
                description
                    "[1..4294967295] - Default: 1488095";
              } //packets

            } //container window

          } //container errored-frame-period

          container errored-frame-seconds {
            description
                "Configure the Errored Frame Seconds Summary parameters";
            leaf event-notification {
              type boolean;
              description
                  "Configure if Event Notification OAMPDUs are transmitted with Errored Frame 
                   Seconds Summary Event TLVs";
            }

            container sd-threshold {
              description
                  "Configure the Errored Frame Seconds Summary signal degrade threshold";
              leaf errored-seconds {
                type uint32 {
                  range "1..900";
                }
              } //errored-seconds

            } //container sd-threshold

            container sf-threshold {
              description
                  "Configure the Errored Frame Seconds Summary signal failure threshold";
              leaf errored-seconds {
                type uint32 {
                  range "1..900";
                }
                default 1;
                description
                    "[1..900] - Default: 1";
              } //errored-seconds

            } //container sf-threshold

            leaf shutdown {
              type boolean;
              description
                  "Enable/disable Errored Frame Seconds Summary link monitoring on the port";
            }

            container window {
              description
                  "Configure the Errored Frame Seconds Summary window";
              leaf deciseconds {
                type uint32 {
                  range "100..9000";
                }
                default 600;
                description
                    "[100..9000] increments of 10 only - Default: 600";
              } //deciseconds

            } //container window

          } //container errored-frame-seconds

          container errored-symbols {
            description
                "Configure the Errored Symbol Period parameters";
            leaf event-notification {
              type boolean;
              description
                  "Configure if Event Notification OAMPDUs are transmitted with Errored Symbol 
                   Period Event TLVs";
            }

            container sd-threshold {
              description
                  "Configure the Errored Symbol Period signal degrade threshold";
              leaf errored-symbols {
                type uint32 {
                  range "1..1000000";
                }
              } //errored-symbols

            } //container sd-threshold

            container sf-threshold {
              description
                  "Configure the Errored Symbol Period signal failure threshold";
              leaf errored-symbols {
                type uint32 {
                  range "1..1000000";
                }
                default 1;
                description
                    "[1..1000000] - Default: 1";
              } //errored-symbols

            } //container sf-threshold

            leaf shutdown {
              type boolean;
              description
                  "Enable/disable Errored Symbol Period link monitoring on the port";
            }

            container window {
              description
                  "Configure the Errored Symbol Period window";
              leaf deciseconds {
                type uint32 {
                  range "10..600";
                }
                default 10;
                description
                    "[10..600] increments of 10 only - Default: 10";
              } //deciseconds

            } //container window

          } //container errored-symbols

          container local-sf-action {
            description
                "Configure parameters used for handling local signal failure threshold 
                 crossings";
            container event-notification-burst {
              description
                  "Configure the number of Event Notification OAMPDUs to burst";
              leaf packets {
                type uint32 {
                  range "1..5";
                }
                default 1;
                description
                    "[1..5] - Default: 1";
              } //packets

            } //container event-notification-burst

            container local-port-action {
              description
                  "Configure the local port action";
              leaf log-only-out-of-service {
                type enumeration {
                  enum log-only;
                  enum out-of-service;
                }
                default "out-of-service";
                description
                    "keywords - Default: out-of-service";
              } //log-only-out-of-service

            } //container local-port-action

            container info-notification {
              description
                  "Configure the different flags in the Information OAMPDU";
              leaf critical-event {
                type boolean;
                description
                    "Set/clear the Critical Event flag";
              }

              leaf dying-gasp {
                type boolean;
                description
                    "Set/clear the Dying Gasp flag";
              }

            } //container info-notification

          } //container local-sf-action

        } //container link-monitoring

        container peer-rdi-rx {
          description
              "Configure parameters used when a Remote Defect Indication is received from a 
               peer";
          container critical-event {
            description
                "Configure the action of the local port when a critical event is received from 
                 a peer";
            leaf local-port-action {
              type enumeration {
                enum log-only;
                enum out-of-service;
              }
              default "out-of-service";
              description
                  "keywords - Default: out-of-service";
            } //local-port-action

          } //container critical-event

          container dying-gasp {
            description
                "Configure the action of the local port when a dying gasp is received from the 
                 peer";
            leaf local-port-action {
              type enumeration {
                enum log-only;
                enum out-of-service;
              }
              default "out-of-service";
              description
                  "keywords - Default: out-of-service";
            } //local-port-action

          } //container dying-gasp

          container event-notification {
            description
                "Configure the action of the local port when an Event Notification OAMPDU is 
                 received from the peer";
            leaf local-port-action {
              type enumeration {
                enum log-only;
                enum out-of-service;
              }
              default "log-only";
              description
                  "keywords - Default: log-only";
            } //local-port-action

          } //container event-notification

          container link-fault {
            description
                "Configure the action of the local port when a link fault is received from the 
                 peer";
            leaf local-port-action {
              type enumeration {
                enum log-only;
                enum out-of-service;
              }
              default "out-of-service";
              description
                  "keywords - Default: out-of-service";
            } //local-port-action

          } //container link-fault

        } //container peer-rdi-rx

      } //container efm-oam

      container egress {
        description
            "Configure egress port parameters";
        container hs-port-pool-policy {
          description
              "Configure an egress hsq port pool policy";
          leaf policy-name {
            type string;
          } //policy-name

        } //container hs-port-pool-policy

        container hs-scheduler-policy {
          description
              "Configure an egress hsq scheduler policy";
          leaf policy-name {
            type string {
              length "1..32";
            }
          } //policy-name

        } //container hs-scheduler-policy

        list exp-secondary-shaper {
          key "secondary-shaper-name";
          description
              "Configure ethernet egress expanded secondary shaper on this port";
          leaf secondary-shaper-name {
            type string {
              length "1..32";
            }
          } //secondary-shaper-name

          list class {
            key "class-number";
            description
                "Specify the exp-secondary-shaper class";
            leaf class-number {
              type int32 {
                range "1..8";
              }
            } //class-number

            leaf rate {
              type string;
              description
                  "max|[1..10000000] Kbps";
            } //rate

            leaf monitor-threshold {
              type int32 {
                range "0..8190";
              }
            } //monitor-threshold

            leaf burst-limit {
              type uint32 {
                range "1..327680";
              }
            } //burst-limit

            leaf bytes-kilobytes {
              type enumeration {
                enum bytes;
                enum kilobytes;
              }
            } //bytes-kilobytes

          } //list class

          container low-burst-max-class {
            description
                "Specify low burst max class";
            leaf class {
              type uint32 {
                range "1..8";
              }
            } //class

          } //container low-burst-max-class

          container rate {
            description
                "Specify the exp-secondary-shaper rate";
            leaf rate {
              type string;
              description
                  "max|[1..10000000] Kbps";
            } //rate

            leaf monitor-threshold {
              type int32 {
                range "0..8190";
              }
            } //monitor-threshold

          } //container rate

          container agg-burst {
            description
                "Specify the Aggregate Burst limits";
            container high-burst-increase {
              description
                  "Specify high burst increase";
              leaf size {
                type uint32 {
                  range "0..65528";
                }
              } //size

              leaf bytes-kilobytes {
                type enumeration {
                  enum bytes;
                  enum kilobytes;
                }
              } //bytes-kilobytes

            } //container high-burst-increase

            container low-burst-limit {
              description
                  "Specify low burst limit";
              leaf size {
                type uint32 {
                  range "1..327680";
                }
              } //size

              leaf bytes-kilobytes {
                type enumeration {
                  enum bytes;
                  enum kilobytes;
                }
              } //bytes-kilobytes

            } //container low-burst-limit

          } //container agg-burst

        } //list exp-secondary-shaper

        container hs-scheduler-overrides {
          description
              "Configure a hs (high scale) scheduler overrides";
          list group {
            key "group-id";
            description
                "Configure a group rate";
            leaf group-id {
              type uint32 {
              }
              description
                  "[1]";
            } //group-id

            leaf rate {
              type string;
              description
                  "[1..100000|max] Mbps";
            } //rate

          } //list group

          container max-rate {
            description
                "Configure the maximum rate";
            leaf rate {
              type string;
              description
                  "[1..100000|max] Mbps";
            } //rate

          } //container max-rate

          list scheduling-class {
            key "class";
            description
                "Configure a scheduling class";
            leaf class {
              type int32 {
                range "1..6";
              }
            } //class

            leaf rate {
              type string;
              description
                  "[1..100000|max] Mbps";
            } //rate

            leaf weight {
              type int32 {
                range "1..127";
              }
            } //weight

          } //list scheduling-class

        } //container hs-scheduler-overrides

        list hs-secondary-shaper {
          key "secondary-shaper-name";
          description
              "Configure ethernet egress HS secondary shaper on this port";
          leaf secondary-shaper-name {
            type string {
              length "1..32";
            }
          } //secondary-shaper-name

          container description {
            description
                "Configure description for HS secondary shaper";
            leaf description-string {
              type string {
                length "1..80";
              }
            } //description-string

          } //container description

          container aggregate {
            presence
                "Configure aggregate parameters";
            container low-burst-max-class {
              description
                  "Specify low burst max class";
              leaf class {
                type uint32 {
                  range "1..6";
                }
              } //class

            } //container low-burst-max-class

            container rate {
              description
                  "Specify aggregate rate";
              leaf rate {
                type string;
                description
                    "[1..100000000|max] Kbps";
              } //rate

            } //container rate

          } //container aggregate

          list class {
            key "class-number";
            description
                "Specify the hs-secondary-shaper class";
            leaf class-number {
              type int32 {
                range "1..6";
              }
            } //class-number

            container rate {
              description
                  "Specify aggregate rate";
              leaf rate {
                type string;
                description
                    "[1..100000000|max] Kbps";
              } //rate

            } //container rate

          } //list class

        } //list hs-secondary-shaper

      } //container egress

      container egress-scheduler-override {
        description
            "Apply egress scheduler overrides";
        list level {
          key "priority-level";
          description
              "Configure priority level parameters";
          leaf priority-level {
            type uint32 {
              range "1..8";
            }
          } //priority-level

          leaf rate {
            type string;
            description
                "[1..6400000000|max] Kbps";
          } //rate

          leaf percent-rate {
            type string;
            description
                "[0.01..100.00]";
          } //percent-rate

          leaf cir {
            type string;
            description
                "[0..6400000000|max] Kbps";
          } //cir

          leaf percent-cir {
            type string;
            description
                "[0.00..100.00]";
          } //percent-cir

        } //list level

        container max-rate {
          description
              "Configure the maximum rate";
          leaf pir-rate {
            type string;
            description
                "[1..6400000000|max] Kbps";
          } //pir-rate

          leaf percent {
            type string;
            description
                "[0.01..100.00]";
          } //percent

        } //container max-rate

      } //container egress-scheduler-override

      container elmi {
        description
            "Configure Ethernet Link Management Interface attributes";
        container mode {
          description
              "Configure the Ethernet LMI Mode";
          leaf mode-id {
            type enumeration {
              enum none;
              enum uni-n;
            }
          } //mode-id

        } //container mode

        container n393 {
          description
              "Configure the monitored count of consecutive errors";
          leaf n393-id {
            type uint32 {
              range "2..10";
            }
          } //n393-id

        } //container n393

        container t391 {
          description
              "Configure Polling Timer for UNI-C";
          leaf t391-id {
            type uint32 {
              range "5..30";
            }
          } //t391-id

        } //container t391

        container t392 {
          description
              "Configure the polling verification timer for UNI-N";
          leaf t392-id {
            type uint32 {
              range "5..30";
            }
          } //t392-id

        } //container t392

      } //container elmi

      container eth-cfm {
        description
            "Configure CFM parameters";
        list mep {
          key "mep-id domain association vlan";
          description
              "Configure a CFM Facility Maintenance Endpoint";
          leaf mep-id {
            type int16 {
              range "1..8191";
            }
            description
                "Attribute mep-id for mep";
          } //mep-id

          leaf domain {
            type uint32 {
              range "1..4294967295";
            }
          } //domain

          leaf association {
            type uint32 {
              range "1..4294967295";
            }
          } //association

          leaf vlan {
            type uint32 {
              range "1..4094";
            }
          } //vlan

          leaf ccm-enable {
            type boolean;
            description
                "Enable/Disable Generation of CCM messages";
          }

          container ccm-ltm-priority {
            description
                "Configure the priority of CCM and LTM messages";
            leaf priority {
              type uint16 {
                range "0..7";
              }
              description
                  "[0..7] - Default highest priority for CCMs and LTMs transmitted by the MEP";
            } //priority

          } //container ccm-ltm-priority

          container ccm-padding-size {
            description
                "Insert additional padding in the CCM packets";
            leaf ccm-padding {
              type uint32 {
                range "3..1500";
              }
              description
                  "3..1500 octets";
            } //ccm-padding

          } //container ccm-padding-size

          container ccm-tlv-ignore {
            description
                "Enable/Disable processing of received CCM TLVs";
            leaf port-status {
              type boolean;
            } //port-status

            leaf interface-status {
              type boolean;
            } //interface-status

          } //container ccm-tlv-ignore

          leaf collect-lmm-stats {
            type boolean;
            description
                "Enable/Disable the collection of statistics for OAM-PM Loss Measurement 
                 Message (LMM) tests";
          }

          container description {
            description
                "Add/remove a text description for the MEP";
            leaf description-string {
              type string {
              }
              description
                  "[80 chars max]";
            } //description-string

          } //container description

          leaf facility-fault {
            type boolean;
            description
                "Enable/disable reaction to fault conditions on a facility MEP";
          }

          leaf install-mep {
            type boolean;
            description
                "Enable/Disable Installation of the MEP in the forwarding plane";
          }

          container low-priority-defect {
            description
                "Configure the Lowest Priority Defect for the MEP";
            leaf allDef-macRemErrXcon-remErrXcon-errXcon-xcon-noXcon {
              type enumeration {
                enum allDef;
                enum macRemErrXcon;
                enum remErrXcon;
                enum errXcon;
                enum xcon;
                enum noXcon;
              }
              description
                  "keywords";
            } //allDef-macRemErrXcon-remErrXcon-errXcon-xcon-noXcon

          } //container low-priority-defect

          container mac-address {
            description
                "Configure the MAC Address for the MEP";
            leaf mac-address {
              type yang:mac-address;
            } //mac-address

          } //container mac-address

          container one-way-delay-threshold {
            description
                "Configure the one-way-delay test threshold";
            leaf seconds {
              type uint32 {
                range "0..600";
              }
              default 3;
              description
                  "[0..600] Default: 3";
            } //seconds

          } //container one-way-delay-threshold

          leaf shutdown {
            type boolean;
            description
                "Administratively enable/disable the MEP";
          }

          container ais-enable {
            presence
                "Configure the generation and reception of Alarm Indication Signal (AIS) 
                 message parameters";
            container client-meg-level {
              description
                  "Configure the client meg level";
              leaf t1 {
                type boolean;
                description
                    "[1..7]";
              } //t1

              leaf t2 {
                type boolean;
              } //t2

              leaf t3 {
                type boolean;
              } //t3

              leaf t4 {
                type boolean;
              } //t4

              leaf t5 {
                type boolean;
              } //t5

              leaf t6 {
                type boolean;
              } //t6

              leaf t7 {
                type boolean;
              } //t7

            } //container client-meg-level

            leaf interface-support-enable {
              type boolean;
              description
                  "Enable/disable the generation of AIS PDUs based on the associated endpoint 
                   state";
            }

            container interval {
              description
                  "Configure the transmission interval of AIS messages";
              leaf t1-60 {
                type enumeration {
                  enum 1;
                  enum 60;
                }
                default 1;
                description
                    "seconds - Default: 1";
              } //t1-60

            } //container interval

            container low-priority-defect {
              description
                  "Configure the Lowest Priority Defect for the MEP AIS generation";
              leaf allDef-macRemErrXcon {
                type enumeration {
                  enum allDef;
                  enum macRemErrXcon;
                }
                description
                    "keywords";
              } //allDef-macRemErrXcon

            } //container low-priority-defect

            container priority {
              description
                  "Configure the priority of AIS messages originated by the node";
              leaf priority-value {
                type uint32 {
                  range "0..7";
                }
                default 7;
                description
                    "[0..7] - Default: 7";
              } //priority-value

            } //container priority

          } //container ais-enable

          container alarm-notification {
            description
                "Configure the MEP alarm notification parameters";
            container fng-alarm-time {
              description
                  "Configure the Fault Notification Generation (FNG) alarm time";
              leaf time {
                type enumeration {
                  enum 0;
                  enum 250;
                  enum 500;
                  enum 1000;
                }
                default 0;
                description
                    "[0,250,500,1000] centi-seconds - Default: 0";
              } //time

            } //container fng-alarm-time

            container fng-reset-time {
              description
                  "Configure the Fault Notification Generation (FNG) reset time";
              leaf time {
                type enumeration {
                  enum 0;
                  enum 250;
                  enum 500;
                  enum 1000;
                }
                default 0;
                description
                    "[0,250,500,1000] centi-seconds - Default: 0";
              } //time

            } //container fng-reset-time

          } //container alarm-notification

          container csf-enable {
            presence
                "Configure the reception of Client Signal Fail (CSF) message parameters";
            container multiplier {
              description
                  "Configure the multiplier used for timing out CSF";
              leaf multiplier-value {
                type string;
                description
                    "[0.0|2.0 .. 30.0] - Default: 3.5";
              } //multiplier-value

            } //container multiplier

          } //container csf-enable

          container eth-bn {
            description
                "Configure Ethernet Bandwidth Notification message handling";
            leaf receive {
              type boolean;
              description
                  "Enable/Disable the accepting and processing of ETH-BN messages";
            }

            container rx-update-pacing {
              description
                  "Configure the pacing of update messages to QoS";
              leaf seconds {
                type uint32 {
                  range "1..600";
                }
                default 5;
                description
                    "[1-600] - Default: 5";
              } //seconds

            } //container rx-update-pacing

          } //container eth-bn

          container eth-test-enable {
            presence
                "Enable/Disable eth-test functionality on MEP";
            container bit-error-threshold {
              description
                  "Configure the bit error trap threshold";
              leaf bit-errors {
                type uint32 {
                  range "0..11840";
                }
                default 1;
                description
                    "[0..11840] Default: 1";
              } //bit-errors

            } //container bit-error-threshold

            container test-pattern {
              description
                  "Configure the test pattern for eth-test frames";
              leaf all-zeros-all-ones {
                type enumeration {
                  enum all-zeros;
                  enum all-ones;
                }
                default "all-zeros";
                description
                    "keywords - Test pattern - default: all-zeros";
              } //all-zeros-all-ones

              leaf crc-enable {
                type boolean;
                description
                    "keyword - Generate CRC checksum";
              } //crc-enable

            } //container test-pattern

          } //container eth-test-enable

          container grace {
            description
                "Configure the generation and reception of grace period parameters";
            container eth-ed {
              description
                  "Configure the generation and reception of eth-ed grace period parameters";
              container max-rx-defect-window {
                description
                    "Configure/Disable an upper maximum defect window length; when disabled the 
                     advertised value from the peer will be used; when enabled the lower of the 
                     configured value or the advertised value from the peer will be used";
                leaf seconds {
                  type uint32 {
                    range "1..86400";
                  }
                  description
                      "[1..86400] - Default: no max-rx-defect-window";
                } //seconds

              } //container max-rx-defect-window

              container priority {
                description
                    "Configure/Disable the transmission priority value for ETH-ED PDUs; when 
                     disabled the priority value of ccm-ltm-priority associated with this MEP will 
                     be used";
                leaf priority {
                  type int32 {
                    range "0..7";
                  }
                  default 0;
                  description
                      "[0..7] - Default: no priority";
                } //priority

              } //container priority

              leaf rx-eth-ed {
                type boolean;
                description
                    "Enable/Disable the receiving and processing of ETH-ED PDUs";
              }

              leaf tx-eth-ed {
                type boolean;
                description
                    "Enable/Disable the transmission of ETH-ED PDUs";
              }

            } //container eth-ed

            container eth-vsm-grace {
              description
                  "Configure the generation and reception of sros vendor specific message (vsm) 
                   grace period parameters";
              leaf rx-eth-vsm-grace {
                type boolean;
                description
                    "Enable/Disable the receiving and processing of vendor specific message (vsm) 
                     grace period notifications";
              }

              leaf tx-eth-vsm-grace {
                type boolean;
                description
                    "Enable/Disable the transmission of vsm grace period notifications";
              }

            } //container eth-vsm-grace

          } //container grace

        } //list mep

      } //container eth-cfm

      container hsmda-scheduler-overrides {
        description
            "Configure HSMDA scheduler policy overrides";
        list group {
          key "group-id";
          description
              "Configure a group rate";
          leaf group-id {
            type int32 {
              range "1..2";
            }
            description
                "[1|2]";
          } //group-id

          leaf rate {
            type string;
            description
                "[1..100000|max] Mbps";
          } //rate

        } //list group

        container max-rate {
          description
              "Configure max rate";
          leaf rate {
            type string;
            description
                "[1..100000|max] Mbps";
          } //rate

        } //container max-rate

        list scheduling-class {
          key "class";
          description
              "Configure a scheduling class";
          leaf class {
            type int32 {
              range "1..8";
            }
          } //class

          leaf rate {
            type string;
            description
                "[1..100000|max] Mbps";
          } //rate

          leaf weight {
            type int32 {
              range "1..100";
            }
          } //weight

        } //list scheduling-class

      } //container hsmda-scheduler-overrides

      container lldp {
        description
            "Configure Link Layer Discovery Protocol parameters";
        list dest-mac {
          key "dest-mac-id";
          description
              "Configure the destination mac-address parameters";
          leaf dest-mac-id {
            type enumeration {
              enum nearest-bridge;
              enum nearest-non-tpmr;
              enum nearest-customer;
            }
          } //dest-mac-id

          container admin-status {
            description
                "Configure LLDP transmission/reception frame handling";
            leaf admin-status-id {
              type enumeration {
                enum rx;
                enum tx;
                enum tx-rx;
                enum disabled;
              }
            } //admin-status-id

          } //container admin-status

          leaf notification {
            type boolean;
            description
                "Enable/Disable LLDP notifications";
          }

          container port-id-subtype {
            description
                "Configure the encoding of the port identifier TLVs transmitted to the peer";
            leaf tx-if-alias-tx-if-name-tx-local {
              type enumeration {
                enum tx-if-alias;
                enum tx-if-name;
                enum tx-local;
              }
              default "tx-local";
              description
                  "keywords - Default: tx-local 
                   tx-if-alias (1) - transmit the ifAlias IF-MIB string 
                   tx-if-name (5) - transmit the ifName IF-MIB string 
                   tx-local (7) - transmit the interface ifIndex value 
                   ";
            } //tx-if-alias-tx-if-name-tx-local

          } //container port-id-subtype

          leaf tunnel-nearest-bridge {
            type boolean;
            description
                "Enable/Disable nearest bridge tunneling";
          }

          container tx-mgmt-address {
            description
                "Configure which management address to transmit";
            leaf system {
              type boolean;
              description
                  "keyword - System IPv4 Address";
            } //system

            leaf system-ipv6 {
              type boolean;
              description
                  "keyword - System IPv6 Address";
            } //system-ipv6

            leaf oob {
              type boolean;
              description
                  "keyword - Out of Band IPv4 Address, active CPM";
            } //oob

            leaf oob-ipv6 {
              type boolean;
              description
                  "keyword - Out of Band IPv6 Address, active CPM";
            } //oob-ipv6

          } //container tx-mgmt-address

          container tx-tlvs {
            description
                "Configure the LLDP TLVs to transmit";
            leaf port-desc {
              type boolean;
            } //port-desc

            leaf sys-name {
              type boolean;
            } //sys-name

            leaf sys-desc {
              type boolean;
            } //sys-desc

            leaf sys-cap {
              type boolean;
            } //sys-cap

          } //container tx-tlvs

        } //list dest-mac

      } //container lldp

      container network {
        description
            "Configure network port parameters";
        container accounting-policy {
          description
              "Configure the accounting policy which applies to the network port";
          leaf policy-id {
            type uint32 {
              range "1..99";
            }
          } //policy-id

        } //container accounting-policy

        leaf collect-stats {
          type boolean;
          description
              "Enable/disable the collection of statistical data";
        }

        container queue-policy {
          description
              "Configure the network policy";
          leaf name {
            type string {
              length "1..32";
            }
            default "default";
          } //name

        } //container queue-policy

        container egress {
          description
              "Configure ethernet port egress queue groups";
          list queue-group {
            key "queue-group-name instance";
            description
                "Configure ethernet port egress queue-group";
            leaf queue-group-name {
              type string {
                length "1..32";
              }
            } //queue-group-name

            leaf instance {
              type uint16 {
                range "1..65535";
              }
              description
                  "[1..65535]";
            } //instance

            list accounting-policy {
              key "acct-policy-id";
              description
                  "Configure accounting policy for the ethernet port egress queue-group";
              leaf acct-policy-id {
                type uint64 {
                  range "1..99";
                }
              } //acct-policy-id

            } //list accounting-policy

            leaf collect-stats {
              type boolean;
              description
                  "Enable/Disable collection of statistics on this queue-group";
            }

            container description {
              description
                  "Configure description for the port queue-group";
              leaf description-string {
                type string {
                  length "1..80";
                }
              } //description-string

            } //container description

            leaf hs-turbo {
              type boolean;
              description
                  "Enable/Disable HS Turbo";
            }

            container policer-control-policy {
              description
                  "Configure policer-control-policy for the QoS egress queue-group";
              leaf policy-name {
                type string {
                  length "1..32";
                }
              } //policy-name

            } //container policer-control-policy

            container scheduler-policy {
              description
                  "Configure scheduler-policy for the QoS egress queue-group";
              leaf scheduler-policy-name {
                type string {
                  length "1..32";
                }
              } //scheduler-policy-name

            } //container scheduler-policy

            container agg-rate {
              presence
                  "Configure aggregate rate limit";
              leaf limit-unused-bandwidth {
                type boolean;
                description
                    "Specify whether to enable limit unused bandwidth";
              }

              leaf queue-frame-based-accounting {
                type boolean;
                description
                    "Specify whether to enable queue frame based accounting";
              }

              container rate {
                description
                    "Specify rate limit for agg-rate";
                leaf kilobits-per-second {
                  type string;
                  description
                      "[1..3200000000|max] Kbps";
                } //kilobits-per-second

              } //container rate

            } //container agg-rate

            container queue-overrides {
              description
                  "Configure queue over-rides";
              list queue {
                key "queue-id";
                description
                    "Configure a queue";
                leaf queue-id {
                  type int32 {
                    range "1..8";
                  }
                } //queue-id

                container adaptation-rule {
                  description
                      "Specify the CIR and PIR adaptation rules";
                  leaf pir {
                    type enumeration {
                      enum max;
                      enum min;
                      enum closest;
                    }
                  } //pir

                  leaf cir {
                    type enumeration {
                      enum max;
                      enum min;
                      enum closest;
                    }
                  } //cir

                } //container adaptation-rule

                container cbs {
                  description
                      "Specify CBS rate";
                  leaf size-in-kbytes {
                    type string;
                    description
                        "Attribute size-in-kbytes for cbs";
                  } //size-in-kbytes

                } //container cbs

                container high-prio-only {
                  status "obsolete";
                  description
                      "Specify high priority only burst size";
                  leaf percent {
                    type string;
                    description
                        "[0..100 | default]";
                  } //percent

                } //container high-prio-only

                container mbs {
                  description
                      "Specify MBS rate";
                  leaf size {
                    type string;
                    description
                        "Attribute size for mbs";
                  } //size

                  leaf bytes-kilobytes {
                    type enumeration {
                      enum bytes;
                      enum kilobytes;
                    }
                    description
                        "keyword";
                  } //bytes-kilobytes

                } //container mbs

                leaf monitor-depth {
                  type boolean;
                  description
                      "Enable/Disable queue-depth monitoring";
                }

                container percent-rate {
                  description
                      "Specify Percent rates (CIR and PIR)";
                  leaf pir-percent {
                    type string;
                    description
                        "[0.01..100.00]";
                  } //pir-percent

                  leaf cir {
                    type string;
                    description
                        "[0.00..100.00]";
                  } //cir

                } //container percent-rate

                container rate {
                  description
                      "Specify rates (CIR and PIR)";
                  leaf pir-rate {
                    type string;
                    description
                        "Attribute pir-rate for rate";
                  } //pir-rate

                  leaf cir {
                    type string;
                    description
                        "Attribute cir-rate for rate";
                  } //cir

                } //container rate

                container drop-tail {
                  description
                      "Specify drop tail";
                  container low {
                    description
                        "Specify low drop-tail";
                    container percent-reduction-from-mbs {
                      description
                          "Specify low drop tail percent reduction from MBS";
                      leaf percent {
                        type string;
                        description
                            "[0..100|default]";
                      } //percent

                    } //container percent-reduction-from-mbs

                  } //container low

                } //container drop-tail

              } //list queue

            } //container queue-overrides

          } //list queue-group

        } //container egress

      } //container network

      container ssm {
        description
            "Configure Ethernet Synchronous Status Message (SSM) parameters";
        container code-type {
          description
              "Set the SSM channel to either use sonet or sdh";
          leaf code-type-id {
            type enumeration {
              enum sonet;
              enum sdh;
            }
          } //code-type-id

        } //container code-type

        leaf shutdown {
          type boolean;
          description
              "Enable/Disable SSM";
        }

        leaf tx-dus {
          type boolean;
          description
              "Enable/disable always transmit 0xF (dus/dnu) in SSM messaging channel";
        }

      } //container ssm

      container symbol-monitor {
        description
            "Configure Ethernet Symbol Monitoring parameters";
        container sd-threshold {
          description
              "Configure the Signal Degradation (SD) threshold";
          leaf threshold {
            type uint32 {
              range "1..9";
            }
          } //threshold

          leaf multiplier {
            type uint32 {
              range "1..9";
            }
          } //multiplier

        } //container sd-threshold

        container sf-threshold {
          description
              "Configure the Signal Failure (SF) threshold";
          leaf threshold {
            type uint32 {
              range "1..9";
            }
          } //threshold

          leaf multiplier {
            type uint32 {
              range "1..9";
            }
          } //multiplier

        } //container sf-threshold

        leaf shutdown {
          type boolean;
          description
              "Administratively enable/disable symbol monitoring on the port";
        }

        container window-size {
          description
              "Configure the symbol-monitor window size";
          leaf seconds {
            type uint32 {
              range "5..60";
            }
            default 10;
            description
                "[5..60] - Default: 10 seconds";
          } //seconds

        } //container window-size

      } //container symbol-monitor

    } //container ethernet

  } //grouping alu-conf-port-ethernet-r13

} //module  alu-conf-port-ethernet-r13
