module alu-conf-l3-nge-r13 {
  yang-version "1";

  namespace "urn:alcatel-lucent.com:sros:ns:yang:conf-l3-nge-r13";

  prefix "conf-l3-nge-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to enable/disable NGE on this interface on SR 
       OS based routers. 
       
       Copyright 2014-2015 Alcatel-Lucent, 2016 Nokia. All rights reserved. 
       Reproduction of this document is authorized on the condition that the 
       foregoing copyright notice is included. 
       
       This alu-conf-l3-nge-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-l3-nge-r13 {
    container group-encryption {
      presence
          "Enable/Disable NGE on this interface";
      list encryption-keygroup {
        key "direction";
        description
            "Configure the encryption keygroup for the interface";
        leaf keygroup-id {
          type string;
          description
              "Attribute keygroup-id for encryption-keygroup";
        } //keygroup-id

        leaf direction {
          type enumeration {
            enum inbound;
            enum outbound;
          }
        } //direction

      } //list encryption-keygroup

      list ip-exception {
        key "direction";
        description
            "IP filter policy which will be used to bypass encryption";
        leaf filter-id {
          type string;
          description
              "[1..65535]|<name:64 char max>";
        } //filter-id

        leaf direction {
          type enumeration {
            enum inbound;
            enum outbound;
          }
        } //direction

      } //list ip-exception

    } //container group-encryption

  } //grouping alu-conf-l3-nge-r13

} //module  alu-conf-l3-nge-r13
