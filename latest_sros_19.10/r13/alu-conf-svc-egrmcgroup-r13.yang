module alu-conf-svc-egrmcgroup-r13 {
  yang-version "1";

  namespace "urn:alcatel-lucent.com:sros:ns:yang:conf-svc-egrmcgroup-r13";

  prefix "conf-svc-egrmcgroup-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure Egress Multicast Groups on SR OS 
       based routers. 
       
       Copyright 2014-2015 Alcatel-Lucent, 2016 Nokia. All rights reserved. 
       Reproduction of this document is authorized on the condition that the 
       foregoing copyright notice is included. 
       
       This alu-conf-svc-egrmcgroup-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-svc-egrmcgroup-r13 {
    list egress-multicast-group {
      key "group-name";
      status "obsolete";
      description
          "Configure Egress Multicast Groups";
      leaf group-name {
        type string {
          length "1..32";
        }
        description
            "32 chars max";
      } //group-name

      container description {
        description
            "Description for the group";
        leaf description-string {
          type string {
            length "1..80";
          }
          description
              "80 chars max";
        } //description-string

      } //container description

      container dest-chain-limit {
        description
            "Configure Destination Chain Limit";
        leaf destinations-per-pass {
          type uint32 {
            range "1..30";
          }
        } //destinations-per-pass

      } //container dest-chain-limit

      container sap-common-requirements {
        description
            "Configure the common SAP paramters";
        container dot1q-etype {
          description
              "Configure the ethertype used for dot1q encapsulation";
          leaf t0x0600..0xffff {
            type string;
            description
                "[1536..65535] - accepts in decimal or hex";
          } //t0x0600..0xffff

        } //container dot1q-etype

        container egress-filter {
          description
              "Configure egress filter";
          leaf ip {
            type string;
            description
                "[1..65535]|<name:64 char max>";
          } //ip

          leaf mac {
            type string;
            description
                "[1..65535]|<name:64 char max>";
          } //mac

          leaf ipv6 {
            type string;
            description
                "[1..65535]|<name:64 char max>";
          } //ipv6

        } //container egress-filter

        container encap-type {
          description
              "Configure encapsulation method";
          leaf dot1q-null-qinq {
            type enumeration {
              enum dot1q;
              enum null;
              enum qinq;
            }
            description
                "keywords";
          } //dot1q-null-qinq

        } //container encap-type

        container qinq-etype {
          description
              "Configure the ethertype used for qinq encapsulation";
          leaf t0x0600..0xffff {
            type string;
            description
                "[1536..65535] - accepts in decimal or hex";
          } //t0x0600..0xffff

        } //container qinq-etype

        container qinq-fixed-tag-value {
          description
              "Configure the fixed tag value used for qinq encapsulation";
          leaf tag-value {
            type uint32 {
              range "1..4094";
            }
          } //tag-value

        } //container qinq-fixed-tag-value

      } //container sap-common-requirements

    } //list egress-multicast-group

  } //grouping alu-conf-svc-egrmcgroup-r13

} //module  alu-conf-svc-egrmcgroup-r13
