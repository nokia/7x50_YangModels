module alu-conf-router-radvert-r13 {
  yang-version "1";

  namespace "urn:alcatel-lucent.com:sros:ns:yang:conf-router-radvert-r13";

  prefix "conf-router-radvert-r13";

  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure IPV6 router advertisement on SR OS 
       based routers. 
       
       Copyright 2014-2015 Alcatel-Lucent, 2016 Nokia. All rights reserved. 
       Reproduction of this document is authorized on the condition that the 
       foregoing copyright notice is included. 
       
       This alu-conf-router-radvert-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-router-radvert-r13 {
    container router-advertisement {
      presence
          "Configure IPV6 router advertisement";
      container dns-options {
        presence
            "Set/reset DNS options for this router";
        container rdnss-lifetime {
          description
              "Maximum time the RDNSS address is valid in this router";
          leaf seconds {
            type uint32 {
              range "0..3600";
            }
            description
                "0|4-3600";
          } //seconds

          leaf infinite {
            type boolean;
          } //infinite

        } //container rdnss-lifetime

        container server {
          description
              "RDNSS server address(es) for this router";
          leaf-list ipv6-address {
            type inet:ipv6-address;
            max-elements 4;
          } //ipv6-address

        } //container server

      } //container dns-options

      list interface {
        key "ip-int-name";
        description
            "Configure router advertisement properties on an interface";
        leaf ip-int-name {
          type string {
            length "1..32";
          }
        } //ip-int-name

        container current-hop-limit {
          description
              "Configure the router to advertise the hop-limit in ICMPv6 ND Router 
               Advertisement messages";
          leaf number {
            type uint16 {
              range "0..255";
            }
          } //number

        } //container current-hop-limit

        leaf managed-configuration {
          type boolean;
          description
              "Configure the managed-config-flag to be advertised in ICMPv6 ND Router 
               Advertisement messages";
        }

        container max-advertisement-interval {
          description
              "Configure max interval between sending ICMPv6 ND Router Advertisement messages";
          leaf seconds {
            type uint32 {
              range "4..1800";
            }
          } //seconds

        } //container max-advertisement-interval

        container min-advertisement-interval {
          description
              "Configure min interval between sending ICMPv6 ND Router Advertisement messages";
          leaf seconds {
            type uint32 {
              range "3..1350";
            }
          } //seconds

        } //container min-advertisement-interval

        container mtu {
          description
              "Configure the MTU for sending packets to the router";
          leaf mtu-bytes {
            type uint32 {
              range "1280..9212";
            }
          } //mtu-bytes

          leaf mtu-bytes-1 {
            type uint32 {
              range "1280..9800";
            }
          } //mtu-bytes-1

        } //container mtu

        leaf other-stateful-configuration {
          type boolean;
          description
              "Configure the other-config-flag to be advertised in ICMPv6 ND Router 
               Advertisement messages";
        }

        container reachable-time {
          description
              "Configure how long this router should be considered reachable by other 
               hosts/nodes on the subnet";
          leaf milli-seconds {
            type uint32 {
              range "0..3600000";
            }
          } //milli-seconds

        } //container reachable-time

        container retransmit-time {
          description
              "Configure the time interval to be advertised in ICMPv6 ND Router Advertisement 
               messages";
          leaf milli-seconds {
            type uint32 {
              range "0..1800000";
            }
          } //milli-seconds

        } //container retransmit-time

        container router-lifetime {
          description
              "Configure the lifetime value that the router advertises in ICMPv6 ND Router 
               Advertisement messages";
          leaf seconds {
            type string;
            description
                "[0|4..9000]";
          } //seconds

        } //container router-lifetime

        leaf shutdown {
          type boolean;
          description
              "Command to disable router advertisement on an interface";
        }

        leaf use-virtual-mac {
          type boolean;
          description
              "Send Router Advertisement messages using VRRP virtual MAC address if virtual 
               router is master";
        }

        container dns-options {
          presence
              "Set/reset DNS options for this interface";
          leaf include-dns {
            type boolean;
            description
                "Include the RDNSS option in the router advertisement";
          }

          container rdnss-lifetime {
            description
                "Maximum time the RDNSS address is valid in this router";
            leaf seconds {
              type uint32 {
                range "0..3600";
              }
              description
                  "0|4-3600";
            } //seconds

            leaf infinite {
              type boolean;
            } //infinite

          } //container rdnss-lifetime

          container server {
            description
                "RDNSS server address(es) for this router";
            leaf-list ipv6-address {
              type inet:ipv6-address;
              max-elements 4;
            } //ipv6-address

          } //container server

        } //container dns-options

        list prefix {
          key "ipv6-prefix-prefix-length";
          description
              "Configure prefix that needs to be included in router advertisements";
          leaf ipv6-prefix-prefix-length {
            type string;
            description
                "ipv6-prefix x:x:x:x:x:x:x:x (eight 16-bit pieces) 
                 x:x:x:x:x:x:d.d.d.d 
                 x [0..FFFF]H 
                 d [0..255]D 
                 prefix-length [4..127]";
          } //ipv6-prefix-prefix-length

          leaf autonomous {
            type boolean;
            description
                "Enable/disable prefix for stateless address auto configuration";
          }

          leaf on-link {
            type boolean;
            description
                "Enable/disable prefix for onlink determination";
          }

          container preferred-lifetime {
            description
                "Configure the length of time that the prefix remains preferred";
            leaf seconds {
              type uint32 {
                range "0..4294967294";
              }
            } //seconds

            leaf infinite {
              type boolean;
            } //infinite

          } //container preferred-lifetime

          container valid-lifetime {
            description
                "Configure the length of time that the prefix is valid";
            leaf seconds {
              type uint32 {
                range "0..4294967294";
              }
            } //seconds

            leaf infinite {
              type boolean;
            } //infinite

          } //container valid-lifetime

        } //list prefix

      } //list interface

    } //container router-advertisement

  } //grouping alu-conf-router-radvert-r13

} //module  alu-conf-router-radvert-r13
