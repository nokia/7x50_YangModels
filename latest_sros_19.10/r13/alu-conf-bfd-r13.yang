module alu-conf-bfd-r13 {
  yang-version "1";

  namespace "urn:alcatel-lucent.com:sros:ns:yang:conf-bfd-r13";

  prefix "conf-bfd-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure Bidirectional Forwarding Detection 
       (BFD) on SR OS based routers. 
       
       Copyright 2014-2015 Alcatel-Lucent, 2016 Nokia. All rights reserved. 
       Reproduction of this document is authorized on the condition that the 
       foregoing copyright notice is included. 
       
       This alu-conf-bfd-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-09";

  grouping alu-conf-bfd-r13 {
    container bfd {
      description
          "Configure Bidirectional Forwarding Detection (BFD)";
      container seamless-bfd {
        description
            "Configure Seamless BFD";
        list reflector {
          key "reflector-name";
          description
              "Configure the Seamless BFD reflector";
          leaf reflector-name {
            type string {
              length "1..32";
            }
            description
                "Reflector name (max 32 characters)";
          } //reflector-name

          container description {
            description
                "Configure the description";
            leaf description-string {
              type string {
                length "1..80";
              }
            } //description-string

          } //container description

          container discriminator {
            description
                "Configure the discriminator";
            leaf discriminator {
              type uint32 {
                range "524288..526335";
              }
              description
                  "[524288..526335]";
            } //discriminator

          } //container discriminator

          container local-state {
            description
                "Configure the local state";
            leaf local-state-id {
              type enumeration {
                enum admin-down;
                enum up;
              }
            } //local-state-id

          } //container local-state

          leaf shutdown {
            type boolean;
            description
                "Enable/disable the S-BFD reflector";
          }

        } //list reflector

      } //container seamless-bfd

    } //container bfd

  } //grouping alu-conf-bfd-r13

} //module  alu-conf-bfd-r13
