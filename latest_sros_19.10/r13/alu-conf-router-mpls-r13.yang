module alu-conf-router-mpls-r13 {
  yang-version "1";

  namespace "urn:alcatel-lucent.com:sros:ns:yang:conf-router-mpls-r13";

  prefix "conf-router-mpls-r13";

  import alu-conf-router-mpls-tp-r13 {
    prefix "conf-router-mpls-tp-r13";
  }
  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure MPLS on SR OS based routers. 
       
       Copyright 2014-2015 Alcatel-Lucent, 2016 Nokia. All rights reserved. 
       Reproduction of this document is authorized on the condition that the 
       foregoing copyright notice is included. 
       
       This alu-conf-router-mpls-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-05-04";

  grouping alu-conf-router-mpls-r13 {
    container mpls {
      presence
          "Configure MPLS";
      leaf admin-group-frr {
        type boolean;
        description
            "Enable/Disable administrative groups for FRR path computation";
      }

      container auto-bandwidth-multipliers {
        description
            "Configure auto-bandwidth multipliers";
        leaf sample-multiplier {
          type uint32 {
            range "1..511";
          }
          description
              "[1..511]";
        } //sample-multiplier

        leaf adjust-multiplier {
          type uint32 {
            range "1..16383";
          }
          description
              "[1..16383]";
        } //adjust-multiplier

      } //container auto-bandwidth-multipliers

      list auto-lsp {
        key "lsp-template";
        description
            "Configure auto creation of an RSVP mesh LSP";
        leaf lsp-template {
          type string {
            length "1..32";
          }
        } //lsp-template

        leaf-list policy {
          type string {
            length "1..32";
          }
          max-elements 5;
        } //policy

        leaf one-hop {
          type boolean;
        } //one-hop

      } //list auto-lsp

      container aux-stats {
        description
            "Configure the counting of the specified labeled traffic type in the MPLS 
             auxiliary statistics table.";
        leaf-list traffic-type {
          type enumeration {
            enum sr;
          }
          max-elements 1;
        } //traffic-type

      } //container aux-stats

      container bypass-resignal-timer {
        description
            "Configure the bypass resignal timer for the MPLS instance";
        leaf minutes {
          type uint32 {
            range "30..10080";
          }
        } //minutes

      } //container bypass-resignal-timer

      leaf cspf-on-loose-hop {
        type boolean;
        description
            "Enable/Disable CSPF calculation till the next loose hop on LSR";
      }

      container dynamic-bypass {
        description
            "Enable/Disable dynamic-bypass tunnels";
        leaf enable-disable {
          type enumeration {
            enum enable;
            enum disable;
          }
          description
              "keywords";
        } //enable-disable

      } //container dynamic-bypass

      container entropy-label {
        description
            "Configure Entropy Label for MPLS";
        leaf rsvp-te {
          type enumeration {
            enum force-disable;
            enum enable;
          }
          description
              "<force-disable | enable>";
        } //rsvp-te

        leaf sr-te {
          type enumeration {
            enum force-disable;
            enum enable;
          }
          description
              "<force-disable | enable>";
        } //sr-te

      } //container entropy-label

      leaf exponential-backoff-retry {
        type boolean;
        description
            "Enable/disable exponential backoff retry mechanism";
      }

      leaf frr-object {
        type boolean;
        description
            "Enable/disable signalling with fast-reroute object";
      }

      container hold-timer {
        description
            "Enable/disable hold-timer";
        leaf seconds {
          type uint32 {
            range "0..10";
          }
        } //seconds

      } //container hold-timer

      container least-fill-min-thd {
        description
            "Configure the least fill minimum threshold value";
        leaf percent {
          type uint32 {
            range "1..100";
          }
        } //percent

      } //container least-fill-min-thd

      container least-fill-reoptim-thd {
        description
            "Configure the least fill reoptimization threshold value";
        leaf percent {
          type uint32 {
            range "1..100";
          }
        } //percent

      } //container least-fill-reoptim-thd

      leaf logger-event-bundling {
        type boolean;
        description
            "Enable/Disable logger event bundling mechanism";
      }

      container lsp-init-retry-timeout {
        description
            "Configure LSP initial retry timeout";
        leaf seconds {
          type uint32 {
            range "10..600";
          }
        } //seconds

      } //container lsp-init-retry-timeout

      container max-bypass-associations {
        description
            "Configure max-bypass-associations";
        leaf number {
          type uint32 {
            range "100..131072";
          }
        } //number

      } //container max-bypass-associations

      container max-bypass-plr-associations {
        description
            "Configure Max Bypass PLR Associations";
        leaf max-bypass-plr-associations-id {
          type uint32 {
            range "1..16";
          }
        } //max-bypass-plr-associations-id

      } //container max-bypass-plr-associations

      leaf mbb-prefer-current-hops {
        type boolean;
        description
            "Enable/Disable mbb preference for current hops for the MPLS instance";
      }

      container p2mp-resignal-timer {
        description
            "Configure the resignal timer for P2MP Lsps in the MPLS instance";
        leaf minutes {
          type uint32 {
            range "60..10080";
          }
        } //minutes

      } //container p2mp-resignal-timer

      container p2mp-s2l-fast-retry {
        description
            "Configure fast retry timer for P2MP S2L paths";
        leaf seconds {
          type uint32 {
            range "1..10";
          }
        } //seconds

      } //container p2mp-s2l-fast-retry

      container p2p-active-path-fast-retry {
        description
            "Configure fast retry timer for P2P active paths";
        leaf seconds {
          type uint32 {
            range "1..10";
          }
        } //seconds

      } //container p2p-active-path-fast-retry

      container pce-report {
        description
            "Configure Pce Report Types for MPLS";
        leaf sr-te {
          type enumeration {
            enum enable;
            enum disable;
          }
          description
              "<enable | disable >";
        } //sr-te

        leaf rsvp-te {
          type enumeration {
            enum enable;
            enum disable;
          }
          description
              "<enable | disable>";
        } //rsvp-te

      } //container pce-report

      container resignal-timer {
        description
            "Configure the resignal timer for RSVP-TE LSPs for the MPLS instance";
        leaf minutes {
          type uint32 {
            range "30..10080";
          }
        } //minutes

      } //container resignal-timer

      leaf retry-on-igp-overload {
        type boolean;
        description
            "Enable/disable tearing down LSPs when IGP is in overload state.";
      }

      container secondary-fast-retry-timer {
        description
            "Configure fast retry timer for secondary paths";
        leaf seconds {
          type uint32 {
            range "1..10";
          }
        } //seconds

      } //container secondary-fast-retry-timer

      leaf shortcut-local-ttl-propagate {
        type boolean;
        description
            "Enable/disable TTL propagation over LSP shortcut for local packets";
      }

      leaf shortcut-transit-ttl-propagate {
        type boolean;
        description
            "Enable/disable TTL propagation over LSP shortcut for transit packets";
      }

      leaf shutdown {
        type boolean;
        description
            "Administratively enable/disable the MPLS instance";
      }

      container srlg-frr {
        description
            "Enable/disable SRLG for FRR path computation";
        leaf strict {
          type boolean;
        } //strict

      } //container srlg-frr

      container static-lsp-fast-retry {
        description
            "Configure static LSP Fast Retry Timer.";
        leaf seconds {
          type uint32 {
            range "1..30";
          }
          description
              "[1..30]";
        } //seconds

      } //container static-lsp-fast-retry

      container user-srlg-db {
        description
            "Enable/Disable use of user SRLG database";
        leaf enable-disable {
          type enumeration {
            enum enable;
            enum disable;
          }
          description
              "keywords";
        } //enable-disable

      } //container user-srlg-db

      list class-forwarding-policy {
        key "policy-name";
        description
            "Configure Class Forwarding Policy in MPLS";
        leaf policy-name {
          type string {
            length "1..32";
          }
        } //policy-name

        container default-set {
          description
              "Configures default forwarding set";
          leaf set-id {
            type string;
            description
                "Attribute set-id for default-set";
          } //set-id

        } //container default-set

        list fc {
          key "fc";
          description
              "Configures forwarding set for each forwarding class";
          leaf fc {
            type enumeration {
              enum be;
              enum l2;
              enum af;
              enum l1;
              enum h2;
              enum ef;
              enum h1;
              enum nc;
            }
          } //fc

          leaf forwarding-set {
            type string;
            description
                "Attribute set-id for fc";
          } //forwarding-set

        } //list fc

      } //list class-forwarding-policy

      container forwarding-policies {
        presence
            "Configure MPLS Forwarding Policies.";
        container reserved-label-block {
          description
              "Configure reserved label block used by MPLS forwarding policies.";
          leaf name {
            type string {
              length "1..64";
            }
          } //name

        } //container reserved-label-block

        leaf shutdown {
          type boolean;
          description
              "Administratively enable/disable MPLS forwarding-policies.";
        }

        list forwarding-policy {
          key "name";
          description
              "Configure Forwarding Policy.";
          leaf name {
            type string {
              length "1..64";
            }
          } //name

          container binding-label {
            description
                "Configure binding label.";
            leaf label-number {
              type uint32 {
                range "32..1048575";
              }
            } //label-number

          } //container binding-label

          container endpoint {
            description
                "Configure endpoint address.";
            leaf ip-address {
              type inet:ip-address;
              description
                  "Attribute ip-address for endpoint";
            } //ip-address

          } //container endpoint

          container metric {
            description
                "Configure metric";
            leaf metric {
              type uint32 {
                range "1..16777215";
              }
            } //metric

          } //container metric

          container preference {
            description
                "Configure preference";
            leaf preference-value {
              type uint32 {
                range "1..255";
              }
            } //preference-value

          } //container preference

          container revert-timer {
            description
                "Configure revert timer.";
            leaf seconds {
              type uint16 {
                range "1..600";
              }
            } //seconds

          } //container revert-timer

          leaf shutdown {
            type boolean;
            description
                "Administratively enable/disable forwarding-policy.";
          }

          container tunnel-table-pref {
            description
                "Configure tunnel table preference";
            leaf preference-value {
              type uint32 {
                range "1..255";
              }
            } //preference-value

          } //container tunnel-table-pref

          container egress-statistics {
            presence
                "Configure egress-statistics for forwarding policy.";
            leaf shutdown {
              type boolean;
              description
                  "Administratively enable/disable egress-statistics.";
            }

          } //container egress-statistics

          container ingress-statistics {
            presence
                "Configure ingress-statistics for forwarding policy.";
            leaf shutdown {
              type boolean;
              description
                  "Administratively enable/disable ingress-statistics.";
            }

          } //container ingress-statistics

          list next-hop-group {
            key "index";
            description
                "Configure next-hop-group for forwarding policy.";
            leaf index {
              type uint8 {
                range "1..32";
              }
            } //index

            leaf resolution-type {
              type enumeration {
                enum direct;
                enum indirect;
              }
            } //resolution-type

            container load-balancing-weight {
              description
                  "Configure load balancing weight.";
              leaf weight {
                type uint64 {
                  range "1..4294967295";
                }
                description
                    "[1..4294967295] Default - 0";
              } //weight

            } //container load-balancing-weight

            leaf shutdown {
              type boolean;
              description
                  "Administratively enable/disable next-hop-group.";
            }

            container backup-next-hop {
              presence
                  "Configure backup next-hop.";
              container next-hop {
                description
                    "Configure next-hop address.";
                leaf ip-address {
                  type inet:ip-address;
                  description
                      "Attribute ip-address for next-hop";
                } //ip-address

              } //container next-hop

              container pushed-labels {
                description
                    "Configure push-labels";
                leaf-list label {
                  type uint32 {
                    range "1..1048575";
                  }
                  max-elements 10;
                } //label

              } //container pushed-labels

            } //container backup-next-hop

            container primary-next-hop {
              presence
                  "Configure primary next-hop.";
              container next-hop {
                description
                    "Configure next-hop address.";
                leaf ip-address {
                  type inet:ip-address;
                  description
                      "Attribute ip-address for next-hop";
                } //ip-address

              } //container next-hop

              container pushed-labels {
                description
                    "Configure push-labels";
                leaf-list label {
                  type uint32 {
                    range "1..1048575";
                  }
                  max-elements 10;
                } //label

              } //container pushed-labels

            } //container primary-next-hop

          } //list next-hop-group

        } //list forwarding-policy

      } //container forwarding-policies

      container ingress-statistics {
        description
            "Configure MPLS LSP Ingress statistics";
        list lsp {
          key "lsp-name sender";
          description
              "Configure LSP";
          leaf lsp-name {
            type string {
              length "1..64";
            }
            description
                "[Max 64 chars]";
          } //lsp-name

          leaf sender {
            type inet:ip-address;
            description
                "[a.b.c.d]";
          } //sender

          container accounting-policy {
            description
                "Configure accounting policy id";
            leaf policy-id {
              type uint32 {
                range "1..99";
              }
            } //policy-id

          } //container accounting-policy

          leaf collect-stats {
            type boolean;
            description
                "Enable/Disable collection of statistics";
          }

          leaf shutdown {
            type boolean;
            description
                "Administratively enable/disable mpls ingress statistics";
          }

        } //list lsp

        list p2mp-template-lsp {
          key "rsvp-session-name sender";
          description
              "Configure p2mp template lsp statistics";
          leaf rsvp-session-name {
            type string {
              length "1..64";
            }
            description
                "[Max 64 chars]";
          } //rsvp-session-name

          leaf sender {
            type inet:ip-address;
            description
                "[a.b.c.d]";
          } //sender

          container accounting-policy {
            description
                "Configure accounting policy id";
            leaf policy-id {
              type uint32 {
                range "1..99";
              }
            } //policy-id

          } //container accounting-policy

          leaf collect-stats {
            type boolean;
            description
                "Enable/Disable collection of statistics";
          }

          container max-stats {
            description
                "Configure to limit the maximum number of stat indices";
            leaf integer {
              type int32 {
                range "1..8191";
              }
              description
                  "[1..8191]";
            } //integer

          } //container max-stats

          leaf shutdown {
            type boolean;
            description
                "Administratively enable/disable mpls ingress statistics";
          }

        } //list p2mp-template-lsp

        list p2p-template-lsp {
          key "rsvp-session-name sender";
          description
              "Configure p2p template lsp statistics";
          leaf rsvp-session-name {
            type string {
              length "1..64";
            }
            description
                "[Max 64 chars]";
          } //rsvp-session-name

          leaf sender {
            type inet:ip-address;
            description
                "[a.b.c.d]";
          } //sender

          container accounting-policy {
            description
                "Configure accounting policy id";
            leaf policy-id {
              type uint32 {
                range "1..99";
              }
            } //policy-id

          } //container accounting-policy

          leaf collect-stats {
            type boolean;
            description
                "Enable/Disable collection of statistics";
          }

          container max-stats {
            description
                "Configure to limit the maximum number of stat indices";
            leaf max-stats-id {
              type int32 {
                range "1..8191";
              }
              description
                  "[1..8191]";
            } //max-stats-id

          } //container max-stats

          leaf shutdown {
            type boolean;
            description
                "Administratively enable/disable mpls ingress statistics";
          }

        } //list p2p-template-lsp

      } //container ingress-statistics

      list interface {
        key "ip-int-name";
        description
            "Configure MPLS on an IP interface";
        leaf ip-int-name {
          type string {
            length "1..32";
          }
        } //ip-int-name

        container admin-group {
          description
              "Associate administrative groups with the interface";
          leaf-list group-name {
            type string {
              length "1..32";
            }
            max-elements 5;
            description
                "[32 char max]";
          } //group-name

        } //container admin-group

        leaf shutdown {
          type boolean;
          description
              "Administratively enable/disable MPLS on the interface";
        }

        container srlg-group {
          description
              "Associate an RSVP interface to a SRLG group (max of 64 groups can be 
               associated)";
          leaf-list group-name {
            type string {
              length "1..32";
            }
            max-elements 5;
            description
                "[32 char max]";
          } //group-name

        } //container srlg-group

        container te-metric {
          description
              "Configure te-metric used on the interface";
          leaf value {
            type uint32 {
              range "1..16777215";
            }
          } //value

        } //container te-metric

        list label-map {
          key "in-label";
          description
              "Create/delete a label-map for the interface";
          leaf in-label {
            type string;
            description
                "Attribute in-label for label-map";
          } //in-label

          leaf pop {
            type boolean;
            description
                "Enable/disable the pop action on the incoming label";
          }

          leaf shutdown {
            type boolean;
            description
                "Administratively enable/disable the label-map definition";
          }

          container swap {
            description
                "Enable/disable the swap action on the incoming label";
            leaf out-label {
              type uint32 {
                range "16..1048575";
              }
            } //out-label

            leaf nexthop {
              type inet:ip-address;
            } //nexthop

            leaf implicit-null-label {
              type boolean;
              description
                  "keyword";
            } //implicit-null-label

          } //container swap

        } //list label-map

        container mpls-tp-mep {
          presence
              "Configure MPLS-TP MEP parameters for this interface";
          leaf ais-enable {
            type boolean;
            description
                "Enable/Disable the Alarm Indication Signal";
          }

          container if-num {
            description
                "Configure the MPLS-TP interface number";
            leaf if-num {
              type uint32 {
                range "1..4294967295";
              }
            } //if-num

          } //container if-num

          container if-num-validation {
            description
                "Enable/Disable the validation of the ingress and egress interface numbers 
                 received on this interface";
            leaf enable-disable {
              type enumeration {
                enum enable;
                enum disable;
              }
            } //enable-disable

          } //container if-num-validation

        } //container mpls-tp-mep

      } //list interface

      list lsp {
        key "lsp-name";
        description
            "Creates an LSP that will be signaled dynamically";
        leaf lsp-name {
          type string;
          description
              "Attribute lsp-name for lsp";
        } //lsp-name

        leaf bypass-only {
          type boolean;
        } //bypass-only

        leaf p2mp-lsp {
          type boolean;
        } //p2mp-lsp

        leaf mpls-tp {
          type uint32 {
            range "1..61440";
          }
        } //mpls-tp

        leaf sr-te {
          type boolean;
        } //sr-te

        leaf adaptive {
          type boolean;
          description
              "Enable/disable make-before-break functionality for the LSP";
        }

        list admin-tag {
          key "tag";
          description
              "Configure admin-tags for LSP.";
          leaf tag {
            type string {
              length "1..32";
            }
          } //tag

        } //list admin-tag

        leaf adspec {
          type boolean;
          description
              "Enable/disable inclusion of ADSPEC objects in RSVP messages";
        }

        leaf bgp-shortcut {
          type boolean;
          description
              "Include/exclude use of this LSP for BGP routes";
        }

        container bgp-transport-tunnel {
          description
              "Include/exclude use of this LSP as transport LSP for labeled BGP routes";
          leaf include-exclude {
            type enumeration {
              enum include;
              enum exclude;
            }
            description
                "keywords";
          } //include-exclude

        } //container bgp-transport-tunnel

        container class-type {
          description
              "Configure class-type for the LSP";
          leaf ct-number {
            type uint16 {
              range "0..7";
            }
          } //ct-number

        } //container class-type

        container cspf {
          description
              "Enable/disable CSPF support for the LSP";
          leaf use-te-metric {
            type boolean;
          } //use-te-metric

        } //container cspf

        container dest-global-id {
          description
              "Destination global id for MPLS-TP Static LSP";
          leaf dest-global-id {
            type uint32;
          } //dest-global-id

        } //container dest-global-id

        container dest-tunnel-number {
          description
              "Destination tunnel number for MPLS-TP Static LSP";
          leaf dest-tunnel-num {
            type uint32 {
              range "1..61440";
            }
          } //dest-tunnel-num

        } //container dest-tunnel-number

        container entropy-label {
          description
              "Configure Entropy Label on LSP";
          leaf force-disable---inherit---enable {
            type enumeration {
              enum force-disable;
              enum inherit;
              enum enable;
            }
          } //force-disable---inherit---enable

        } //container entropy-label

        container exclude {
          description
              "Configure administrative groups that should be excluded when the LSP is setup";
          leaf-list group-name {
            type string {
              length "1..32";
            }
            max-elements 5;
            description
                "[32 char max]";
          } //group-name

        } //container exclude

        container exclude-node {
          description
              "Configure exclude node";
          leaf ip-address {
            type inet:ip-address;
          } //ip-address

        } //container exclude-node

        container from {
          description
              "IP address of the ingress router for the LSP";
          leaf ip-address {
            type inet:ip-address;
            description
                "Attribute ip-address for from";
          } //ip-address

        } //container from

        container hop-limit {
          description
              "Max number of hops that an LSP can traverse including ingress and egress 
               routers";
          leaf number {
            type uint16 {
              range "2..255";
            }
          } //number

        } //container hop-limit

        container igp-shortcut {
          description
              "Enable/disable use of LSP as IGP shortcut";
          leaf lfa-protect {
            type boolean;
          } //lfa-protect

          leaf lfa-only {
            type boolean;
          } //lfa-only

          leaf relative-metric {
            type boolean;
          } //relative-metric

          leaf offset {
            type int32 {
              range "-10..10";
            }
          } //offset

        } //container igp-shortcut

        container include {
          description
              "Configure administrative groups that should be included when the LSP is setup";
          leaf-list group-name {
            type string {
              length "1..32";
            }
            max-elements 5;
            description
                "[32 char max]";
          } //group-name

        } //container include

        leaf label-stack-reduction {
          type boolean;
          description
              "Enable/Disable Label Stack Reduction on LSP";
        }

        container ldp-over-rsvp {
          description
              "Configure if this LSP will be included in LDP over RSVP";
          leaf include-exclude {
            type enumeration {
              enum include;
              enum exclude;
            }
            description
                "keywords";
          } //include-exclude

        } //container ldp-over-rsvp

        leaf least-fill {
          type boolean;
          description
              "Configure use of least-fill path selection method";
        }

        container load-balancing-weight {
          description
              "Configure load balancing weight for this LSP.";
          leaf weight {
            type uint32;
            default 0;
            description
                "[0..4294967295] Default - 0";
          } //weight

        } //container load-balancing-weight

        container local-sr-protection {
          description
              "Configure local-sr-protection for LSP";
          leaf local-sr-protection {
            type enumeration {
              enum none;
              enum preferred;
              enum mandatory;
            }
          } //local-sr-protection

        } //container local-sr-protection

        container lsp-self-ping {
          description
              "Configure lsp-self-ping";
          leaf lsp-self-ping {
            type enumeration {
              enum enable;
              enum disable;
              enum inherit;
            }
            default "inherit";
          } //lsp-self-ping

        } //container lsp-self-ping

        container main-ct-retry-limit {
          description
              "Max number of attempts before switching to backup class type";
          leaf number {
            type uint64 {
              range "0..10000";
            }
            description
                "[0...10000]";
          } //number

        } //container main-ct-retry-limit

        container max-sr-labels {
          description
              "Configure Max Segment Route Labels for this LSP";
          leaf label-stack-size {
            type string;
            description
                "Attribute label-stack-size for max-sr-labels";
          } //label-stack-size

          leaf additional-frr-labels {
            type uint32 {
              range "0..4";
            }
          } //additional-frr-labels

        } //container max-sr-labels

        container metric {
          description
              "Configure LSP metric";
          leaf metric {
            type string;
            description
                "<0..16777215>";
          } //metric

        } //container metric

        container metric-type {
          description
              "Configure metric type for LSP";
          leaf metric-type {
            type enumeration {
              enum igp;
              enum te;
            }
          } //metric-type

        } //container metric-type

        container p2mp-id {
          description
              "Configure P2MP identifier";
          leaf id {
            type uint16;
          } //id

        } //container p2mp-id

        container path-computation-method {
          description
              "Configure Path Computation Method on LSP";
          leaf path-computation-method {
            type enumeration {
              enum local-cspf;
              enum pce;
            }
          } //path-computation-method

        } //container path-computation-method

        list path-profile {
          key "profile-id";
          description
              "Configure Path Profile for the LSP";
          leaf profile-id {
            type uint32 {
              range "1..4294967295";
            }
          } //profile-id

          leaf path-group {
            type uint32;
          } //path-group

        } //list path-profile

        leaf pce-computation {
          type boolean;
          description
              "Configure PCE Computation on LSP";
        }

        leaf pce-control {
          type boolean;
          description
              "Configure PCE Control on LSP";
        }

        container pce-report {
          description
              "Configure PCE Report on LSP";
          leaf enable---disable---inherit {
            type enumeration {
              enum enable;
              enum disable;
              enum inherit;
            }
          } //enable---disable---inherit

        } //container pce-report

        leaf propagate-admin-group {
          type boolean;
          description
              "Enable/Disable admin groups via session attribute object";
        }

        container retry-limit {
          description
              "Max number of attempts made to reestablish the LSP after it has failed";
          leaf number {
            type uint16 {
              range "0..10000";
            }
          } //number

        } //container retry-limit

        container retry-timer {
          description
              "Time between attempts to reestablish the LSP after it has failed";
          leaf seconds {
            type uint32 {
              range "1..600";
            }
          } //seconds

        } //container retry-timer

        container revert-timer {
          description
              "Configure revert timer for this LSP.";
          leaf minutes {
            type uint32 {
              range "1..4320";
            }
          } //minutes

        } //container revert-timer

        container rsvp-resv-style {
          description
              "RSVP reservation style - shared-explicit(se) or fixed-filter(ff)";
          leaf se-ff {
            type enumeration {
              enum se;
              enum ff;
            }
            description
                "keywords";
          } //se-ff

        } //container rsvp-resv-style

        leaf shutdown {
          type boolean;
          description
              "Administratively enable/disable the LSP";
        }

        container to {
          description
              "IP address of the egress router for the LSP";
          leaf ip-address {
            type inet:ip-address;
            description
                "Attribute ip-address for to";
          } //ip-address

          leaf node-id {
            type string {
              length "1..15";
            }
            description
                "a.b.c.d|<1..4294967295>";
          } //node-id

        } //container to

        container vprn-auto-bind {
          description
              "Configure if this LSP will be included in auto-bind for VPRN";
          leaf include-exclude {
            type enumeration {
              enum include;
              enum exclude;
            }
            description
                "keywords";
          } //include-exclude

        } //container vprn-auto-bind

        container auto-bandwidth {
          presence
              "Enable/Disable Auto-Bandwidth for LSP";
          container adjust-down {
            description
                "Configure adjust down bandwidth for LSP";
            leaf percent {
              type uint32 {
                range "0..100";
              }
              description
                  "[0..100]";
            } //percent

            leaf bw {
              type string;
              description
                  "Attribute rate-in-mbps for adjust-down";
            } //bw

          } //container adjust-down

          container adjust-up {
            description
                "Configure adjust up for auto-bandwidth for LSP";
            leaf percent {
              type uint32 {
                range "0..100";
              }
              description
                  "[0..100]";
            } //percent

            leaf bw {
              type string;
              description
                  "Attribute rate-in-mbps for adjust-up";
            } //bw

          } //container adjust-up

          list fc {
            key "fc-name";
            description
                "Configure sampling weights for forwarding-class subsets for auto-bandwidth for 
                 LSP";
            leaf fc-name {
              type enumeration {
                enum be;
                enum l2;
                enum af;
                enum l1;
                enum h2;
                enum ef;
                enum h1;
                enum nc;
              }
            } //fc-name

            leaf sampling-weight {
              type uint32 {
                range "0..100";
              }
            } //sampling-weight

          } //list fc

          container max-bandwidth {
            description
                "Configure maximum bandwidth for auto-bandwidth for LSP";
            leaf rate-in-mbps {
              type string;
              description
                  "Attribute rate-in-mbps for max-bandwidth";
            } //rate-in-mbps

          } //container max-bandwidth

          container min-bandwidth {
            description
                "Configure minimum bandwidth for auto-bandwidth for LSP";
            leaf rate-in-mbps {
              type string;
              description
                  "Attribute rate-in-mbps for min-bandwidth";
            } //rate-in-mbps

          } //container min-bandwidth

          leaf monitor-bandwidth {
            type boolean;
            description
                "Enable/disable monitor bandwidth for auto-bandwidth for LSP";
          }

          container multipliers {
            description
                "Configure sample and adjust multiplier for auto-bandwidth for LSP";
            leaf sample-multiplier {
              type uint32 {
                range "1..511";
              }
              description
                  "[1..511]";
            } //sample-multiplier

            leaf adjust-multiplier {
              type uint32 {
                range "1..16383";
              }
              description
                  "[1..16383]";
            } //adjust-multiplier

          } //container multipliers

          container overflow-limit {
            description
                "Configure overflow limit for auto-bandwidth for LSP";
            leaf number {
              type uint32 {
                range "1..10";
              }
              description
                  "[1..10]";
            } //number

            leaf threshold {
              type uint32 {
                range "0..100";
              }
              description
                  "[0..100]";
            } //threshold

            leaf bw {
              type string;
              description
                  "Attribute rate-in-mbps for overflow-limit";
            } //bw

          } //container overflow-limit

          container underflow-limit {
            description
                "Configure underflow limit for auto-bandwidth for LSP";
            leaf number {
              type uint32 {
                range "1..10";
              }
              description
                  "[1..10]";
            } //number

            leaf threshold {
              type uint32 {
                range "0..100";
              }
              description
                  "[0..100]";
            } //threshold

            leaf bw {
              type string;
              description
                  "Attribute rate-in-mbps for underflow-limit";
            } //bw

          } //container underflow-limit

          container use-last-adj-bw {
            description
                "Enable/disable use of last adjusted bandwidth for LSP";
            leaf secondary-retry-limit {
              type boolean;
            } //secondary-retry-limit

            leaf number {
              type uint32 {
                range "1..10000";
              }
              description
                  "[1..10000] - default 5";
            } //number

            leaf infinite {
              type boolean;
            } //infinite

          } //container use-last-adj-bw

        } //container auto-bandwidth

        container bfd {
          description
              "Configure BFD for MPLS LSP";
          leaf bfd-enable {
            type boolean;
            description
                "Enable/Disable BFD for MPLS LSP";
          }

          container bfd-template {
            description
                "Configure the Bidirectional Forwarding Detection (BFD) template";
            leaf name {
              type string {
                length "1..32";
              }
            } //name

          } //container bfd-template

          container failure-action {
            description
                "Configure BFD LSP Failure Action";
            leaf failure-action {
              type enumeration {
                enum down;
                enum failover;
                enum failover-or-down;
              }
              description
                  "Attribute failure-action for failure-action";
            } //failure-action

          } //container failure-action

          container lsp-ping-interval {
            description
                "Configure LSP ping interval for BFD bootstrapping";
            leaf seconds {
              type string;
              description
                  "0|60-300";
            } //seconds

          } //container lsp-ping-interval

          container wait-for-up-timer {
            description
                "Configure BFD wait for up timer";
            leaf wait-for-up-timer-id {
              type uint32 {
                range "1..60";
              }
            } //wait-for-up-timer-id

          } //container wait-for-up-timer

        } //container bfd

        container class-forwarding {
          presence
              "Enables/Disables class based forwarding over this LSP";
          leaf default-lsp {
            type boolean;
            description
                "Enables/Disables use of this LSP as the default forwarding LSP";
          }

          list fc {
            key "fc";
            description
                "Configures one or more forwarding classes for this LSP";
            leaf fc {
              type enumeration {
                enum be;
                enum l2;
                enum af;
                enum l1;
                enum h2;
                enum ef;
                enum h1;
                enum nc;
              }
            } //fc

          } //list fc

          container forwarding-set {
            description
                "Configures class forwarding policy and set for this LSP";
            leaf policy {
              type string {
                length "1..32";
              }
            } //policy

            leaf set {
              type string;
              description
                  "Attribute set-id for forwarding-set";
            } //set

          } //container forwarding-set

        } //container class-forwarding

        container egress-statistics {
          presence
              "Configure LSP Egress statistics";
          container accounting-policy {
            description
                "Configure accounting policy id";
            leaf policy-id {
              type uint32 {
                range "1..99";
              }
            } //policy-id

          } //container accounting-policy

          leaf collect-stats {
            type boolean;
            description
                "Enable/Disable collection of statistics";
          }

          leaf shutdown {
            type boolean;
            description
                "Administratively enable/disable the LSP egress statistics";
          }

        } //container egress-statistics

        container fast-reroute {
          description
              "Configure fast reroute for LSP";
          leaf frr-method {
            type enumeration {
              enum one-to-one;
              enum facility;
            }
            description
                "one-to-one|facility - keywords";
          } //frr-method

          container hop-limit {
            description
                "Configure hop limit for fast reroute";
            leaf limit {
              type uint16 {
                range "0..255";
              }
            } //limit

          } //container hop-limit

          leaf node-protect {
            type boolean;
            description
                "Configure node protect";
          }

          leaf propagate-admin-group {
            type boolean;
            description
                "Configure admin-group propagation";
          }

        } //container fast-reroute

        container ingress-statistics {
          presence
              "Configure LSP Ingress statistics";
          container accounting-policy {
            description
                "Configure accounting policy id";
            leaf policy-id {
              type uint32 {
                range "1..99";
              }
            } //policy-id

          } //container accounting-policy

          leaf collect-stats {
            type boolean;
            description
                "Enable/Disable collection of statistics";
          }

          leaf shutdown {
            type boolean;
            description
                "Administratively enable/disable the LSP ingress statistics";
          }

        } //container ingress-statistics

        list primary {
          key "path-name";
          description
              "Configure a preferred path for the LSP";
          leaf path-name {
            type string;
          } //path-name

          leaf adaptive {
            type boolean;
            description
                "Enable/Disable make-before-break functionality for the LSP path";
          }

          container backup-class-type {
            description
                "Configure backup class-type for the LSP path";
            leaf ct-number {
              type uint32 {
                range "0..7";
              }
              description
                  "[0..7]";
            } //ct-number

          } //container backup-class-type

          container bandwidth {
            description
                "Amount of bandwidth to be reserved for the path";
            leaf rate-in-mbps {
              type string;
              description
                  "Attribute rate-in-mbps for bandwidth";
            } //rate-in-mbps

          } //container bandwidth

          container class-type {
            description
                "Configure class-type for the LSP path";
            leaf ct-number {
              type uint16 {
                range "0..7";
              }
            } //ct-number

          } //container class-type

          container exclude {
            description
                "Configure administrative groups that should be excluded when the LSP path is 
                 setup";
            leaf-list group-name {
              type string {
                length "1..32";
              }
              max-elements 5;
              description
                  "[32 char max]";
            } //group-name

          } //container exclude

          container hop-limit {
            description
                "Max number of hops that an LSP will traverse including ingress and egress 
                 routers - overrides LSP hop-limit";
            leaf number {
              type uint16 {
                range "2..255";
              }
            } //number

          } //container hop-limit

          container include {
            description
                "Configure administrative groups that should be included when the LSP path is 
                 setup";
            leaf-list group-name {
              type string {
                length "1..32";
              }
              max-elements 5;
              description
                  "[32 char max]";
            } //group-name

          } //container include

          container priority {
            description
                "Configure setup and hold priority";
            leaf setup-priority {
              type uint16 {
                range "0..7";
              }
              default 7;
            } //setup-priority

            leaf hold-priority {
              type uint16 {
                range "0..7";
              }
            } //hold-priority

          } //container priority

          leaf record {
            type boolean;
            description
                "Enable/disable recording of all hops that an LSP path traverses";
          }

          leaf record-label {
            type boolean;
            description
                "Enable/disable recording of recording of labels at each node that an LSP path 
                 traverses";
          }

          leaf shutdown {
            type boolean;
            description
                "Administratively enable/disable the LSP path";
          }

          container bfd {
            description
                "Configure BFD for MPLS primary LSP";
            leaf bfd-enable {
              type boolean;
              description
                  "Enable/Disable BFD for MPLS primary LSP";
            }

            container bfd-template {
              description
                  "Configure the Bidirectional Forwarding Detection (BFD) template";
              leaf name {
                type string {
                  length "1..32";
                }
              } //name

            } //container bfd-template

            container lsp-ping-interval {
              description
                  "Configure LSP ping interval for BFD bootstrapping";
              leaf seconds {
                type string;
                description
                    "0|60-300";
              } //seconds

            } //container lsp-ping-interval

            container wait-for-up-timer {
              description
                  "Configure BFD Wait for Up Timer";
              leaf seconds {
                type uint32 {
                  range "1..60";
                }
              } //seconds

            } //container wait-for-up-timer

          } //container bfd

        } //list primary

        list primary-p2mp-instance {
          key "instance-name";
          description
              "Creates a P2MP primary instance for LSP";
          leaf instance-name {
            type string {
              length "1..32";
            }
          } //instance-name

          leaf adaptive {
            type boolean;
            description
                "Enable/Disable make-before-break functionality for the primary P2MP instance";
          }

          container bandwidth {
            description
                "Amount of bandwidth to be reserved for the P2MP instance";
            leaf rate-in-mbps {
              type string;
              description
                  "Attribute rate-in-mbps for bandwidth";
            } //rate-in-mbps

          } //container bandwidth

          container exclude {
            description
                "Configure administrative groups that should be excluded when the P2MP instance 
                 is setup";
            leaf-list group-name {
              type string {
                length "1..32";
              }
              max-elements 5;
              description
                  "[32 char max]";
            } //group-name

          } //container exclude

          container hop-limit {
            description
                "Max number of hops that an P2MP instance will traverse including ingress and 
                 egress routers - overrides LSP hop-limit";
            leaf number {
              type uint16 {
                range "2..255";
              }
            } //number

          } //container hop-limit

          container include {
            description
                "Configure administrative groups that should be included when the P2MP instance 
                 is setup";
            leaf-list group-name {
              type string {
                length "1..32";
              }
              max-elements 5;
              description
                  "[32 char max]";
            } //group-name

          } //container include

          leaf record {
            type boolean;
            description
                "Enable/disable recording of all hops that a P2MP instance traverses";
          }

          leaf record-label {
            type boolean;
            description
                "Enable/disable recording of labels at each node that a P2MP instance traverses";
          }

          leaf shutdown {
            type boolean;
            description
                "Administratively enable/disable the P2MP instance";
          }

          list s2l-path {
            key "path-name to";
            description
                "Configure a S2L sub LSP";
            leaf path-name {
              type string;
            } //path-name

            leaf to {
              type inet:ip-address;
              description
                  "[a.b.c.d]";
            } //to

            leaf shutdown {
              type boolean;
              description
                  "Administratively enable/disable the S2L path";
            }

          } //list s2l-path

        } //list primary-p2mp-instance

        container protect-tp-path {
          presence
              "Configure the protection Transport-Profile (TP) path";
          container in-label {
            description
                "Configure the protect-tp-path in-label";
            leaf label {
              type string;
              description
                  "Attribute label for in-label";
            } //label

          } //container in-label

          container lsp-num {
            description
                "Configure the protect-tp-path lsp-number";
            leaf lsp-number {
              type uint32 {
                range "1..65535";
              }
            } //lsp-number

          } //container lsp-num

          container out-label {
            description
                "Configure the protect-tp-path out-label";
            leaf out-label {
              type uint32 {
                range "16..1048575";
              }
            } //out-label

            leaf out-link {
              type string {
                length "1..32";
              }
            } //out-link

            leaf next-hop {
              type string;
              description
                  "[a.b.c.d]";
            } //next-hop

          } //container out-label

          leaf shutdown {
            type boolean;
            description
                "Administratively enable/disable the LSP protect-tp-path";
          }

          container mep {
            presence
                "Configure the protect-tp-path Maintenance Endpoint (MEP) parameters";
            container bfd-enable {
              description
                  "Enable/Disable Bidirectional Forwarding Detection (BFD) on the MEP";
              leaf bfd-mode {
                type enumeration {
                  enum cc;
                  enum cc-cv;
                }
              } //bfd-mode

            } //container bfd-enable

            leaf bfd-trap-suppression {
              type boolean;
              description
                  "Enable/Disable BFD trap suppression";
            }

            container dsmap {
              description
                  "Configure the DSMAP for the MEP";
              leaf if-num {
                type string;
                description
                    "<in-if-num>[:<out-if-num>] 
                     <in-if-num> - [0..4294967295] - Default: 0 
                     <out-if-num> - [0..4294967295] - Default: 0";
              } //if-num

            } //container dsmap

            container oam-template {
              description
                  "Configure the MEP's OAM template";
              leaf oam-template-string {
                type string {
                  length "1..32";
                }
              } //oam-template-string

            } //container oam-template

            container protection-template {
              description
                  "Configure the MPLS-TP protection template";
              leaf protection-template-string {
                type string {
                }
              } //protection-template-string

            } //container protection-template

            leaf shutdown {
              type boolean;
              description
                  "Administratively enable/disable the LSP protection path MEP";
            }

          } //container mep

        } //container protect-tp-path

        list secondary {
          key "path-name";
          description
              "Configure an alternate path for the LSP if the primary path is not available";
          leaf path-name {
            type string;
          } //path-name

          leaf adaptive {
            type boolean;
            description
                "Enable/Disable make-before-break functionality for the LSP path";
          }

          container bandwidth {
            description
                "Amount of bandwidth to be reserved for the path";
            leaf rate-in-mbps {
              type string;
              description
                  "Attribute rate-in-mbps for bandwidth";
            } //rate-in-mbps

          } //container bandwidth

          container class-type {
            description
                "Configure class-type for the LSP path";
            leaf class-type {
              type uint16 {
                range "0..7";
              }
            } //class-type

          } //container class-type

          container exclude {
            description
                "Configure administrative groups that should be excluded when the LSP path is 
                 setup";
            leaf-list group-name {
              type string {
                length "1..32";
              }
              max-elements 5;
              description
                  "[32 char max]";
            } //group-name

          } //container exclude

          container hop-limit {
            description
                "Max number of hops that an LSP will traverse including ingress and egress 
                 routers - overrides LSP hop-limit";
            leaf number {
              type uint16 {
                range "2..255";
              }
            } //number

          } //container hop-limit

          container include {
            description
                "Configure administrative groups that should be included when the LSP path is 
                 setup";
            leaf-list group-name {
              type string {
                length "1..32";
              }
              max-elements 5;
              description
                  "[32 char max]";
            } //group-name

          } //container include

          container path-preference {
            description
                "Configure path preference for the secondary path";
            leaf preference-number {
              type uint32 {
                range "1..255";
              }
              description
                  "[1..255]";
            } //preference-number

          } //container path-preference

          container priority {
            description
                "Configure setup and hold priority";
            leaf setup-priority {
              type uint16 {
                range "0..7";
              }
              default 7;
            } //setup-priority

            leaf hold-priority {
              type uint16 {
                range "0..7";
              }
            } //hold-priority

          } //container priority

          leaf record {
            type boolean;
            description
                "Enable/disable recording of all hops that an LSP path traverses";
          }

          leaf record-label {
            type boolean;
            description
                "Enable/disable recording of recording of labels at each node that an LSP path 
                 traverses";
          }

          leaf shutdown {
            type boolean;
            description
                "Administratively enable/disable the LSP path";
          }

          leaf srlg {
            type boolean;
            description
                "Enable/Disable SRLG for the secondary LSP path computation";
          }

          leaf standby {
            type boolean;
            description
                "Enable standby to ensure that secondary path is signaled and maintained in a 
                 hot-standby";
          }

          container bfd {
            description
                "Configure BFD for MPLS Secondary LSP";
            leaf bfd-enable {
              type boolean;
              description
                  "Enable/Disable BFD for MPLS secondary LSP";
            }

            container bfd-template {
              description
                  "Configure the Bidirectional Forwarding Detection (BFD) template";
              leaf name {
                type string {
                  length "1..32";
                }
              } //name

            } //container bfd-template

            container lsp-ping-interval {
              description
                  "Configure LSP ping interval for BFD bootstrapping";
              leaf seconds {
                type string;
                description
                    "0|60-300";
              } //seconds

            } //container lsp-ping-interval

            container wait-for-up-timer {
              description
                  "Configure Secondary BFD Wait for Up Timer";
              leaf seconds {
                type uint32 {
                  range "1..60";
                }
              } //seconds

            } //container wait-for-up-timer

          } //container bfd

        } //list secondary

        container working-tp-path {
          presence
              "Configure the working Transport-Profile (TP) path";
          container in-label {
            description
                "Configure the working-tp-path in-label";
            leaf label {
              type string;
              description
                  "Attribute label for in-label";
            } //label

          } //container in-label

          container lsp-num {
            description
                "Configure the working-tp-path lsp-number";
            leaf lsp-number {
              type uint32 {
                range "1..65535";
              }
            } //lsp-number

          } //container lsp-num

          container out-label {
            description
                "Configure the working-tp-path out-label";
            leaf out-label {
              type uint32 {
                range "16..1048575";
              }
            } //out-label

            leaf out-link {
              type string {
                length "1..32";
              }
            } //out-link

            leaf next-hop {
              type string;
              description
                  "[a.b.c.d]";
            } //next-hop

          } //container out-label

          leaf shutdown {
            type boolean;
            description
                "Administratively enable/disable the LSP working-tp-path";
          }

          container mep {
            presence
                "Configure the working-tp-path Maintenance Endpoint (MEP) parameters";
            container bfd-enable {
              description
                  "Enable/Disable Bidirectional Forwarding Detection (BFD) on the MEP";
              leaf bfd-mode {
                type enumeration {
                  enum cc;
                  enum cc-cv;
                }
              } //bfd-mode

            } //container bfd-enable

            leaf bfd-trap-suppression {
              type boolean;
              description
                  "Enable/Disable BFD trap suppression";
            }

            container dsmap {
              description
                  "Configure the DSMAP for the MEP";
              leaf if-num {
                type string;
                description
                    "<in-if-num>[:<out-if-num>] 
                     <in-if-num> - [0..4294967295] - Default: 0 
                     <out-if-num> - [0..4294967295] - Default: 0";
              } //if-num

            } //container dsmap

            container oam-template {
              description
                  "Configure the MEP's OAM template";
              leaf oam-template-string {
                type string {
                  length "1..32";
                }
              } //oam-template-string

            } //container oam-template

            leaf shutdown {
              type boolean;
              description
                  "Administratively enable/disable the LSP working path MEP";
            }

          } //container mep

        } //container working-tp-path

      } //list lsp

      container lsp-self-ping {
        presence
            "Configure lsp self ping.";
        container interval {
          description
              "Configure lsp-self-ping interval.";
          leaf seconds {
            type uint64 {
              range "1..10";
            }
            default 1;
          } //seconds

        } //container interval

        container rsvp-te {
          description
              "Configure lsp-self-ping rsvp-te.";
          leaf rsvp-te {
            type enumeration {
              enum enable;
              enum disable;
            }
            default "disable";
          } //rsvp-te

        } //container rsvp-te

        container timeout {
          description
              "Configure lsp-self-ping timeout.";
          leaf seconds {
            type uint32 {
              range "3..3600";
            }
            default 300;
          } //seconds

        } //container timeout

        container timeout-action {
          description
              "Configure lsp-self-ping timeout-action";
          leaf timeout-action {
            type enumeration {
              enum retry;
              enum switch;
            }
            default "retry";
          } //timeout-action

        } //container timeout-action

      } //container lsp-self-ping

      list lsp-template {
        key "template-name";
        description
            "Creates an LSP Template that will be referenced when dynamic LSP creation is 
             required";
        leaf template-name {
          type string {
            length "1..32";
          }
        } //template-name

        leaf p2mp {
          type boolean;
        } //p2mp

        leaf mesh-p2p {
          type boolean;
        } //mesh-p2p

        leaf one-hop-p2p {
          type boolean;
        } //one-hop-p2p

        leaf one-hop-p2p-srte {
          type boolean;
        } //one-hop-p2p-srte

        leaf mesh-p2p-srte {
          type boolean;
        } //mesh-p2p-srte

        leaf pce-init-p2p-srte {
          type boolean;
        } //pce-init-p2p-srte

        leaf template-id {
          type string;
          description
              "default | 1...4294967295";
        } //template-id

        leaf adaptive {
          type boolean;
          description
              "Enable/disable make-before-break functionality for LSP instances created using 
               this LSP template";
        }

        list admin-tag {
          key "tag";
          description
              "Configure an admin-tag for LSP-Template.";
          leaf tag {
            type string {
              length "1..32";
            }
          } //tag

        } //list admin-tag

        leaf adspec {
          type boolean;
          description
              "Enable/disable inclusion of ADSPEC objects in RSVP messages";
        }

        container backup-class-type {
          description
              "Configure backup-class-type for this LSP template";
          leaf ct-number {
            type uint16 {
              range "0..7";
            }
          } //ct-number

        } //container backup-class-type

        container bandwidth {
          description
              "Specify bandwidth in mbps for LSP instances created using this LSP template";
          leaf rate-in-mbps {
            type string;
            description
                "Attribute rate-in-mbps for bandwidth";
          } //rate-in-mbps

        } //container bandwidth

        leaf bgp-shortcut {
          type boolean;
          description
              "Include/exclude use of RSVP LSP template for IPv4 BGP routes";
        }

        container bgp-transport-tunnel {
          description
              "Include/exclude use of RSVP LSP as transport LSP for labeled IPv4 BGP routes";
          leaf include-exclude {
            type enumeration {
              enum include;
              enum exclude;
            }
            description
                "keywords";
          } //include-exclude

        } //container bgp-transport-tunnel

        container class-type {
          description
              "Configure class-type for this LSP template";
          leaf ct-number {
            type uint16 {
              range "0..7";
            }
          } //ct-number

        } //container class-type

        container cspf {
          description
              "Enable/disable CSPF support for LSP instances created using this LSP template";
          leaf use-te-metric {
            type boolean;
          } //use-te-metric

        } //container cspf

        container default-path {
          description
              "Specify default path to be used for signaling LSP instances created using this 
               LSP template";
          leaf path-name {
            type string;
          } //path-name

        } //container default-path

        container entropy-label {
          description
              "Configure Entropy label on this LSP Template instance";
          leaf force-disable---inherit---enable {
            type enumeration {
              enum force-disable;
              enum inherit;
              enum enable;
            }
          } //force-disable---inherit---enable

        } //container entropy-label

        container exclude {
          description
              "Configure administrative groups that should be excluded for signaling LSP 
               instances created using this LSP template";
          leaf-list group-name {
            type string {
              length "1..32";
            }
            max-elements 5;
            description
                "[32 char max]";
          } //group-name

        } //container exclude

        container from {
          description
              "IP address of the ingress router for the LSP template";
          leaf ip-address {
            type inet:ip-address;
          } //ip-address

        } //container from

        container hop-limit {
          description
              "Configure maximum number of hops that can be traversed by LSP instances 
               created using this LSP template";
          leaf number {
            type uint16 {
              range "2..255";
            }
          } //number

        } //container hop-limit

        container igp-shortcut {
          description
              "Enable/disable use of RSVP LSP template as IGP shortcut for IPv4 routes";
          leaf lfa-protect {
            type boolean;
          } //lfa-protect

          leaf lfa-only {
            type boolean;
          } //lfa-only

          leaf relative-metric {
            type boolean;
          } //relative-metric

          leaf offset {
            type int32 {
              range "-10..10";
            }
          } //offset

        } //container igp-shortcut

        container include {
          description
              "Configure administrative groups that should be included for signaling LSP 
               instances created using this LSP template";
          leaf-list group-name {
            type string {
              length "1..32";
            }
            max-elements 5;
            description
                "[32 char max]";
          } //group-name

        } //container include

        leaf label-stack-reduction {
          type boolean;
          description
              "Enable/Disable Label Stack Reduction on LSP Template";
        }

        container ldp-over-rsvp {
          description
              "Configure if this LSP template will be included in LDP over RSVP";
          leaf include-exclude {
            type enumeration {
              enum include;
              enum exclude;
            }
            description
                "keywords";
          } //include-exclude

        } //container ldp-over-rsvp

        leaf least-fill {
          type boolean;
          description
              "Configure use of least-fill path selection method created using this LSP 
               template";
        }

        container load-balancing-weight {
          description
              "Configure load balancing weight for this LSP template.";
          leaf weight {
            type uint32;
            default 0;
            description
                "[0..4294967295] Default - 0";
          } //weight

        } //container load-balancing-weight

        container local-sr-protection {
          description
              "Configure local-sr-protection for LSP Template";
          leaf local-sr-protection {
            type enumeration {
              enum none;
              enum preferred;
              enum mandatory;
            }
          } //local-sr-protection

        } //container local-sr-protection

        container lsp-self-ping {
          description
              "Configure lsp self ping.";
          leaf lsp-self-ping {
            type enumeration {
              enum enable;
              enum disable;
              enum inherit;
            }
            default "inherit";
          } //lsp-self-ping

        } //container lsp-self-ping

        container main-ct-retry-limit {
          description
              "Max number of attempts before switching to backup class type";
          leaf number {
            type uint64;
            description
                "[0..10000]";
          } //number

        } //container main-ct-retry-limit

        container max-sr-labels {
          description
              "Configure Max Segment Route Labels for this LSP template";
          leaf label-stack-size {
            type string;
            description
                "Attribute label-stack-size for max-sr-labels";
          } //label-stack-size

          leaf additional-frr-labels {
            type uint32 {
              range "0..4";
            }
          } //additional-frr-labels

        } //container max-sr-labels

        container metric {
          description
              "Configure mpls lsp-template metric";
          leaf metric {
            type string;
            description
                "<0..16777215>";
          } //metric

        } //container metric

        container metric-type {
          description
              "Configure metric type on LSP Template";
          leaf metric-type {
            type enumeration {
              enum igp;
              enum te;
            }
          } //metric-type

        } //container metric-type

        container path-computation-method {
          description
              "Configure Path Computation Method on LSP Template";
          leaf path-computation-method {
            type enumeration {
              enum local-cspf;
            }
          } //path-computation-method

        } //container path-computation-method

        container pce-report {
          description
              "Configure Pce-Report on this LSP Template instance";
          leaf enable---inherit---disable {
            type enumeration {
              enum enable;
              enum inherit;
              enum disable;
            }
          } //enable---inherit---disable

        } //container pce-report

        container priority {
          description
              "Setup and hold priorities for the LSP template";
          leaf setup-priority {
            type uint16 {
              range "0..7";
            }
            default 7;
          } //setup-priority

          leaf hold-priority {
            type uint16 {
              range "0..7";
            }
          } //hold-priority

        } //container priority

        leaf propagate-admin-group {
          type boolean;
          description
              "Enable/Disable admin groups via session attribute object";
        }

        leaf record {
          type boolean;
          description
              "Enable/Disable recording of all hops for LSP instances created using this LSP 
               template";
        }

        leaf record-label {
          type boolean;
          description
              "Enable/Disable recording of all labels for LSP instances created using this 
               LSP template";
        }

        container retry-limit {
          description
              "Configure maximum number of attempts that will be made to establish LSP 
               instances created using this LSP template";
          leaf number {
            type uint16 {
              range "0..10000";
            }
          } //number

        } //container retry-limit

        container retry-timer {
          description
              "Configure time between attempts to reestablish LSP instances created using 
               this LSP template";
          leaf seconds {
            type uint32 {
              range "1..600";
            }
          } //seconds

        } //container retry-timer

        leaf shutdown {
          type boolean;
          description
              "Administratively enable/disable the LSP Template";
        }

        container vprn-auto-bind {
          description
              "Configure if this LSP template will be included in auto-bind for vprn";
          leaf include-exclude {
            type enumeration {
              enum include;
              enum exclude;
            }
            description
                "keywords";
          } //include-exclude

        } //container vprn-auto-bind

        container auto-bandwidth {
          presence
              "Enable/Disable Auto-Bandwidth for LSP template";
          list adjust-down {
            key "percent bw";
            description
                "Configure adjust down bandwidth for LSP template";
            leaf percent {
              type uint32 {
                range "0..100";
              }
              description
                  "[0..100]";
            } //percent

            leaf bw {
              type string;
              description
                  "Attribute rate-in-mbps for adjust-down";
            } //bw

          } //list adjust-down

          container adjust-up {
            description
                "Configure adjust up bandwidth for LSP template";
            leaf percent {
              type uint32 {
                range "0..100";
              }
              description
                  "[0..100]";
            } //percent

            leaf bw {
              type string;
              description
                  "Attribute rate-in-mbps for adjust-up";
            } //bw

          } //container adjust-up

          list fc {
            key "fc-name";
            description
                "Configure sampling weights for forwarding-class subsets for auto-bandwidth for 
                 LSP template";
            leaf fc-name {
              type enumeration {
                enum be;
                enum l2;
                enum af;
                enum l1;
                enum h2;
                enum ef;
                enum h1;
                enum nc;
              }
            } //fc-name

            leaf sampling-weight {
              type uint32 {
                range "0..100";
              }
            } //sampling-weight

          } //list fc

          container max-bandwidth {
            description
                "Configure maximum bandwidth for auto-bandwidth for LSP template";
            leaf rate-in-mbps {
              type string;
              description
                  "Attribute rate-in-mbps for max-bandwidth";
            } //rate-in-mbps

          } //container max-bandwidth

          container min-bandwidth {
            description
                "Configure minimum bandwidth for auto-bandwidth for LSP template";
            leaf rate-in-mbps {
              type string;
              description
                  "Attribute rate-in-mbps for min-bandwidth";
            } //rate-in-mbps

          } //container min-bandwidth

          leaf monitor-bandwidth {
            type boolean;
            description
                "Enable/disable monitor bandwidth for auto-bandwidth for LSP template";
          }

          container multipliers {
            description
                "Configure sample and adjust multiplier for auto-bandwidth for LSP template";
            leaf sample-multiplier {
              type uint32 {
                range "1..511";
              }
              description
                  "[1..511]";
            } //sample-multiplier

            leaf adjust-multiplier {
              type uint32 {
                range "1..16383";
              }
              description
                  "[1..16383]";
            } //adjust-multiplier

          } //container multipliers

          container overflow-limit {
            description
                "Configure overflow limit for auto-bandwidth for LSP template";
            leaf number {
              type uint32 {
                range "1..10";
              }
              description
                  "[1..10]";
            } //number

            leaf threshold {
              type uint32 {
                range "0..100";
              }
              description
                  "[0..100]";
            } //threshold

            leaf bw {
              type string;
              description
                  "Attribute rate-in-mbps for overflow-limit";
            } //bw

          } //container overflow-limit

          container underflow-limit {
            description
                "Configure underflow limit for auto-bandwidth for LSP template";
            leaf number {
              type uint32 {
                range "1..10";
              }
              description
                  "[1..10]";
            } //number

            leaf threshold {
              type uint32 {
                range "0..100";
              }
              description
                  "[0..100]";
            } //threshold

            leaf bw {
              type string;
              description
                  "Attribute rate-in-mbps for underflow-limit";
            } //bw

          } //container underflow-limit

        } //container auto-bandwidth

        container bfd {
          description
              "Configure BFD for MPLS LSP Template";
          leaf bfd-enable {
            type boolean;
            description
                "Enable/Disable BFD for MPLS LSP Template";
          }

          container bfd-template {
            description
                "Configure the Bidirectional Forwarding Detection (BFD) template";
            leaf name {
              type string {
                length "1..32";
              }
            } //name

          } //container bfd-template

          container failure-action {
            description
                "Configure BFD LSP Template Failure Action";
            leaf down---failover-or-down {
              type enumeration {
                enum down;
                enum failover;
                enum failover-or-down;
              }
            } //down---failover-or-down

          } //container failure-action

          container lsp-ping-interval {
            description
                "Configure LSP ping interval for BFD bootstrapping";
            leaf seconds {
              type string;
              description
                  "0|60-300";
            } //seconds

          } //container lsp-ping-interval

          container wait-for-up-timer {
            description
                "Configure BFD Wait For Up Timer";
            leaf seconds {
              type uint32 {
                range "1..60";
              }
            } //seconds

          } //container wait-for-up-timer

        } //container bfd

        container class-forwarding {
          presence
              "Enables/Disables class based forwarding over instances created using this LSP 
               template";
          leaf default-lsp {
            type boolean;
            description
                "Enables/Disables use of LSP instances created using this LSP template as the 
                 default forwarding LSP";
          }

          list fc {
            key "fc";
            description
                "Configures one or more forwarding classes for LSP instances created using this 
                 LSP template";
            leaf fc {
              type enumeration {
                enum be;
                enum l2;
                enum af;
                enum l1;
                enum h2;
                enum ef;
                enum h1;
                enum nc;
              }
            } //fc

          } //list fc

          container forwarding-set {
            description
                "Configures class forwarding policy and set for this LSP Template";
            leaf policy {
              type string {
                length "1..32";
              }
            } //policy

            leaf set {
              type string;
              description
                  "Attribute set-id for forwarding-set";
            } //set

          } //container forwarding-set

        } //container class-forwarding

        container egress-statistics {
          presence
              "Configure LSP template Egress statistics";
          container accounting-policy {
            description
                "Configure accounting policy id";
            leaf policy-id {
              type uint32 {
                range "1..99";
              }
            } //policy-id

          } //container accounting-policy

          leaf collect-stats {
            type boolean;
            description
                "Enable/Disable collection of statistics";
          }

        } //container egress-statistics

        container fast-reroute {
          description
              "Configure fast reroute for LSP instances created using this LSP template";
          leaf frr-method {
            type enumeration {
              enum one-to-one;
              enum facility;
            }
            description
                "one-to-one|facility - keywords";
          } //frr-method

          container hop-limit {
            description
                "Configure hop limit for fast reroute";
            leaf limit {
              type uint16 {
                range "0..255";
              }
            } //limit

          } //container hop-limit

          leaf node-protect {
            type boolean;
            description
                "Configure node protect";
          }

          leaf propagate-admin-group {
            type boolean;
            description
                "Configure admin-group propagation";
          }

        } //container fast-reroute

      } //list lsp-template

      uses "conf-router-mpls-tp-r13:alu-conf-router-mpls-tp-r13";
      list path {
        key "path-name";
        description
            "Configure the path to be used for a LSP";
        leaf path-name {
          type string;
        } //path-name

        list hop {
          key "hop-index";
          description
              "Configure the IP address or SID Label of the hops that the LSP should traverse 
               on its way to the egress";
          leaf hop-index {
            type uint32 {
              range "1..1024";
            }
          } //hop-index

          leaf ip-address {
            type inet:ip-address;
            description
                "Attribute ip-address for hop";
          } //ip-address

          leaf strict-loose {
            type enumeration {
              enum strict;
              enum loose;
            }
            description
                "keywords";
          } //strict-loose

          leaf sid-label {
            type uint32 {
              range "32..1048575";
            }
          } //sid-label

        } //list hop

        leaf shutdown {
          type boolean;
          description
              "Administratively enable/disable the LSP path";
        }

      } //list path

      container pce-initiated-lsp {
        presence
            "Configure MPLS PCE Initiated LSP";
        container sr-te {
          presence
              "Configure PCE Initialted LSP SR-TE";
          leaf shutdown {
            type boolean;
            description
                "Configure PCE Init LSP SRTE Shutdown";
          }

        } //container sr-te

      } //container pce-initiated-lsp

      container sr-te-resignal {
        description
            "Configure resignal events for the MPLS SR-TE LSP instance";
        leaf resignal-on-igp-event {
          type boolean;
          description
              "Enable/disable capability to resignal SR-TE LSPs on an IGP event";
        }

        container resignal-timer {
          description
              "Configure the resignal timer for the MPLS SR-TE LSP instance";
          leaf minutes {
            type uint32 {
              range "30..10080";
            }
          } //minutes

        } //container resignal-timer

      } //container sr-te-resignal

      container srlg-database {
        presence
            "Configure the SRLG database";
        list router-id {
          key "ip-address";
          description
              "Configure router-id for SRLG database";
          leaf ip-address {
            type inet:ip-address;
            description
                "[a.b.c.d]";
          } //ip-address

          list interface {
            key "ip-address";
            description
                "Configure interface for router-id under SRLG database";
            leaf ip-address {
              type inet:ip-address;
              description
                  "[a.b.c.d]";
            } //ip-address

            leaf-list srlg-group {
              type string {
                length "1..32";
              }
              max-elements 5;
              description
                  "[Max 32 chars]";
            } //srlg-group

          } //list interface

          leaf shutdown {
            type boolean;
            description
                "Configure admin state for router-id";
          }

        } //list router-id

      } //container srlg-database

      list static-lsp {
        key "lsp-name";
        description
            "Configure a static LSP on the ingress router";
        leaf lsp-name {
          type string;
          description
              "Attribute lsp-name for static-lsp";
        } //lsp-name

        container metric {
          description
              "Configure mpls static-lsp metric";
          leaf metric {
            type uint32 {
              range "0..16777215";
            }
            description
                "<0..16777215>";
          } //metric

        } //container metric

        container push {
          description
              "Label to be pushed on the label stack and the next hop IP address";
          leaf label {
            type uint32 {
              range "16..1048575";
            }
          } //label

          leaf nexthop {
            type inet:ip-address;
          } //nexthop

          leaf implicit-null-label {
            type boolean;
            description
                "keyword";
          } //implicit-null-label

        } //container push

        leaf shutdown {
          type boolean;
          description
              "Administratively enable/disable the static LSP";
        }

        container to {
          description
              "IP address of the egress router for the static LSP";
          leaf ip-address {
            type inet:ip-address;
          } //ip-address

        } //container to

      } //list static-lsp

    } //container mpls

  } //grouping alu-conf-router-mpls-r13

} //module  alu-conf-router-mpls-r13
