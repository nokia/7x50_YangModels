module alu-conf-router-pcep-r13 {
  yang-version "1";

  namespace "urn:alcatel-lucent.com:sros:ns:yang:conf-router-pcep-r13";

  prefix "conf-router-pcep-r13";

  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure Path Computation Element 
       communications Protocol (PCEP) on SR OS based routers. 
       
       Copyright 2014-2015 Alcatel-Lucent, 2016 Nokia. All rights reserved. 
       Reproduction of this document is authorized on the condition that the 
       foregoing copyright notice is included. 
       
       This alu-conf-router-pcep-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-26";

  grouping alu-conf-router-pcep-r13 {
    container pcep {
      description
          "Configure Path Computation Element communications Protocol (PCEP)";
      container pcc {
        presence
            "Configure Path Computation Client (PCC) parameters";
        container dead-timer {
          description
              "Configure dead timer interval for PCC";
          leaf seconds {
            type uint32 {
              range "1..255";
            }
            description
                "[1..255] - Default 120";
          } //seconds

        } //container dead-timer

        container keepalive {
          description
              "Configure keepalive interval for PCC";
          leaf seconds {
            type uint32 {
              range "1..255";
            }
            default 30;
            description
                "[1..255] Default - 30";
          } //seconds

        } //container keepalive

        container local-address {
          description
              "Configure local IP address for PCC";
          leaf ip-address {
            type inet:ip-address;
            description
                "ip-address - a.b.c.d (IPv4)";
          } //ip-address

        } //container local-address

        container max-srte-pce-init-lsps {
          description
              "Configure maximum SRTE PCE INIT LSPs for PCC";
          leaf max-srte-pce-init-lsps-id {
            type uint32 {
              range "0..8191";
            }
          } //max-srte-pce-init-lsps-id

        } //container max-srte-pce-init-lsps

        container redelegation-timer {
          description
              "Configure redelegation timer for PCC";
          leaf seconds {
            type uint32 {
              range "1..3600";
            }
            default 3600;
          } //seconds

        } //container redelegation-timer

        leaf report-path-constraints {
          type boolean;
          description
              "Specify whether to enable/disable path constraints in PCC report";
        }

        leaf shutdown {
          type boolean;
          description
              "Administratively enable or disable PCC";
        }

        container state-timer {
          description
              "Configure state timer for PCC";
          leaf seconds {
            type uint32 {
              range "1..3600";
            }
            default 3600;
          } //seconds

          leaf action {
            type enumeration {
              enum remove;
              enum none;
            }
            description
                "remove | none";
          } //action

        } //container state-timer

        container unknown-message-rate {
          description
              "Configure unknown message rate for PCC";
          leaf msg-min {
            type uint32 {
              range "1..255";
            }
            default 10;
            description
                "[1..255] Default - 10";
          } //msg-min

        } //container unknown-message-rate

        list peer {
          key "ip-address";
          description
              "Configure peer parameters for PCC";
          leaf ip-address {
            type inet:ip-address;
            description
                "ip-address - a.b.c.d (IPv4)";
          } //ip-address

          leaf preference {
            type uint32 {
              range "0..100";
            }
          } //preference

          leaf shutdown {
            type boolean;
            description
                "Administratively enable or disable the PCC Peer";
          }

        } //list peer

      } //container pcc

      container pce {
        presence
            "Configure Path Computation Server (PCE) parameters";
        container dead-timer {
          description
              "Configure dead timer interval for PCE";
          leaf seconds {
            type uint32 {
              range "1..255";
            }
            description
                "[1..255] - Default 120";
          } //seconds

        } //container dead-timer

        container keepalive {
          description
              "Configure keepalive interval for PCE";
          leaf seconds {
            type uint32 {
              range "1..255";
            }
            default 30;
            description
                "[1..255] Default - 30";
          } //seconds

        } //container keepalive

        container local-address {
          description
              "Configure local IP address for PCE";
          leaf ip-address {
            type inet:ip-address;
            description
                "ip-address - a.b.c.d (IPv4)";
          } //ip-address

        } //container local-address

        leaf shutdown {
          type boolean;
          description
              "Administratively enable or disable PCE";
        }

        container unknown-message-rate {
          description
              "Configure unknown message rate for PCE";
          leaf msg-min {
            type uint32 {
              range "1..255";
            }
            default 10;
            description
                "[1..255] Default - 10";
          } //msg-min

        } //container unknown-message-rate

      } //container pce

    } //container pcep

  } //grouping alu-conf-router-pcep-r13

} //module  alu-conf-router-pcep-r13
