module alu-conf-svc-vpls-macmo-r13 {
  yang-version "1";

  namespace "urn:alcatel-lucent.com:sros:ns:yang:conf-svc-vpls-macmo-r13";

  prefix "conf-svc-vpls-macmo-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure ethernet Mac Move on SR OS based 
       routers. 
       
       Copyright 2014-2015 Alcatel-Lucent, 2016 Nokia. All rights reserved. 
       Reproduction of this document is authorized on the condition that the 
       foregoing copyright notice is included. 
       
       This alu-conf-svc-vpls-macmo-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-svc-vpls-macmo-r13 {
    container mac-move {
      presence
          "Configure ethernet Mac Move";
      container move-frequency {
        description
            "Configure move frequency to be used";
        leaf frequency {
          type uint64 {
            range "1..10";
          }
        } //frequency

      } //container move-frequency

      container number-retries {
        description
            "Configure number of retries for reenabling";
        leaf number-retries {
          type uint32 {
            range "0..255";
          }
          description
              "[0..255] - 0 for unlimited";
        } //number-retries

      } //container number-retries

      container retry-timeout {
        description
            "Configure retry timeout to be used";
        leaf timeout {
          type uint64 {
            range "0..600";
          }
        } //timeout

      } //container retry-timeout

      leaf shutdown {
        type boolean;
        description
            "Administratively enable/disable mac-move";
      }

      container primary-ports {
        description
            "Configure primary-ports for this service";
        container cumulative-factor {
          description
              "mac-relearn periods to be used for mac-relearn rate";
          leaf cumulative-factor {
            type int32 {
              range "3..10";
            }
          } //cumulative-factor

        } //container cumulative-factor

        list sap {
          key "sap-id";
          description
              "configure this sap as primary vpls-port";
          leaf sap-id {
            type string;
            description
                "Attribute sap-id for sap";
          } //sap-id

        } //list sap

        list spoke-sdp {
          key "sdp-id-vc-id";
          description
              "configure this sdp as primary vpls-port";
          leaf sdp-id-vc-id {
            type string;
            description
                "sdp-id - [1..32767] 
                 vc-id - [1..4294967295]";
          } //sdp-id-vc-id

        } //list spoke-sdp

      } //container primary-ports

      container secondary-ports {
        description
            "Configure secondary-ports for this service";
        container cumulative-factor {
          description
              "mac-relearn periods to be used for mac-relearn rate";
          leaf cumulative-factor {
            type int32 {
              range "2..9";
            }
          } //cumulative-factor

        } //container cumulative-factor

        list sap {
          key "sap-id";
          description
              "configure this sap as secondary vpls-port";
          leaf sap-id {
            type string;
            description
                "Attribute sap-id for sap";
          } //sap-id

        } //list sap

        list spoke-sdp {
          key "sdp-id-vc-id";
          description
              "configure this sdp as secondary vpls-port";
          leaf sdp-id-vc-id {
            type string;
            description
                "sdp-id - [1..32767] 
                 vc-id - [1..4294967295]";
          } //sdp-id-vc-id

        } //list spoke-sdp

      } //container secondary-ports

    } //container mac-move

  } //grouping alu-conf-svc-vpls-macmo-r13

} //module  alu-conf-svc-vpls-macmo-r13
