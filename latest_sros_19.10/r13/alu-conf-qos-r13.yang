module alu-conf-qos-r13 {
  yang-version "1";

  namespace "urn:alcatel-lucent.com:sros:ns:yang:conf-qos-r13";

  prefix "conf-qos-r13";

  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure QoS policies on SR OS based 
       routers. 
       
       Copyright 2014-2015 Alcatel-Lucent, 2016 Nokia. All rights reserved. 
       Reproduction of this document is authorized on the condition that the 
       foregoing copyright notice is included. 
       
       This alu-conf-qos-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-09-17";

  grouping alu-conf-qos-r13 {
    container qos {
      description
          "Configure QoS policies";
      list adv-config-policy {
        key "adv-config-policy-name";
        description
            "Configure advanced configuration policy";
        leaf adv-config-policy-name {
          type string {
            length "1..32";
          }
        } //adv-config-policy-name

        container description {
          description
              "Description for this policy";
          leaf description-string {
            type string {
              length "1..80";
            }
          } //description-string

        } //container description

        container child-control {
          description
              "Configure child-control parameters";
          container bandwidth-distribution {
            description
                "Configure bandwidth-distribution parameters";
            container above-offered-cap {
              description
                  "Specify above-offered-cap perecent/rate";
              leaf percent {
                type string;
                description
                    "[0.00..100.00]";
              } //percent

              leaf rate {
                type string;
                description
                    "[0..100000000|max]";
              } //rate

            } //container above-offered-cap

            leaf enqueue-on-pir-zero {
              type boolean;
              description
                  "Specify enabling enqueue when PIR is 0";
            }

            container granularity {
              description
                  "Specify bandwidth-distribution granularity percent/rate";
              leaf percent {
                type string;
                description
                    "[0.00..100.00]";
              } //percent

              leaf rate {
                type uint32 {
                  range "0..100000000";
                }
                description
                    "[0..100000000]";
              } //rate

            } //container granularity

            container internal-scheduler-weight-mode {
              description
                  "Specify internal scheduler weight mode";
              leaf weight-mode {
                type enumeration {
                  enum default;
                  enum force-equal;
                  enum offered-load;
                  enum capped-offered-load;
                }
                description
                    "default|force-equal|offered-load|capped-offered-load";
              } //weight-mode

            } //container internal-scheduler-weight-mode

            leaf limit-pir-zero-drain {
              type boolean;
              description
                  "Specify queue draining when PIR is 0";
            }

            leaf lub-init-min-pir {
              type boolean;
              description
                  "Specify initializing minimal PIR on LUB enabled";
            }

          } //container bandwidth-distribution

          container offered-measurement {
            description
                "Configure offered-measurement parameters";
            container add {
              description
                  "Specify percent/rate to add";
              leaf percent {
                type string;
                description
                    "[0.00..100.00]";
              } //percent

              leaf rate {
                type uint32 {
                  range "0..100000000";
                }
                description
                    "[0..100000000]";
              } //rate

              leaf min-only {
                type boolean;
              } //min-only

              leaf active-min-only {
                type boolean;
              } //active-min-only

            } //container add

            leaf fast-start {
              type boolean;
              description
                  "Specify fast-start";
            }

            leaf fast-stop {
              type boolean;
              description
                  "Specify fast-stop";
            }

            container granularity {
              description
                  "Specify granularity percent/rate";
              leaf percent {
                type string;
                description
                    "[0.00..100.00]";
              } //percent

              leaf rate {
                type uint32 {
                  range "0..100000000";
                }
                description
                    "[0..100000000]";
              } //rate

            } //container granularity

            container high-rate-hold-time {
              description
                  "Specify high-rate-hold-time";
              leaf seconds {
                type uint32 {
                  range "0..60";
                }
                description
                    "[0..60]";
              } //seconds

              leaf active-min-only {
                type boolean;
              } //active-min-only

            } //container high-rate-hold-time

            container max-decrement {
              description
                  "Specify max-decrement percent/rate";
              leaf percent {
                type string;
                description
                    "[0.00..100.00]";
              } //percent

              leaf rate {
                type uint32 {
                  range "1..100000000";
                }
                description
                    "[1..100000000]";
              } //rate

            } //container max-decrement

            container sample-interval {
              description
                  "Specify sample-interval";
              leaf sample-period {
                type uint16 {
                  range "1..8";
                }
                description
                    "[1..8]";
              } //sample-period

            } //container sample-interval

            container time-average-factor {
              description
                  "Specify time-average-factor";
              leaf taf-value {
                type uint32 {
                  range "0..64";
                }
                description
                    "[0..64]";
              } //taf-value

              leaf dec-only {
                type boolean;
              } //dec-only

            } //container time-average-factor

          } //container offered-measurement

        } //container child-control

      } //list adv-config-policy

      list atm-td-profile {
        key "traffic-desc-profile-id";
        description
            "Configure ATM traffic descriptor profile";
        leaf traffic-desc-profile-id {
          type int32 {
            range "1..1000";
          }
        } //traffic-desc-profile-id

        leaf clp-tagging {
          type boolean;
          description
              "Configure clp-tagging";
        }

        container description {
          description
              "Description for this ATM traffic descriptor profile";
          leaf description-string {
            type string {
              length "1..80";
            }
          } //description-string

        } //container description

        container descriptor-type {
          description
              "Configure the descriptor-type";
          leaf type {
            type enumeration {
              enum P0_1;
              enum P0_1andS0;
              enum P0_1andS0_1;
              enum P0_1andS0_Tag;
            }
          } //type

        } //container descriptor-type

        leaf policing {
          type boolean;
          description
              "Configure policing";
        }

        container service-category {
          description
              "Configure the service category";
          leaf service-category {
            type enumeration {
              enum cbr;
              enum rt-vbr;
              enum nrt-vbr;
              enum ubr;
            }
            description
                "keywords - cbr|rt-vbr|nrt-vbr|ubr";
          } //service-category

        } //container service-category

        leaf shaping {
          type boolean;
          description
              "Configure the shaping attribute";
        }

        container traffic {
          description
              "Configure the traffic parameters";
          leaf sir {
            type uint64;
            description
                "[0..4294967295]";
          } //sir

          leaf pir {
            type uint64;
            description
                "[0..4294967295]";
          } //pir

          leaf mir {
            type uint64;
            description
                "[0..4294967295]";
          } //mir

          leaf mbs {
            type uint64;
            description
                "[0..4294967295]";
          } //mbs

          leaf cdvt {
            type uint32;
          } //cdvt

        } //container traffic

        container weight {
          description
              "Configure the VP shaping weight";
          leaf weight {
            type uint8 {
              range "1..255";
            }
          } //weight

        } //container weight

      } //list atm-td-profile

      container copy {
        description
            "Copy an existing policy";
        container adv-config-policy {
          description
              "Copy an existing adv-config-policy";
          leaf-list name {
            type string {
              length "1..32";
            }
            max-elements 2;
            description
                "src-name, dst-name - [32 chars max]";
          } //name

          leaf overwrite {
            type boolean;
            description
                "keyword - forces overwrite";
          } //overwrite

        } //container adv-config-policy

        container atm-td-profile {
          description
              "Copy an existing atm-td-profile";
          leaf-list atm-prof {
            type uint32 {
              range "1..1000";
            }
            max-elements 2;
            description
                "src-atm-prof, dst-atm-prof - [1..1000]";
          } //atm-prof

          leaf overwrite {
            type boolean;
            description
                "keyword - forces overwrite";
          } //overwrite

        } //container atm-td-profile

        container egress-remark-policy {
          description
              "Copy an existing egress-remark-policy";
          leaf-list name {
            type string {
              length "1..64";
            }
            max-elements 2;
            description
                "src-name, dst-name - [64 chars max]";
          } //name

          leaf overwrite {
            type boolean;
            description
                "keyword - forces overwrite";
          } //overwrite

        } //container egress-remark-policy

        container hs-attachment-policy {
          description
              "Copy an existing hs-attachment-policy";
          leaf-list name {
            type string;
            max-elements 2;
            description
                "src-name, dst-name - [32 chars max]";
          } //name

          leaf overwrite {
            type boolean;
            description
                "keyword - forces overwrite";
          } //overwrite

        } //container hs-attachment-policy

        container hs-pool-policy {
          description
              "Copy an existing hs-pool-policy";
          leaf-list name {
            type string;
            max-elements 2;
            description
                "src-name, dst-name - [32 chars max]";
          } //name

          leaf overwrite {
            type boolean;
            description
                "keyword - forces overwrite";
          } //overwrite

        } //container hs-pool-policy

        container hs-port-pool-policy {
          description
              "Copy an existing hs-port-pool-policy";
          leaf-list name {
            type string;
            max-elements 2;
            description
                "src-name, dst-name - [32 chars max]";
          } //name

          leaf overwrite {
            type boolean;
            description
                "keyword - forces overwrite";
          } //overwrite

        } //container hs-port-pool-policy

        container hs-scheduler-policy {
          description
              "Copy an existing hs-scheduler-policy";
          leaf-list name {
            type string;
            max-elements 2;
            description
                "src-name, dst-name - [32 chars max]";
          } //name

          leaf overwrite {
            type boolean;
            description
                "keyword - forces overwrite";
          } //overwrite

        } //container hs-scheduler-policy

        container hsmda-pool-policy {
          description
              "Copy an existing hsmda-pool-policy";
          leaf-list name {
            type string {
              length "1..32";
            }
            max-elements 2;
            description
                "src-name, dst-name - [32 chars max]";
          } //name

          leaf overwrite {
            type boolean;
            description
                "keyword - forces overwrite";
          } //overwrite

        } //container hsmda-pool-policy

        container hsmda-scheduler-policy {
          description
              "Copy an existing hsmda-scheduler-policy";
          leaf-list name {
            type string {
              length "1..32";
            }
            max-elements 2;
            description
                "src-name, dst-name - [32 chars max]";
          } //name

          leaf overwrite {
            type boolean;
            description
                "keyword - forces overwrite";
          } //overwrite

        } //container hsmda-scheduler-policy

        container hsmda-slope-policy {
          description
              "Copy an existing hsmda-slope-policy";
          leaf-list name {
            type string {
              length "1..32";
            }
            max-elements 2;
            description
                "src-name, dst-name - [32 chars max]";
          } //name

          leaf overwrite {
            type boolean;
            description
                "keyword - forces overwrite";
          } //overwrite

        } //container hsmda-slope-policy

        container hsmda-wrr-policy {
          description
              "Copy an existing hsmda-wrr-policy";
          leaf-list name {
            type string {
              length "1..32";
            }
            max-elements 2;
            description
                "src-name, dst-name - [32 chars max]";
          } //name

          leaf overwrite {
            type boolean;
            description
                "keyword - forces overwrite";
          } //overwrite

        } //container hsmda-wrr-policy

        container ingress-classification-policy {
          description
              "Copy an existing ingress-classification-policy";
          leaf-list name {
            type string {
              length "1..64";
            }
            max-elements 2;
            description
                "src-name, dst-name - [64 chars max]";
          } //name

          leaf overwrite {
            type boolean;
            description
                "keyword - forces overwrite";
          } //overwrite

        } //container ingress-classification-policy

        container mc-fr-profile-egress {
          description
              "Copy an existing mc-fr-profile-egress";
          leaf-list mc-fr-prof {
            type uint32 {
              range "1..65535";
            }
            max-elements 2;
            description
                "src-mc-fr-prof, dst-mc-fr-prof - [1..65535]";
          } //mc-fr-prof

          leaf overwrite {
            type boolean;
            description
                "keyword - forces overwrite";
          } //overwrite

        } //container mc-fr-profile-egress

        container mc-fr-profile-ingress {
          description
              "Copy an existing mc-fr-profile-ingress";
          leaf-list mc-fr-prof {
            type uint32 {
              range "1..65535";
            }
            max-elements 2;
            description
                "src-mc-fr-prof, dst-mc-fr-prof - [1..65535]";
          } //mc-fr-prof

          leaf overwrite {
            type boolean;
            description
                "keyword - forces overwrite";
          } //overwrite

        } //container mc-fr-profile-ingress

        container mlppp-profile-egress {
          description
              "Copy an existing mlppp-profile-egress";
          leaf-list mlppp-prof {
            type uint32 {
              range "1..65535";
            }
            max-elements 2;
            description
                "src-mlppp-prof, dst-mlppp-prof - [1..65535]";
          } //mlppp-prof

          leaf overwrite {
            type boolean;
            description
                "keyword - forces overwrite";
          } //overwrite

        } //container mlppp-profile-egress

        container mlppp-profile-ingress {
          description
              "Copy an existing mlppp-profile-ingress";
          leaf-list mlppp-prof {
            type uint32 {
              range "1..65535";
            }
            max-elements 2;
            description
                "src-mlppp-prof, dst-mlppp-prof - [1..65535]";
          } //mlppp-prof

          leaf overwrite {
            type boolean;
            description
                "keyword - forces overwrite";
          } //overwrite

        } //container mlppp-profile-ingress

        container named-pool-policy {
          description
              "Copy an existing named-pool-policy";
          leaf overwrite {
            type boolean;
            description
                "keyword - forces overwrite";
          } //overwrite

          leaf-list name {
            type string {
              length "1..32";
            }
            max-elements 2;
            description
                "src-name, dst-name - [32 chars max]";
          } //name

        } //container named-pool-policy

        container network {
          description
              "Copy an existing network policy";
          leaf-list policy-id {
            type uint32 {
              range "1..65535";
            }
            max-elements 2;
            description
                "src-pol, dst-pol - [1..65535]";
          } //policy-id

          leaf overwrite {
            type boolean;
            description
                "keyword - forces overwrite";
          } //overwrite

        } //container network

        container network-ingress {
          description
              "Copy an existing network-ingress policy";
          leaf-list name {
            type string {
              length "1..64";
            }
            max-elements 2;
            description
                "src-name, dst-name - [64 chars max]";
          } //name

          leaf overwrite {
            type boolean;
            description
                "keyword - forces overwrite";
          } //overwrite

        } //container network-ingress

        container network-queue {
          description
              "Copy an existing network queue";
          leaf-list name {
            type string {
              length "1..32";
            }
            max-elements 2;
            description
                "src-name, dst-name - [32 chars max]";
          } //name

          leaf overwrite {
            type boolean;
            description
                "keyword - forces overwrite";
          } //overwrite

        } //container network-queue

        container policer-control-policy {
          description
              "Copy an existing policer-control-policy";
          leaf-list name {
            type string {
              length "1..32";
            }
            max-elements 2;
            description
                "src-name, dst-name - [32 chars max]";
          } //name

          leaf overwrite {
            type boolean;
            description
                "keyword - forces overwrite";
          } //overwrite

        } //container policer-control-policy

        container port-qos-policy {
          description
              "Copy an existing port-qos-policy";
          leaf-list port-qos-policy-name {
            type string {
              length "1..64";
            }
            max-elements 2;
            description
                "src-port-qos-policy-name, dst-port-qos-policy-name - [64 chars max]";
          } //port-qos-policy-name

          leaf overwrite {
            type boolean;
            description
                "keyword - forces overwrite";
          } //overwrite

        } //container port-qos-policy

        container port-scheduler-policy {
          description
              "Copy an existing port-scheduler-policy";
          leaf-list name {
            type string {
              length "1..32";
            }
            max-elements 2;
            description
                "src-name, dst-name - [32 chars max]";
          } //name

          leaf overwrite {
            type boolean;
            description
                "keyword - forces overwrite";
          } //overwrite

        } //container port-scheduler-policy

        container post-policer-mapping {
          description
              "Copy an existing post-policer-mapping";
          leaf-list name {
            type string;
            max-elements 2;
            description
                "src-name, dst-name - [32 chars max]";
          } //name

          leaf overwrite {
            type boolean;
            description
                "keyword - forces overwrite";
          } //overwrite

        } //container post-policer-mapping

        container queue-group-egress {
          description
              "Copy an existing queue-group-egress";
          leaf-list qgrp-name {
            type string {
              length "1..32";
            }
            max-elements 2;
            description
                "src-qgrp-name, dst-qgrp-name - [32 chars max]";
          } //qgrp-name

          leaf overwrite {
            type boolean;
            description
                "keyword - forces overwrite";
          } //overwrite

        } //container queue-group-egress

        container queue-group-ingress {
          description
              "Copy an existing queue-group-ingress";
          leaf-list qgrp-name {
            type string {
              length "1..32";
            }
            max-elements 2;
            description
                "src-qgrp-name, dst-qgrp-name - [32 chars max]";
          } //qgrp-name

          leaf overwrite {
            type boolean;
            description
                "keyword - forces overwrite";
          } //overwrite

        } //container queue-group-ingress

        container queue-mgmt-policy {
          description
              "Copy an existing queue-mgmt-policy";
          leaf-list queue-mgmt-policy-name {
            type string;
            max-elements 2;
            description
                "src-queue-mgmt-policy-name, dst-queue-mgmt-policy-name - [64 chars max]";
          } //queue-mgmt-policy-name

          leaf overwrite {
            type boolean;
            description
                "keyword - forces overwrite";
          } //overwrite

        } //container queue-mgmt-policy

        container sap-egress {
          description
              "Copy an existing sap-egress policy";
          leaf-list sap-egr-name-id {
            type string;
            max-elements 2;
            description
                "[1..65535]|<name:64 char max>";
          } //sap-egr-name-id

          leaf overwrite {
            type boolean;
            description
                "keyword - forces overwrite";
          } //overwrite

        } //container sap-egress

        container sap-ingress {
          description
              "Copy an existing sap-ingress policy";
          leaf-list sap-ing-name-id {
            type string;
            max-elements 2;
            description
                "[1..65535]|<name:64 char max>";
          } //sap-ing-name-id

          leaf overwrite {
            type boolean;
            description
                "keyword - forces overwrite";
          } //overwrite

        } //container sap-ingress

        container scheduler-policy {
          description
              "Copy an existing scheduler policy";
          leaf-list name {
            type string {
              length "1..32";
            }
            max-elements 2;
            description
                "src-name, dst-name - [32 chars max]";
          } //name

          leaf overwrite {
            type boolean;
            description
                "keyword - forces overwrite";
          } //overwrite

        } //container scheduler-policy

        container shared-queue {
          description
              "Copy an existing shared queue";
          leaf-list name {
            type string {
              length "1..32";
            }
            max-elements 2;
            description
                "src-name, dst-name - [32 chars max]";
          } //name

          leaf overwrite {
            type boolean;
            description
                "keyword - forces overwrite";
          } //overwrite

        } //container shared-queue

        container slope-policy {
          description
              "Copy an existing slope policy";
          leaf-list name {
            type string {
              length "1..32";
            }
            max-elements 2;
            description
                "src-name, dst-name - [32 chars max]";
          } //name

          leaf overwrite {
            type boolean;
            description
                "keyword - forces overwrite";
          } //overwrite

        } //container slope-policy

        container vlan-qos-policy {
          description
              "Copy an existing vlan-qos-policy";
          leaf-list vlan-qos-policy-name {
            type string {
              length "1..64";
            }
            max-elements 2;
            description
                "src-vlan-qos-policy-name, dst-vlan-qos-policy-name - [64 chars max]";
          } //vlan-qos-policy-name

          leaf overwrite {
            type boolean;
            description
                "keyword - forces overwrite";
          } //overwrite

        } //container vlan-qos-policy

      } //container copy

      list egress-remark-policy {
        key "egress-remark-policy-name";
        description
            "Configure an egress-remark-policy";
        leaf egress-remark-policy-name {
          type string;
          description
              "<name:64 char max>";
        } //egress-remark-policy-name

        container description {
          description
              "Description for this egress remark policy";
          leaf description-string {
            type string {
              length "1..80";
            }
          } //description-string

        } //container description

        container scope {
          description
              "Specify the scope of the policy";
          leaf exclusive-template {
            type enumeration {
              enum exclusive;
              enum template;
            }
            description
                "keywords - specify type of policy";
          } //exclusive-template

        } //container scope

        list fc {
          key "fc-name";
          description
              "Configure a forwarding class";
          leaf fc-name {
            type enumeration {
              enum be;
              enum l2;
              enum af;
              enum l1;
              enum h2;
              enum ef;
              enum h1;
              enum nc;
            }
          } //fc-name

          container de-mark {
            description
                "Specify DE value for marking";
            leaf force {
              type int32 {
                range "0..1";
              }
            } //force

          } //container de-mark

          container dot1p {
            description
                "Specify the dot1p value to be used";
            leaf dot1p-value {
              type string;
            } //dot1p-value

            leaf in-profile {
              type string;
              description
                  "dot1p-value";
            } //in-profile

            leaf out-profile {
              type string;
              description
                  "dot1p-value";
            } //out-profile

          } //container dot1p

          container dscp {
            description
                "Specify DSCP mappings";
            leaf dscp-name {
              type string {
                length "1..32";
              }
              description
                  "Attribute dscp-name for dscp";
            } //dscp-name

            leaf in-profile {
              type string {
                length "1..32";
              }
              description
                  "dscp-name";
            } //in-profile

            leaf out-profile {
              type string {
                length "1..32";
              }
              description
                  "dscp-name";
            } //out-profile

          } //container dscp

          container lsp-exp {
            description
                "Specify LSP-EXP in profile mapping";
            leaf lsp-exp-value {
              type int32 {
                range "0..7";
              }
            } //lsp-exp-value

            leaf in-profile {
              type int32 {
                range "0..7";
              }
              description
                  "lsp-exp-value";
            } //in-profile

            leaf out-profile {
              type int32 {
                range "0..7";
              }
              description
                  "lsp-exp-value";
            } //out-profile

          } //container lsp-exp

        } //list fc

      } //list egress-remark-policy

      list hs-attachment-policy {
        key "policy-name";
        description
            "Configure a hs (high scale) attachment policy";
        leaf policy-name {
          type string {
            length "1..32";
          }
        } //policy-name

        container description {
          description
              "Description for this policy";
          leaf description-string {
            type string {
              length "1..80";
            }
          } //description-string

        } //container description

        container low-burst-max-class {
          description
              "Specify low burst max class";
          leaf class {
            type uint32 {
              range "1..6";
            }
          } //class

        } //container low-burst-max-class

        list queue {
          key "queue-id";
          description
              "Configure queue mapping";
          leaf queue-id {
            type uint32 {
              range "1..8";
            }
          } //queue-id

          leaf sched-class {
            type uint32 {
              range "1..6";
            }
          } //sched-class

          leaf wrr-group {
            type uint32 {
              range "1..2";
            }
          } //wrr-group

          leaf unattached {
            type boolean;
            description
                "keyword";
          } //unattached

        } //list queue

        list wrr-group {
          key "group-id";
          description
              "Configure wrr-group mapping";
          leaf group-id {
            type uint32 {
              range "1..2";
            }
          } //group-id

          leaf sched-class {
            type uint32 {
              range "1..6";
            }
          } //sched-class

          leaf unattached {
            type boolean;
            description
                "keyword";
          } //unattached

        } //list wrr-group

      } //list hs-attachment-policy

      list hs-pool-policy {
        key "policy-name";
        description
            "Configure a hs (high scale) pool policy";
        leaf policy-name {
          type string {
            length "1..32";
          }
        } //policy-name

        container description {
          description
              "Description for this policy";
          leaf description-string {
            type string {
              length "1..80";
            }
          } //description-string

        } //container description

        container system-reserve {
          description
              "Configure the system reserve";
          leaf percent-of-buffers {
            type string;
            description
                "[1.00..30.00]";
          } //percent-of-buffers

        } //container system-reserve

        container mid-tier {
          description
              "Configure mid-tier pools";
          list mid-pool {
            key "mid-pool-id";
            description
                "Configure a mid pool";
            leaf mid-pool-id {
              type uint32 {
                range "1..16";
              }
            } //mid-pool-id

            container allocation-percent {
              description
                  "Specify allocation percent";
              leaf percent-of-parent-pool {
                type string;
                description
                    "[0.01..100.00]";
              } //percent-of-parent-pool

            } //container allocation-percent

            container parent-root-pool {
              description
                  "Specify parent root pool";
              leaf root-pool-id {
                type string;
                description
                    "[1..16 | none]";
              } //root-pool-id

            } //container parent-root-pool

            container port-bw-oversub-factor {
              description
                  "Specify port oversubscription factor";
              leaf oversubscription-factor {
                type uint32 {
                  range "1..10";
                }
                description
                    "[1..10]";
              } //oversubscription-factor

            } //container port-bw-oversub-factor

            container slope-policy {
              description
                  "Specify slope policy";
              leaf policy-name {
                type string {
                  length "1..32";
                }
              } //policy-name

            } //container slope-policy

          } //list mid-pool

        } //container mid-tier

        container root-tier {
          description
              "Configure root pools";
          list root-pool {
            key "root-pool-id";
            description
                "Configure a root pool";
            leaf root-pool-id {
              type uint32 {
                range "1..16";
              }
            } //root-pool-id

            container allocation-weight {
              description
                  "Specify allocation weight";
              leaf pool-weight {
                type uint32 {
                  range "0..100";
                }
                description
                    "[0..100]";
              } //pool-weight

            } //container allocation-weight

            container slope-policy {
              description
                  "Specify slope policy";
              leaf policy-name {
                type string {
                  length "1..32";
                }
              } //policy-name

            } //container slope-policy

          } //list root-pool

        } //container root-tier

      } //list hs-pool-policy

      list hs-port-pool-policy {
        key "policy-name";
        description
            "Configure a hs (high scale) port-pool policy";
        leaf policy-name {
          type string {
            length "1..32";
          }
        } //policy-name

        container description {
          description
              "Description for this policy";
          leaf description-string {
            type string {
              length "1..80";
            }
          } //description-string

        } //container description

        container alt-port-class-pools {
          description
              "Configure alternate port class pools";
          list class-pool {
            key "alt-class-pool-id";
            description
                "Configure a alternate class pool";
            leaf alt-class-pool-id {
              type uint32 {
                range "1..6";
              }
            } //alt-class-pool-id

            container allocation {
              description
                  "Specify allocation percent or weight";
              leaf explicit-percent {
                type string;
                description
                    "[0.01..100.00]";
              } //explicit-percent

              leaf port-bw-weight {
                type uint32 {
                  range "1..100";
                }
                description
                    "[1..100]";
              } //port-bw-weight

            } //container allocation

            container parent-mid-pool {
              description
                  "Specify mid-pool parent";
              leaf mid-pool-id {
                type string;
                description
                    "[1..16 | none]";
              } //mid-pool-id

            } //container parent-mid-pool

            container slope-policy {
              description
                  "Specify slope policy";
              leaf policy-name {
                type string {
                  length "1..32";
                }
              } //policy-name

            } //container slope-policy

          } //list class-pool

        } //container alt-port-class-pools

        container std-port-class-pools {
          description
              "Configure standard port class pools";
          list class-pool {
            key "std-class-pool-id";
            description
                "Configure a class pool";
            leaf std-class-pool-id {
              type uint32 {
                range "1..6";
              }
            } //std-class-pool-id

            container allocation {
              description
                  "Specify allocation percent or weight";
              leaf explicit-percent {
                type string;
                description
                    "[0.01..100.00]";
              } //explicit-percent

              leaf port-bw-weight {
                type uint32 {
                  range "1..100";
                }
                description
                    "[1..100]";
              } //port-bw-weight

            } //container allocation

            container parent-mid-pool {
              description
                  "Specify mid-pool parent";
              leaf mid-pool-id {
                type string;
                description
                    "[1..16 | none]";
              } //mid-pool-id

            } //container parent-mid-pool

            container slope-policy {
              description
                  "Specify slope policy";
              leaf policy-name {
                type string {
                  length "1..32";
                }
              } //policy-name

            } //container slope-policy

          } //list class-pool

        } //container std-port-class-pools

      } //list hs-port-pool-policy

      list hs-scheduler-policy {
        key "policy-name";
        description
            "Configure a hs (high scale) scheduler-policy";
        leaf policy-name {
          type string {
            length "1..32";
          }
        } //policy-name

        container description {
          description
              "Description for this policy";
          leaf description-string {
            type string {
              length "1..80";
            }
          } //description-string

        } //container description

        list group {
          key "group-id";
          description
              "Configure a group rate";
          leaf group-id {
            type uint32 {
            }
            description
                "[1]";
          } //group-id

          leaf rate {
            type string;
            description
                "[1..100000|max] Mbps";
          } //rate

        } //list group

        container max-rate {
          description
              "Configure the maximum rate";
          leaf rate {
            type string;
            description
                "[1..100000|max] Mbps";
          } //rate

        } //container max-rate

        list scheduling-class {
          key "class-id";
          description
              "Configure a scheduling class";
          leaf class-id {
            type int32 {
              range "1..6";
            }
          } //class-id

          leaf rate {
            type string;
            description
                "[1..100000|max] Mbps";
          } //rate

          leaf group {
            type int32 {
            }
            description
                "[1]";
          } //group

          leaf weight {
            type int32 {
              range "1..127";
            }
          } //weight

        } //list scheduling-class

      } //list hs-scheduler-policy

      list hsmda-pool-policy {
        key "policy-name";
        description
            "Configure a hsmda pool policy";
        leaf policy-name {
          type string {
            length "1..32";
          }
        } //policy-name

        container description {
          description
              "Description for this policy";
          leaf description-string {
            type string {
              length "1..80";
            }
          } //description-string

        } //container description

        container system-reserve {
          description
              "Configure the system reserve";
          leaf percentage-of-buffers {
            type string;
            description
                "[1.00..30.00]";
          } //percentage-of-buffers

        } //container system-reserve

        container class-tier {
          description
              "Configure class pools";
          list class-pool {
            key "class-pool-id";
            description
                "Configure a class pool";
            leaf class-pool-id {
              type uint32 {
                range "1..8";
              }
            } //class-pool-id

            leaf root-parent {
              type uint32 {
                range "1..8";
              }
            } //root-parent

            leaf allocation-percent {
              type string;
              description
                  "[0.01..100.00]";
            } //allocation-percent

          } //list class-pool

        } //container class-tier

        container root-tier {
          description
              "Configure root pools";
          list root-pool {
            key "root-pool-id";
            description
                "Configure a root pool";
            leaf root-pool-id {
              type uint32 {
                range "1..8";
              }
            } //root-pool-id

            leaf allocation-weight {
              type uint32 {
                range "0..100";
              }
            } //allocation-weight

          } //list root-pool

        } //container root-tier

      } //list hsmda-pool-policy

      list hsmda-scheduler-policy {
        key "scheduler-policy-name";
        description
            "Configure a hsmda scheduler-policy";
        leaf scheduler-policy-name {
          type string {
            length "1..32";
          }
        } //scheduler-policy-name

        container description {
          description
              "Description for this policy";
          leaf description-string {
            type string {
              length "1..80";
            }
          } //description-string

        } //container description

        list group {
          key "group-id";
          description
              "Configure a group rate";
          leaf group-id {
            type int32 {
              range "1..2";
            }
            description
                "[1|2]";
          } //group-id

          leaf rate {
            type string;
            description
                "[1..100000|max] Mbps";
          } //rate

          leaf burst-limit {
            type uint32 {
              range "1..327680";
            }
          } //burst-limit

          leaf bytes-kilobytes {
            type enumeration {
              enum bytes;
              enum kilobytes;
            }
          } //bytes-kilobytes

        } //list group

        container max-rate {
          description
              "Configure the maximum rate";
          leaf rate {
            type string;
            description
                "[1..100000|max] Mbps";
          } //rate

          leaf burst-limit {
            type uint32 {
              range "1..327680";
            }
          } //burst-limit

          leaf bytes-kilobytes {
            type enumeration {
              enum bytes;
              enum kilobytes;
            }
          } //bytes-kilobytes

        } //container max-rate

        list scheduling-class {
          key "class";
          description
              "Configure a scheduling class";
          leaf class {
            type int32 {
              range "1..8";
            }
          } //class

          leaf rate {
            type string;
            description
                "[1..100000|max] Mbps";
          } //rate

          leaf group {
            type int32 {
              range "1..2";
            }
            description
                "[1|2]";
          } //group

          leaf weight {
            type int32 {
              range "1..100";
            }
          } //weight

          leaf burst-limit {
            type uint32 {
              range "1..327680";
            }
          } //burst-limit

          leaf bytes-kilobytes {
            type enumeration {
              enum bytes;
              enum kilobytes;
            }
          } //bytes-kilobytes

        } //list scheduling-class

      } //list hsmda-scheduler-policy

      list hsmda-slope-policy {
        key "policy-name";
        description
            "Configure a hsmda slope policy";
        leaf policy-name {
          type string {
            length "1..32";
          }
        } //policy-name

        container description {
          description
              "Description for this policy";
          leaf description-string {
            type string {
              length "1..80";
            }
          } //description-string

        } //container description

        container high-slope {
          description
              "Configure a high slope parameters";
          container max-depth {
            description
                "Configure max depth for the high slope";
            leaf percent-of-queue-depth {
              type string;
              description
                  "[0.01..100.00]";
            } //percent-of-queue-depth

          } //container max-depth

          container max-prob {
            description
                "Configure max probability percentage for the high slope";
            leaf discard-probability-in-percent {
              type string;
              description
                  "[0.01..100.00]";
            } //discard-probability-in-percent

          } //container max-prob

          leaf shutdown {
            type boolean;
            description
                "Administratively enable/disable the high slope";
          }

          container start-depth {
            description
                "Configure start depth for the high slope";
            leaf percent-of-queue-depth {
              type string;
              description
                  "[0.01..100.00]";
            } //percent-of-queue-depth

          } //container start-depth

        } //container high-slope

        container low-slope {
          description
              "Configure a low slope parameters";
          container max-depth {
            description
                "Configure max depth for the low slope";
            leaf percent-of-queue-depth {
              type string;
              description
                  "[0.01..100.00]";
            } //percent-of-queue-depth

          } //container max-depth

          container max-prob {
            description
                "Configure max probability percentage for the low slope";
            leaf discard-probability-in-percent {
              type string;
              description
                  "[0.01..100.00]";
            } //discard-probability-in-percent

          } //container max-prob

          leaf shutdown {
            type boolean;
            description
                "Administratively enable/disable the low slope";
          }

          container start-depth {
            description
                "Configure start depth for the low slope";
            leaf percent-of-queue-depth {
              type string;
              description
                  "[0.01..100.00]";
            } //percent-of-queue-depth

          } //container start-depth

        } //container low-slope

      } //list hsmda-slope-policy

      list hsmda-wrr-policy {
        key "policy-name";
        description
            "Configure a hsmda wrr policy";
        leaf policy-name {
          type string {
            length "1..32";
          }
        } //policy-name

        container class-agg-weight {
          description
              "Configure class-agg-weight";
          leaf class-agg-weight-id {
            type enumeration {
              enum 1;
              enum 2;
              enum 4;
              enum 8;
            }
          } //class-agg-weight-id

        } //container class-agg-weight

        container description {
          description
              "Description for this policy";
          leaf description-string {
            type string {
              length "1..80";
            }
          } //description-string

        } //container description

        container include-queues {
          description
              "Include queues for this policy";
          leaf include-queues-id {
            type enumeration {
              enum 1-2;
              enum 1-3;
            }
          } //include-queues-id

        } //container include-queues

        container schedule-using-class {
          description
              "Configure a schedule-using-class";
          leaf schedule-using-class-id {
            type int32 {
              range "1..3";
            }
          } //schedule-using-class-id

        } //container schedule-using-class

      } //list hsmda-wrr-policy

      list ingress-classification-policy {
        key "name";
        description
            "Configure ingress classification of service";
        leaf name {
          type string {
            length "1..64";
          }
        } //name

        leaf allow-egress-dscp-exp-remarking {
          type boolean;
          status "obsolete";
          description
              "To enable DSCP/EXP remarking";
        }

        container default-action {
          description
              "Configure default forwarding class for this policy";
          leaf fc {
            type string;
            description
                "fc-name - be|l2|af|l1|h2|ef|h1|nc";
          } //fc

          leaf profile {
            type enumeration {
              enum in;
              enum out;
            }
            description
                "keywords - specify type of marking to be done";
          } //profile

        } //container default-action

        container description {
          description
              "Description for this ingress-cos policy";
          leaf description-string {
            type string {
              length "1..80";
            }
            description
                "[80 chars max]";
          } //description-string

        } //container description

        list dot1p {
          key "dot1p-priority";
          description
              "Specify 802.1 priority mappings";
          leaf fc {
            type enumeration {
              enum be;
              enum l2;
              enum af;
              enum l1;
              enum h2;
              enum ef;
              enum h1;
              enum nc;
            }
            default "be";
            description
                "fc-name - be|l2|af|l1|h2|ef|h1|nc";
          } //fc

          leaf profile {
            type enumeration {
              enum in;
              enum out;
              enum use-de;
            }
            description
                "profile";
          } //profile

          leaf dot1p-priority {
            type int32 {
              range "0..7";
            }
            description
                "[0..7]";
          } //dot1p-priority

        } //list dot1p

        list dscp {
          key "dscp-name";
          description
              "Specify DSCP mappings";
          leaf fc {
            type enumeration {
              enum be;
              enum l2;
              enum af;
              enum l1;
              enum h2;
              enum ef;
              enum h1;
              enum nc;
            }
            default "be";
            description
                "fc-name - be|l2|af|l1|h2|ef|h1|nc";
          } //fc

          leaf profile {
            type enumeration {
              enum in;
              enum out;
            }
            description
                "profile";
          } //profile

          leaf dscp-name {
            type string {
              length "1..32";
            }
            description
                "Attribute dscp-name for dscp";
          } //dscp-name

        } //list dscp

        list lsp-exp {
          key "lsp-exp-priority";
          description
              "Specify EXP Bits mappings";
          leaf fc {
            type enumeration {
              enum be;
              enum l2;
              enum af;
              enum l1;
              enum h2;
              enum ef;
              enum h1;
              enum nc;
            }
            default "be";
            description
                "fc-name - be|l2|af|l1|h2|ef|h1|nc";
          } //fc

          leaf profile {
            type enumeration {
              enum in;
              enum out;
            }
            description
                "profile";
          } //profile

          leaf lsp-exp-priority {
            type int32 {
              range "0..7";
            }
            description
                "[0..7]";
          } //lsp-exp-priority

        } //list lsp-exp

        container remark {
          description
              "Specify remark";
          leaf remark-value {
            type enumeration {
              enum dot1p-exp;
              enum any;
            }
          } //remark-value

        } //container remark

        container scope {
          description
              "Specify scope of the policy";
          leaf exclusive-template {
            type enumeration {
              enum exclusive;
              enum template;
            }
            description
                "keywords - specify type of policy";
          } //exclusive-template

        } //container scope

      } //list ingress-classification-policy

      container match-list {
        description
            "Configure a match-list for use in QoS";
        list ip-prefix-list {
          key "ip-prefix-list-name";
          description
              "Configure an ip prefix-list";
          leaf ip-prefix-list-name {
            type string {
              length "1..32";
            }
          } //ip-prefix-list-name

          container description {
            description
                "Description for this ip prefix list";
            leaf description-string {
              type string {
                length "1..80";
              }
            } //description-string

          } //container description

          list prefix {
            key "ip-prefix-prefix-length";
            description
                "Create/delete an entry in the ip prefix list";
            leaf ip-prefix-prefix-length {
              type inet:ip-prefix;
              description
                  "ip-prefix - a.b.c.d (host bits must be 0) 
                   prefix-length - [0..32] 
                   ";
            } //ip-prefix-prefix-length

          } //list prefix

        } //list ip-prefix-list

        list ipv6-prefix-list {
          key "ipv6-prefix-list-name";
          description
              "Configure an ipv6 prefix list";
          leaf ipv6-prefix-list-name {
            type string {
              length "1..32";
            }
          } //ipv6-prefix-list-name

          container description {
            description
                "Description for this ip prefix list";
            leaf description-string {
              type string {
                length "1..80";
              }
            } //description-string

          } //container description

          list prefix {
            key "ipv6-prefix-prefix-length";
            description
                "Create/delete an entry in the ip prefix list";
            leaf ipv6-prefix-prefix-length {
              type string;
              description
                  "ipv6-prefix x:x:x:x:x:x:x:x (eight 16-bit pieces) 
                   x:x:x:x:x:x:d.d.d.d 
                   x [0..FFFF]H 
                   d [0..255]D 
                   prefix-length [1..128]";
            } //ipv6-prefix-prefix-length

          } //list prefix

        } //list ipv6-prefix-list

      } //container match-list

      list mc-fr-profile-egress {
        key "profile-id";
        description
            "Configure a multi-class frame-relay egress profile";
        leaf profile-id {
          type uint32 {
            range "1..65535";
          }
        } //profile-id

        container description {
          description
              "Description for this profile";
          leaf description {
            type string {
              length "1..80";
            }
          } //description

        } //container description

        list class {
          key "class-id";
          description
              "Configure a class for this profile";
          leaf class-id {
            type uint32 {
              range "0..3";
            }
          } //class-id

          container max-queue-size {
            description
                "Configure maximum queue size for mc-fr class";
            leaf queue-size {
              type uint32 {
                range "1..1000";
              }
              description
                  "[1..1000] - in milliseconds of buffer space";
            } //queue-size

          } //container max-queue-size

          container mir {
            description
                "Configure MIR scheduling parameter";
            leaf mir-value {
              type uint32 {
                range "1..100";
              }
            } //mir-value

          } //container mir

          container weight {
            description
                "Configure weight scheduling parameter";
            leaf weight-value {
              type uint32 {
                range "1..100";
              }
            } //weight-value

          } //container weight

        } //list class

      } //list mc-fr-profile-egress

      list mc-fr-profile-ingress {
        key "profile-id";
        description
            "Configure a multi-class frame-relay ingress profile";
        leaf profile-id {
          type uint32 {
            range "1..65535";
          }
        } //profile-id

        container description {
          description
              "Description for this profile";
          leaf description {
            type string {
              length "1..80";
            }
          } //description

        } //container description

        list class {
          key "class-id";
          description
              "Configure a class for this profile";
          leaf class-id {
            type uint32 {
              range "0..3";
            }
          } //class-id

          container reassembly-timeout {
            description
                "Configure a reassembly timeout for this policy";
            leaf timeout {
              type uint32 {
                range "1..1000";
              }
              description
                  "[1..1000] - in milliseconds";
            } //timeout

          } //container reassembly-timeout

        } //list class

      } //list mc-fr-profile-ingress

      container md-auto-id {
        description
            "Configure auto identifier ranges for model-driven CLI";
        container qos-policy-id-range {
          description
              "Configure qos policy identifier range";
          leaf start {
            type uint32 {
              range "1..65535";
            }
          } //start

          leaf end {
            type uint32 {
              range "1..65535";
            }
            description
                "policy-id";
          } //end

        } //container qos-policy-id-range

      } //container md-auto-id

      list mlppp-profile-egress {
        key "profile-id";
        description
            "Configure an egress mlppp profile";
        leaf profile-id {
          type uint32 {
            range "1..65535";
          }
        } //profile-id

        container description {
          description
              "Description for this policy";
          leaf description-string {
            type string {
              length "1..80";
            }
          } //description-string

        } //container description

        list fc {
          key "fc-id";
          description
              "Configure fc to class-id mappings";
          leaf fc-id {
            type enumeration {
              enum be;
              enum l2;
              enum af;
              enum l1;
              enum h2;
              enum ef;
              enum h1;
              enum nc;
            }
          } //fc-id

          leaf mlppp-class {
            type uint16 {
              range "0..3";
            }
          } //mlppp-class

        } //list fc

        list class {
          key "class-id";
          description
              "Configure a class for this policy.";
          leaf class-id {
            type uint32 {
              range "0..3";
            }
          } //class-id

          container max-queue-size {
            description
                "Configure maximum queue size for mlppp class";
            leaf queue-size {
              type uint16 {
                range "1..1000";
              }
              description
                  "[1..1000] - in milliseconds of buffer space";
            } //queue-size

          } //container max-queue-size

          container mir {
            description
                "Configure MIR scheduling parameter";
            leaf mir-value {
              type uint16 {
                range "1..100";
              }
            } //mir-value

          } //container mir

          container weight {
            description
                "Configure weight scheduling parameter";
            leaf weight-value {
              type uint16 {
                range "1..100";
              }
            } //weight-value

          } //container weight

        } //list class

      } //list mlppp-profile-egress

      list mlppp-profile-ingress {
        key "profile-id";
        description
            "Configure an ingress mlppp-profile";
        leaf profile-id {
          type uint32 {
            range "1..65535";
          }
        } //profile-id

        container description {
          description
              "Description for this policy.";
          leaf description-string {
            type string {
              length "1..80";
            }
          } //description-string

        } //container description

        list class {
          key "class-id";
          description
              "Configure a class for this policy.";
          leaf class-id {
            type uint32 {
              range "0..3";
            }
          } //class-id

          container reassembly-timeout {
            description
                "Configure a reassembly timeout for this policy";
            leaf timeout-value {
              type uint32 {
                range "1..1000";
              }
              description
                  "[1..1000] - in milliseconds";
            } //timeout-value

          } //container reassembly-timeout

        } //list class

      } //list mlppp-profile-ingress

      list named-pool-policy {
        key "policy-name";
        description
            "Configure a named-pool-policy";
        leaf policy-name {
          type string {
            length "1..32";
          }
        } //policy-name

        container description {
          description
              "Description for this policy";
          leaf description {
            type string {
              length "1..80";
            }
          } //description

        } //container description

        container q1-pools {
          description
              "Configure Q1 pools";
          container port-allocation-weights {
            description
                "Configure port allocation weights";
            leaf default {
              type int32 {
                range "0..100";
              }
              description
                  "[0..100] - default is 50";
            } //default

            leaf mda {
              type int32 {
                range "0..100";
              }
            } //mda

            leaf port {
              type int32 {
                range "0..100";
              }
            } //port

          } //container port-allocation-weights

          list pool {
            key "pool-name";
            description
                "Configure pool for named pool policy";
            leaf pool-name {
              type string {
                length "1..32";
              }
            } //pool-name

            container amber-alarm-threshold {
              description
                  "Configure amber alarm threshold";
              leaf percentage {
                type uint32 {
                  range "1..1000";
                }
              } //percentage

            } //container amber-alarm-threshold

            container description {
              description
                  "Description for this pool";
              leaf description {
                type string {
                  length "1..80";
                }
              } //description

            } //container description

            container red-alarm-threshold {
              description
                  "Configure red alarm threshold";
              leaf percentage {
                type uint32 {
                  range "1..1000";
                }
              } //percentage

            } //container red-alarm-threshold

            container resv-cbs {
              description
                  "Configure reserved CBS";
              leaf percentage-of-pool-size {
                type string;
                description
                    "[0..100|default]";
              } //percentage-of-pool-size

              leaf amber-alarm-action {
                type boolean;
              } //amber-alarm-action

              leaf step {
                type uint32 {
                  range "1..100";
                }
              } //step

              leaf max {
                type uint32 {
                  range "1..100";
                }
              } //max

            } //container resv-cbs

            container slope-policy {
              description
                  "Configure slope policy for this pool";
              leaf slope-policy-name {
                type string {
                  length "1..32";
                }
              } //slope-policy-name

            } //container slope-policy

            container application-weights {
              description
                  "Configure application weights";
              container access-allocation-weight {
                description
                    "Configure access allocation weight for this pool";
                leaf weight {
                  type uint32 {
                    range "0..100";
                  }
                } //weight

              } //container access-allocation-weight

              container network-allocation-weight {
                description
                    "Configure network allocation weight for this pool";
                leaf weight {
                  type uint32 {
                    range "0..100";
                  }
                } //weight

              } //container network-allocation-weight

            } //container application-weights

          } //list pool

        } //container q1-pools

      } //list named-pool-policy

      list network {
        key "network-policy-id";
        description
            "Configure network policy";
        leaf network-policy-id {
          type uint32 {
            range "1..65535";
          }
        } //network-policy-id

        leaf name {
          type string {
            length "1..64";
          }
        } //name

        container description {
          description
              "Description for this network policy";
          leaf description-string {
            type string {
              length "1..80";
            }
          } //description-string

        } //container description

        container policy-name {
          status "obsolete";
          description
              "Configure a name to the policy";
          leaf policy-name {
            type string {
              length "1..64";
            }
          } //policy-name

        } //container policy-name

        container scope {
          description
              "Specify scope of the policy";
          leaf exclusive-template {
            type enumeration {
              enum exclusive;
              enum template;
            }
            description
                "keywords - specify type of policy";
          } //exclusive-template

        } //container scope

        container egress {
          description
              "Configure egress parameters";
          list dscp {
            key "dscp-name";
            description
                "Specify DSCP mappings";
            leaf dscp-name {
              type string {
                length "1..32";
              }
              description
                  "Attribute dscp-name for dscp";
            } //dscp-name

            leaf fc {
              type enumeration {
                enum be;
                enum l2;
                enum af;
                enum l1;
                enum h2;
                enum ef;
                enum h1;
                enum nc;
              }
            } //fc

            leaf profile {
              type enumeration {
                enum in;
                enum out;
                enum exceed;
                enum inplus;
              }
            } //profile

          } //list dscp

          list prec {
            key "ip-prec-value";
            description
                "Specify IP precedence mappings";
            leaf ip-prec-value {
              type int32 {
                range "0..7";
              }
            } //ip-prec-value

            leaf fc {
              type enumeration {
                enum be;
                enum l2;
                enum af;
                enum l1;
                enum h2;
                enum ef;
                enum h1;
                enum nc;
              }
            } //fc

            leaf profile {
              type enumeration {
                enum in;
                enum out;
                enum exceed;
                enum inplus;
              }
            } //profile

          } //list prec

          container remarking {
            description
                "Enable/disable remarking";
            leaf force {
              type boolean;
            } //force

          } //container remarking

          list fc {
            key "fc-name";
            description
                "Configure a forwarding class";
            leaf fc-name {
              type enumeration {
                enum be;
                enum l2;
                enum af;
                enum l1;
                enum h2;
                enum ef;
                enum h1;
                enum nc;
              }
            } //fc-name

            container de-mark {
              description
                  "Specify DE value for marking";
              leaf force {
                type int32 {
                  range "0..1";
                }
              } //force

            } //container de-mark

            container dot1p {
              description
                  "Specify Dot1p profile mapping";
              leaf dot1p-priority {
                type int32 {
                  range "0..7";
                }
              } //dot1p-priority

            } //container dot1p

            container dot1p-in-profile {
              description
                  "Specify Dot1p in profile mapping";
              leaf dot1p-priority {
                type int32 {
                  range "0..7";
                }
              } //dot1p-priority

            } //container dot1p-in-profile

            container dot1p-out-profile {
              description
                  "Specify Dot1p out profile mapping";
              leaf dot1p-priority {
                type int32 {
                  range "0..7";
                }
              } //dot1p-priority

            } //container dot1p-out-profile

            container dscp-in-profile {
              description
                  "Specify DSCP in profile mapping";
              leaf dscp-name {
                type string {
                  length "1..32";
                }
                description
                    "Attribute dscp-name for dscp-in-profile";
              } //dscp-name

            } //container dscp-in-profile

            container dscp-out-profile {
              description
                  "Specify DSCP out profile mapping";
              leaf dscp-name {
                type string {
                  length "1..32";
                }
                description
                    "Attribute dscp-name for dscp-out-profile";
              } //dscp-name

            } //container dscp-out-profile

            container lsp-exp-in-profile {
              description
                  "Specify LSP-EXP in profile mapping";
              leaf lsp-exp-value {
                type int32 {
                  range "0..7";
                }
              } //lsp-exp-value

            } //container lsp-exp-in-profile

            container lsp-exp-out-profile {
              description
                  "Specify LSP-EXP out profile mapping";
              leaf lsp-exp-value {
                type int32 {
                  range "0..7";
                }
              } //lsp-exp-value

            } //container lsp-exp-out-profile

            container port-redirect-group {
              description
                  "Configure QoS network egress port redirect group";
              leaf policer {
                type uint32 {
                  range "1..8";
                }
              } //policer

              leaf queue {
                type int32 {
                  range "1..8";
                }
              } //queue

            } //container port-redirect-group

          } //list fc

          container ip-criteria {
            presence
                "Configure IP match criteria";
            container renum {
              description
                  "Renumber an entry";
              leaf old-entry-id {
                type uint32 {
                  range "1..65535";
                }
              } //old-entry-id

              leaf new-entry-id {
                type uint32 {
                  range "1..65535";
                }
              } //new-entry-id

            } //container renum

            list entry {
              key "entry-id";
              description
                  "Configure an IP based policy entry";
              leaf entry-id {
                type uint32 {
                  range "1..65535";
                }
              } //entry-id

              container action {
                description
                    "Specify action fc, policer, port-group redirection, queue and priority";
                leaf fc {
                  type enumeration {
                    enum be;
                    enum l2;
                    enum af;
                    enum l1;
                    enum h2;
                    enum ef;
                    enum h1;
                    enum nc;
                  }
                } //fc

                leaf profile {
                  type enumeration {
                    enum in;
                    enum out;
                    enum exceed;
                    enum inplus;
                  }
                } //profile

                leaf port-redirect-group {
                  type boolean;
                  description
                      "keyword";
                } //port-redirect-group

                leaf policer {
                  type uint32 {
                    range "1..8";
                  }
                } //policer

                leaf queue {
                  type int32 {
                    range "1..8";
                  }
                } //queue

              } //container action

              container description {
                description
                    "Description for this entry";
                leaf description-string {
                  type string {
                    length "1..80";
                  }
                } //description-string

              } //container description

              container match {
                description
                    "Specify IP match criteria for this policy";
                leaf protocol {
                  type string;
                  description
                      "Attribute protocol-id for match";
                } //protocol

                container dscp {
                  description
                      "Specify DSCP match";
                  leaf dscp-name {
                    type string {
                      length "1..32";
                    }
                    description
                        "Attribute dscp-name for dscp";
                  } //dscp-name

                } //container dscp

                container dst-ip {
                  description
                      "Specify destination IP and mask match";
                  leaf ip-address-mask {
                    type inet:ip-prefix;
                    description
                        "<ip-address>/<mask>";
                  } //ip-address-mask

                  leaf ip-address {
                    type inet:ip-address;
                    description
                        "Attribute ip-address for dst-ip";
                  } //ip-address

                  leaf ipv4-address-mask {
                    type string;
                    description
                        "a.b.c.d any address mask expressed as dotted quad [0..255]";
                  } //ipv4-address-mask

                } //container dst-ip

                container dst-port {
                  description
                      "Specify destination TCP/UDP port match";
                  leaf lt-gt-eq {
                    type enumeration {
                      enum lt;
                      enum gt;
                      enum eq;
                    }
                    description
                        "operators";
                  } //lt-gt-eq

                  leaf dst-port-number {
                    type string;
                    description
                        "Attribute dst-port-number for dst-port";
                  } //dst-port-number

                  leaf-list range {
                    type string;
                    max-elements 2;
                    description
                        "dst-port-number";
                  } //range

                } //container dst-port

                container fragment {
                  description
                      "Specify match criteria applies to IP fragments";
                  leaf true-false {
                    type enumeration {
                      enum true;
                      enum false;
                    }
                    description
                        "keywords - specify fragment match";
                  } //true-false

                } //container fragment

                container icmp-type {
                  description
                      "Configure ICMP type match condition";
                  leaf icmp-type {
                    type string;
                    description
                        "Attribute icmp-type for icmp-type";
                  } //icmp-type

                } //container icmp-type

                container src-ip {
                  description
                      "Specify source IP and mask match";
                  leaf ip-address-mask {
                    type inet:ip-prefix;
                    description
                        "<ip-address>/<mask>";
                  } //ip-address-mask

                  leaf ip-address {
                    type inet:ip-address;
                    description
                        "Attribute ip-address for src-ip";
                  } //ip-address

                  leaf ipv4-address-mask {
                    type string;
                    description
                        "a.b.c.d any address mask expressed as dotted quad [0..255]";
                  } //ipv4-address-mask

                } //container src-ip

                container src-port {
                  description
                      "Specify source TCP/UDP port match";
                  leaf lt-gt-eq {
                    type enumeration {
                      enum lt;
                      enum gt;
                      enum eq;
                    }
                    description
                        "operators";
                  } //lt-gt-eq

                  leaf src-port-number {
                    type string;
                    description
                        "Attribute src-port-number for src-port";
                  } //src-port-number

                  leaf-list range {
                    type string;
                    max-elements 2;
                    description
                        "src-port-number";
                  } //range

                } //container src-port

              } //container match

            } //list entry

          } //container ip-criteria

          container ipv6-criteria {
            presence
                "Configure IPv6 match criteria";
            container renum {
              description
                  "Renumber an entry";
              leaf old-entry-id {
                type uint32 {
                  range "1..65535";
                }
              } //old-entry-id

              leaf new-entry-id {
                type uint32 {
                  range "1..65535";
                }
              } //new-entry-id

            } //container renum

            list entry {
              key "entry-id";
              description
                  "Configure an IPv6 based policy entry";
              leaf entry-id {
                type uint32 {
                  range "1..65535";
                }
              } //entry-id

              container action {
                description
                    "Specify action fc, policer, port-group redirection, queue and priority";
                leaf fc {
                  type enumeration {
                    enum be;
                    enum l2;
                    enum af;
                    enum l1;
                    enum h2;
                    enum ef;
                    enum h1;
                    enum nc;
                  }
                } //fc

                leaf profile {
                  type enumeration {
                    enum in;
                    enum out;
                    enum exceed;
                    enum inplus;
                  }
                } //profile

                leaf port-redirect-group {
                  type boolean;
                  description
                      "keyword";
                } //port-redirect-group

                leaf policer {
                  type uint32 {
                    range "1..8";
                  }
                } //policer

                leaf queue {
                  type int32 {
                    range "1..8";
                  }
                } //queue

              } //container action

              container description {
                description
                    "Description for this entry";
                leaf description-string {
                  type string {
                    length "1..80";
                  }
                } //description-string

              } //container description

              container match {
                description
                    "Specify IPv6 match criteria for this policy";
                leaf next-header {
                  type string;
                  description
                      "Attribute next-header for match";
                } //next-header

                container dscp {
                  description
                      "Specify DSCP match";
                  leaf dscp-name {
                    type string {
                      length "1..32";
                    }
                    description
                        "Attribute dscp-name for dscp";
                  } //dscp-name

                } //container dscp

                container dst-ip {
                  description
                      "Specify destination IPv6 and mask match";
                  leaf ipv6-address-prefix-length {
                    type string;
                    description
                        "<ipv6-address>/<prefix-length>";
                  } //ipv6-address-prefix-length

                  leaf ipv6-address {
                    type inet:ipv6-address;
                    description
                        "Attribute ipv6-address for dst-ip";
                  } //ipv6-address

                  leaf ipv6-address-1 {
                    type inet:ipv6-address;
                    description
                        "Attribute ipv6-address for dst-ip";
                  } //ipv6-address-1

                } //container dst-ip

                container dst-port {
                  description
                      "Specify destination TCP/UDP port match";
                  leaf lt-gt-eq {
                    type enumeration {
                      enum lt;
                      enum gt;
                      enum eq;
                    }
                    description
                        "operators";
                  } //lt-gt-eq

                  leaf dst-port-number {
                    type string;
                    description
                        "Attribute dst-port-number for dst-port";
                  } //dst-port-number

                  leaf-list range {
                    type string;
                    max-elements 2;
                    description
                        "dst-port-number";
                  } //range

                } //container dst-port

                container fragment {
                  description
                      "Specify match criteria applies to IPv6 fragments";
                  leaf true-false-first-only-non-first-only {
                    type enumeration {
                      enum true;
                      enum false;
                      enum first-only;
                      enum non-first-only;
                    }
                    description
                        "keywords - specify fragment match";
                  } //true-false-first-only-non-first-only

                } //container fragment

                container icmp-type {
                  description
                      "Configure ICMP type match condition";
                  leaf icmp-type {
                    type string;
                    description
                        "Attribute icmp-type for icmp-type";
                  } //icmp-type

                } //container icmp-type

                container src-ip {
                  description
                      "Specify source IPv6 and mask match";
                  leaf ipv6-address-prefix-length {
                    type string;
                    description
                        "<ipv6-address>/<prefix-length>";
                  } //ipv6-address-prefix-length

                  leaf ipv6-address {
                    type inet:ipv6-address;
                    description
                        "Attribute ipv6-address for src-ip";
                  } //ipv6-address

                  leaf ipv6-address-mask {
                    type inet:ipv6-address;
                    description
                        "Attribute ipv6-address-mask for src-ip";
                  } //ipv6-address-mask

                } //container src-ip

                container src-port {
                  description
                      "Specify source TCP/UDP port match";
                  leaf lt-gt-eq {
                    type enumeration {
                      enum lt;
                      enum gt;
                      enum eq;
                    }
                    description
                        "operators";
                  } //lt-gt-eq

                  leaf src-port-number {
                    type string;
                    description
                        "Attribute src-port-number for src-port";
                  } //src-port-number

                  leaf-list range {
                    type string;
                    max-elements 2;
                    description
                        "src-port-number";
                  } //range

                } //container src-port

              } //container match

            } //list entry

          } //container ipv6-criteria

        } //container egress

        container ingress {
          description
              "Configure ingress parameters";
          container default-action {
            description
                "Specify default forwarding class and profile marking";
            leaf fc {
              type enumeration {
                enum be;
                enum l2;
                enum af;
                enum l1;
                enum h2;
                enum ef;
                enum h1;
                enum nc;
              }
            } //fc

            leaf profile {
              type enumeration {
                enum in;
                enum out;
              }
              description
                  "keywords - specify type of marking to be done";
            } //profile

          } //container default-action

          list dot1p {
            key "dot1p-priority";
            description
                "Configure Dot1p mappings";
            leaf dot1p-priority {
              type int32 {
                range "0..7";
              }
            } //dot1p-priority

            leaf fc {
              type enumeration {
                enum be;
                enum l2;
                enum af;
                enum l1;
                enum h2;
                enum ef;
                enum h1;
                enum nc;
              }
            } //fc

            leaf profile {
              type enumeration {
                enum in;
                enum out;
                enum use-de;
              }
              description
                  "Keywords";
            } //profile

          } //list dot1p

          list dscp {
            key "dscp-name";
            description
                "Configure DSCP mappings";
            leaf dscp-name {
              type string {
                length "1..32";
              }
              description
                  "Attribute dscp-name for dscp";
            } //dscp-name

            leaf fc {
              type enumeration {
                enum be;
                enum l2;
                enum af;
                enum l1;
                enum h2;
                enum ef;
                enum h1;
                enum nc;
              }
            } //fc

            leaf profile {
              type enumeration {
                enum in;
                enum out;
              }
              description
                  "keywords - specify type of marking to be done";
            } //profile

          } //list dscp

          leaf ler-use-dscp {
            type boolean;
            description
                "Specify the LERs to use DSCP marking instead of LSPEXP";
          }

          list lsp-exp {
            key "lsp-exp-value";
            description
                "Configure LSP-EXP mappings";
            leaf lsp-exp-value {
              type int32 {
                range "0..7";
              }
            } //lsp-exp-value

            leaf fc {
              type enumeration {
                enum be;
                enum l2;
                enum af;
                enum l1;
                enum h2;
                enum ef;
                enum h1;
                enum nc;
              }
            } //fc

            leaf profile {
              type enumeration {
                enum in;
                enum out;
              }
              description
                  "keywords - specify type of marking to be done";
            } //profile

          } //list lsp-exp

          list fc {
            key "fc-name";
            description
                "Configure a forwarding class";
            leaf fc-name {
              type enumeration {
                enum be;
                enum l2;
                enum af;
                enum l1;
                enum h2;
                enum ef;
                enum h1;
                enum nc;
              }
            } //fc-name

            list fp-redirect-group {
              key "policer-type";
              description
                  "Configure QoS ingress network fp-redirect unicast, multicast, broadcast and 
                   unknown policer";
              leaf policer-type {
                type enumeration {
                  enum broadcast-policer;
                  enum mcast-policer;
                  enum unknown-policer;
                  enum policer;
                }
              } //policer-type

              leaf policer-id {
                type uint32 {
                  range "1..32";
                }
              } //policer-id

            } //list fp-redirect-group

          } //list fc

          container ip-criteria {
            presence
                "Configure IP match criteria";
            container renum {
              description
                  "Renumber an entry";
              leaf old-entry-id {
                type uint32 {
                  range "1..65535";
                }
              } //old-entry-id

              leaf new-entry-id {
                type uint32 {
                  range "1..65535";
                }
              } //new-entry-id

            } //container renum

            list entry {
              key "entry-id";
              description
                  "Configure an IP based policy entry";
              leaf entry-id {
                type uint32 {
                  range "1..65535";
                }
              } //entry-id

              container action {
                description
                    "Specify action fc and priority";
                leaf fc {
                  type enumeration {
                    enum be;
                    enum l2;
                    enum af;
                    enum l1;
                    enum h2;
                    enum ef;
                    enum h1;
                    enum nc;
                  }
                } //fc

                leaf profile {
                  type enumeration {
                    enum in;
                    enum out;
                  }
                  description
                      "keywords - specify type of marking to be done";
                } //profile

              } //container action

              container description {
                description
                    "Description for this entry";
                leaf description-string {
                  type string {
                    length "1..80";
                  }
                } //description-string

              } //container description

              container match {
                description
                    "Specify IP match criteria for this policy";
                leaf protocol {
                  type string;
                  description
                      "Attribute protocol-id for match";
                } //protocol

                container dscp {
                  description
                      "Specify DSCP match";
                  leaf dscp-name {
                    type string {
                      length "1..32";
                    }
                    description
                        "Attribute dscp-name for dscp";
                  } //dscp-name

                } //container dscp

                container dst-ip {
                  description
                      "Specify destination IP and mask match";
                  leaf ip-address-mask {
                    type inet:ip-prefix;
                    description
                        "<ip-address>/<mask>";
                  } //ip-address-mask

                  leaf ip-address {
                    type inet:ip-address;
                    description
                        "Attribute ip-address for dst-ip";
                  } //ip-address

                  leaf ipv4-address-mask {
                    type string;
                    description
                        "a.b.c.d any address mask expressed as dotted quad [0..255]";
                  } //ipv4-address-mask

                  leaf ip-prefix-list {
                    type string {
                      length "1..32";
                    }
                  } //ip-prefix-list

                } //container dst-ip

                container dst-port {
                  description
                      "Specify destination TCP/UDP port match";
                  leaf lt-gt-eq {
                    type enumeration {
                      enum lt;
                      enum gt;
                      enum eq;
                    }
                    description
                        "operators";
                  } //lt-gt-eq

                  leaf dst-port-number {
                    type string;
                    description
                        "Attribute dst-port-number for dst-port";
                  } //dst-port-number

                  leaf-list range {
                    type string;
                    max-elements 2;
                    description
                        "dst-port-number";
                  } //range

                } //container dst-port

                container fragment {
                  description
                      "Specify match criteria applies to IP fragments";
                  leaf true-false {
                    type enumeration {
                      enum true;
                      enum false;
                    }
                    description
                        "keywords - specify fragment match";
                  } //true-false

                } //container fragment

                container src-ip {
                  description
                      "Specify source IP and mask match";
                  leaf ip-address-mask {
                    type inet:ip-prefix;
                    description
                        "<ip-address>/<mask>";
                  } //ip-address-mask

                  leaf ip-address {
                    type inet:ip-address;
                    description
                        "Attribute ip-address for src-ip";
                  } //ip-address

                  leaf ipv4-address-mask {
                    type string;
                    description
                        "a.b.c.d any address mask expressed as dotted quad [0..255]";
                  } //ipv4-address-mask

                  leaf ip-prefix-list {
                    type string {
                      length "1..32";
                    }
                  } //ip-prefix-list

                } //container src-ip

                container src-port {
                  description
                      "Specify source TCP/UDP port match";
                  leaf lt-gt-eq {
                    type enumeration {
                      enum lt;
                      enum gt;
                      enum eq;
                    }
                    description
                        "operators";
                  } //lt-gt-eq

                  leaf src-port-number {
                    type string;
                    description
                        "Attribute src-port-number for src-port";
                  } //src-port-number

                  leaf-list range {
                    type string;
                    max-elements 2;
                    description
                        "src-port-number";
                  } //range

                } //container src-port

              } //container match

            } //list entry

          } //container ip-criteria

          container ipv6-criteria {
            presence
                "Configure IPv6 match criteria";
            container renum {
              description
                  "Renumber an entry";
              leaf old-entry-id {
                type uint32 {
                  range "1..65535";
                }
              } //old-entry-id

              leaf new-entry-id {
                type uint32 {
                  range "1..65535";
                }
              } //new-entry-id

            } //container renum

            list entry {
              key "entry-id";
              description
                  "Configure an IPv6 based policy entry";
              leaf entry-id {
                type uint32 {
                  range "1..65535";
                }
              } //entry-id

              container action {
                description
                    "Specify action fc and priority";
                leaf fc {
                  type enumeration {
                    enum be;
                    enum l2;
                    enum af;
                    enum l1;
                    enum h2;
                    enum ef;
                    enum h1;
                    enum nc;
                  }
                } //fc

                leaf profile {
                  type enumeration {
                    enum in;
                    enum out;
                  }
                  description
                      "keywords - specify type of marking to be done";
                } //profile

              } //container action

              container description {
                description
                    "Description for this entry";
                leaf description-string {
                  type string {
                    length "1..80";
                  }
                } //description-string

              } //container description

              container match {
                description
                    "Specify IPv6 match criteria for this policy";
                leaf next-header {
                  type string;
                  description
                      "Attribute next-header for match";
                } //next-header

                container dscp {
                  description
                      "Specify DSCP match";
                  leaf dscp-name {
                    type string {
                      length "1..32";
                    }
                    description
                        "Attribute dscp-name for dscp";
                  } //dscp-name

                } //container dscp

                container dst-ip {
                  description
                      "Specify destination IPv6 and mask match";
                  leaf ipv6-address-prefix-length {
                    type string;
                    description
                        "<ipv6-address>/<prefix-length>";
                  } //ipv6-address-prefix-length

                  leaf ipv6-address {
                    type inet:ipv6-address;
                    description
                        "Attribute ipv6-address for dst-ip";
                  } //ipv6-address

                  leaf ipv6-address-1 {
                    type inet:ipv6-address;
                    description
                        "Attribute ipv6-address for dst-ip";
                  } //ipv6-address-1

                  leaf ipv6-prefix-list {
                    type string {
                      length "1..32";
                    }
                  } //ipv6-prefix-list

                } //container dst-ip

                container dst-port {
                  description
                      "Specify destination TCP/UDP port match";
                  leaf lt-gt-eq {
                    type enumeration {
                      enum lt;
                      enum gt;
                      enum eq;
                    }
                    description
                        "operators";
                  } //lt-gt-eq

                  leaf dst-port-number {
                    type string;
                    description
                        "Attribute dst-port-number for dst-port";
                  } //dst-port-number

                  leaf-list range {
                    type string;
                    max-elements 2;
                    description
                        "dst-port-number";
                  } //range

                } //container dst-port

                container fragment {
                  description
                      "Specify match criteria applies to IPv6 fragments";
                  leaf true-false-first-only-non-first-only {
                    type enumeration {
                      enum true;
                      enum false;
                      enum first-only;
                      enum non-first-only;
                    }
                    description
                        "keywords - specify fragment match";
                  } //true-false-first-only-non-first-only

                } //container fragment

                container src-ip {
                  description
                      "Specify source IPv6 and mask match";
                  leaf ipv6-address-prefix-length {
                    type string;
                    description
                        "<ipv6-address>/<prefix-length>";
                  } //ipv6-address-prefix-length

                  leaf ipv6-address {
                    type inet:ipv6-address;
                    description
                        "Attribute ipv6-address for src-ip";
                  } //ipv6-address

                  leaf ipv6-address-mask {
                    type inet:ipv6-address;
                    description
                        "Attribute ipv6-address-mask for src-ip";
                  } //ipv6-address-mask

                  leaf ipv6-prefix-list {
                    type string {
                      length "1..32";
                    }
                  } //ipv6-prefix-list

                } //container src-ip

                container src-port {
                  description
                      "Specify source TCP/UDP port match";
                  leaf lt-gt-eq {
                    type enumeration {
                      enum lt;
                      enum gt;
                      enum eq;
                    }
                    description
                        "operators";
                  } //lt-gt-eq

                  leaf src-port-number {
                    type string;
                    description
                        "Attribute src-port-number for src-port";
                  } //src-port-number

                  leaf-list range {
                    type string;
                    max-elements 2;
                    description
                        "src-port-number";
                  } //range

                } //container src-port

              } //container match

            } //list entry

          } //container ipv6-criteria

        } //container ingress

      } //list network

      list network-ingress {
        key "name";
        description
            "Configure network-ingress parameters";
        leaf name {
          type string {
            length "1..64";
          }
        } //name

        container description {
          description
              "Description for this policy";
          leaf description-string {
            type string {
              length "1..80";
            }
          } //description-string

        } //container description

        container ingress-classification-policy {
          description
              "Attach ingress-cos-policy policy";
          leaf name {
            type string {
              length "1..64";
            }
          } //name

        } //container ingress-classification-policy

        container scope {
          description
              "Specify scope of the policy";
          leaf exclusive-template {
            type enumeration {
              enum exclusive;
              enum template;
            }
            description
                "keywords - specify type of policy";
          } //exclusive-template

        } //container scope

        list fc {
          key "fc";
          description
              "Configure forwarding-class to meter mappings";
          leaf fc {
            type string;
            description
                "Attribute fc for fc";
          } //fc

          container multicast-policer {
            description
                "Specify the multicast-policer";
            leaf policer-id {
              type int32 {
                range "1..16";
              }
              description
                  "[1..16]";
            } //policer-id

          } //container multicast-policer

          container policer {
            description
                "Specify the unicast-policer";
            leaf policer-id {
              type int32 {
                range "1..16";
              }
              description
                  "[1..16]";
            } //policer-id

          } //container policer

        } //list fc

        list policer {
          key "policer-id";
          description
              "Configure a policer";
          leaf policer-id {
            type int32 {
              range "1..16";
            }
            description
                "[1..16]";
          } //policer-id

          container adaptation-rule {
            description
                "Specify the CIR and PIR adaptation rules";
            leaf pir {
              type enumeration {
                enum max;
                enum min;
                enum closest;
              }
            } //pir

            leaf cir {
              type enumeration {
                enum max;
                enum min;
                enum closest;
              }
            } //cir

          } //container adaptation-rule

          container cbs {
            description
                "Specify Cbs";
            leaf size {
              type string;
              description
                  "Attribute size for cbs";
            } //size

            leaf cbs-id {
              type enumeration {
                enum bytes;
                enum kilobytes;
              }
            } //cbs-id

          } //container cbs

          container mbs {
            description
                "Specify Mbs";
            leaf size {
              type string;
              description
                  "Attribute size for mbs";
            } //size

            leaf mbs-id {
              type enumeration {
                enum bytes;
                enum kilobytes;
              }
            } //mbs-id

          } //container mbs

          container rate {
            description
                "Specify rates (CIR and PIR)";
            leaf pir-rate {
              type string;
              description
                  "[144..400000000|max] Kbps";
            } //pir-rate

            leaf cir {
              type string;
              description
                  "[0..400000000|max] Kbps";
            } //cir

          } //container rate

          container stat-mode {
            description
                "Specify policer stat-mode";
            leaf stat-mode {
              type enumeration {
                enum no-stats;
                enum offered-profile-with-discards;
              }
            } //stat-mode

          } //container stat-mode

        } //list policer

      } //list network-ingress

      list network-queue {
        key "policy-name";
        description
            "Configure network-queue policy";
        leaf policy-name {
          type string {
            length "1..32";
          }
        } //policy-name

        container description {
          description
              "Description for this policy";
          leaf description-string {
            type string {
              length "1..80";
            }
          } //description-string

        } //container description

        container hs-attachment-policy {
          description
              "Specify HS attachment policy";
          leaf policy-name {
            type string;
          } //policy-name

        } //container hs-attachment-policy

        container egress-hsmda {
          description
              "Configure Egress Hsmda";
          container packet-byte-offset {
            description
                "Configure egress Hsmda packet byte offset";
            leaf add {
              type uint32 {
                range "1..31";
              }
            } //add

            leaf subtract {
              type string;
              description
                  "Attribute sub-bytes for packet-byte-offset";
            } //subtract

          } //container packet-byte-offset

          container wrr-policy {
            description
                "Configure egress Hsmda-wrr policy";
            leaf wrr-policy-name {
              type string {
                length "1..32";
              }
            } //wrr-policy-name

          } //container wrr-policy

          list queue {
            key "queue-id";
            description
                "Configure egress Hsmda queue";
            leaf queue-id {
              type int32 {
                range "1..8";
              }
            } //queue-id

            container adaptation-rule {
              description
                  "Specify the PIR adaptation rule";
              leaf pir {
                type enumeration {
                  enum max;
                  enum min;
                  enum closest;
                }
              } //pir

            } //container adaptation-rule

            container burst-limit {
              description
                  "Specify Burst limit";
              leaf size {
                type uint32 {
                  range "1..1000000";
                }
                description
                    "[1..1000000]";
              } //size

              leaf bytes-kilobytes {
                type enumeration {
                  enum bytes;
                  enum kilobytes;
                }
              } //bytes-kilobytes

            } //container burst-limit

            container mbs {
              description
                  "Specify MBS";
              leaf size {
                type string;
                description
                    "[0..2625 kilobytes | 0..2688000 bytes | default]";
              } //size

              leaf mbs-id {
                type enumeration {
                  enum bytes;
                  enum kilobytes;
                }
              } //mbs-id

            } //container mbs

            container percent-rate {
              description
                  "Specify percent rate (PIR)";
              leaf pir-percent {
                type string;
                description
                    "[0.01..100.00]";
              } //pir-percent

            } //container percent-rate

            container slope-policy {
              description
                  "Specify HSMDA Slope-Policy name";
              leaf slope-policy-name {
                type string {
                  length "1..32";
                }
              } //slope-policy-name

            } //container slope-policy

            container wrr-weight {
              description
                  "Specify weight";
              leaf weight {
                type int32 {
                  range "1..32";
                }
                description
                    "Attribute weight for wrr-weight";
              } //weight

            } //container wrr-weight

          } //list queue

        } //container egress-hsmda

        list fc {
          key "fc-name";
          description
              "Configure forwarding-class to queue mappings";
          leaf fc-name {
            type enumeration {
              enum be;
              enum l2;
              enum af;
              enum l1;
              enum h2;
              enum ef;
              enum h1;
              enum nc;
            }
            description
                "<be|l2|af|l1|h2|ef|h1|nc> - keywords";
          } //fc-name

          container multicast-queue {
            description
                "Specify the multicast-queue";
            leaf queue-id {
              type int32 {
                range "1..16";
              }
            } //queue-id

          } //container multicast-queue

          container queue {
            description
                "Specify the unicast-queue";
            leaf queue-id {
              type int32 {
                range "1..16";
              }
            } //queue-id

          } //container queue

          container egress-hsmda {
            description
                "Specify Egress Hsmda";
            container queue {
              description
                  "Specify the egress Hsmda queue";
              leaf queue-id {
                type int32 {
                  range "1..8";
                }
              } //queue-id

            } //container queue

          } //container egress-hsmda

        } //list fc

        list hs-wrr-group {
          key "group-id";
          description
              "Configure HS WRR Group";
          leaf group-id {
            type uint16 {
              range "1..2";
            }
            description
                "[1..2]";
          } //group-id

          container adaptation-rule {
            description
                "Specify the PIR adaptation rules";
            leaf pir {
              type enumeration {
                enum max;
                enum min;
                enum closest;
              }
            } //pir

          } //container adaptation-rule

          container hs-class-weight {
            description
                "Specify class weight";
            leaf weight {
              type enumeration {
                enum 1;
                enum 2;
                enum 4;
                enum 8;
              }
            } //weight

          } //container hs-class-weight

          container rate {
            description
                "Specify rates (PIR)";
            leaf percent {
              type uint32 {
                range "1..100";
              }
            } //percent

          } //container rate

        } //list hs-wrr-group

        list queue {
          key "queue-id";
          description
              "Configure a queue";
          leaf queue-id {
            type int32 {
              range "1..16";
            }
          } //queue-id

          leaf multipoint {
            type boolean;
            description
                "keyword - mandatory while creating a multipoint queue";
          } //multipoint

          leaf queue-type {
            type enumeration {
              enum expedite;
              enum best-effort;
              enum auto-expedite;
            }
            description
                "expedite|best-effort|auto-expedite - keywords";
          } //queue-type

          container adaptation-rule {
            description
                "Specify the information rate adaptation rules";
            leaf pir {
              type enumeration {
                enum max;
                enum min;
                enum closest;
              }
            } //pir

            leaf cir {
              type enumeration {
                enum max;
                enum min;
                enum closest;
              }
            } //cir

            leaf fir {
              type enumeration {
                enum max;
                enum min;
                enum closest;
              }
            } //fir

          } //container adaptation-rule

          container avg-frame-overhead {
            description
                "Configure average frame overhead";
            leaf percentage {
              type string;
              description
                  "[0.00..100.00]";
            } //percentage

          } //container avg-frame-overhead

          container cbs {
            description
                "Specify CBS size";
            leaf percentage {
              type string;
              description
                  "[0.00..100.00]";
            } //percentage

          } //container cbs

          container high-prio-only {
            status "obsolete";
            description
                "Specify high priority only burst size";
            leaf percent {
              type string;
              description
                  "[0..100 | default]";
            } //percent

          } //container high-prio-only

          leaf hs-alt-port-class-pool {
            type boolean;
            description
                "Specify HS alternate class port pool policy";
          }

          container hs-class-weight {
            description
                "Specify HS class weight";
            leaf weight {
              type enumeration {
                enum 1;
                enum 2;
                enum 4;
                enum 8;
              }
            } //weight

          } //container hs-class-weight

          container hs-mbs {
            description
                "Specify HS MBS size";
            leaf percent-of-queue-rate {
              type string;
              description
                  "[0.00..100.00]";
            } //percent-of-queue-rate

          } //container hs-mbs

          container hs-wred-queue {
            description
                "Configure WRED queue";
            leaf policy {
              type string {
                length "1..32";
              }
            } //policy

          } //container hs-wred-queue

          container hs-wrr-weight {
            description
                "Specify HS WRR weight";
            leaf weight {
              type uint16 {
                range "1..127";
              }
              description
                  "[1..127]";
            } //weight

          } //container hs-wrr-weight

          container mbs {
            description
                "Specify MBS size";
            leaf percentage {
              type string;
              description
                  "[0.00..100.00]";
            } //percentage

          } //container mbs

          container pool {
            description
                "Configure named pool for this queue";
            leaf pool-name {
              type string {
                length "1..32";
              }
            } //pool-name

          } //container pool

          container port-parent {
            description
                "Specify the port-scheduler to which this queue feeds";
            leaf weight {
              type uint32 {
                range "0..100";
              }
            } //weight

            leaf level {
              type uint32 {
                range "1..8";
              }
            } //level

            leaf cir-weight {
              type uint32 {
                range "0..100";
              }
            } //cir-weight

            leaf cir-level {
              type uint32 {
                range "0..8";
              }
            } //cir-level

          } //container port-parent

          container rate {
            description
                "Specify information rates";
            leaf pir-percent {
              type uint32 {
                range "1..100";
              }
            } //pir-percent

            leaf cir {
              type uint32 {
                range "0..100";
              }
            } //cir

            leaf fir {
              type uint32 {
                range "0..100";
              }
            } //fir

          } //container rate

          container drop-tail {
            description
                "Specify drop tail";
            container low {
              description
                  "Specify low drop-tail";
              container percent-reduction-from-mbs {
                description
                    "Specify low drop tail percent reduction from MBS";
                leaf percent {
                  type string;
                  description
                      "[0..100|default]";
                } //percent

              } //container percent-reduction-from-mbs

            } //container low

          } //container drop-tail

        } //list queue

      } //list network-queue

      list policer-control-policy {
        key "policer-control-policy-name";
        description
            "Configure Qos Policer control Policy";
        leaf policer-control-policy-name {
          type string {
            length "1..32";
          }
        } //policer-control-policy-name

        container description {
          description
              "Description for this policy";
          leaf description-string {
            type string {
              length "1..80";
            }
          } //description-string

        } //container description

        container root {
          description
              "Specify Root Configuration";
          container max-rate {
            description
                "Configure Max Rate in kilobits-per-second";
            leaf rate {
              type string;
              description
                  "[1..6400000000|max] Kbps";
            } //rate

          } //container max-rate

          leaf profile-preferred {
            type boolean;
            description
                "Configure Profile Preferred status";
          }

          container priority-mbs-thresholds {
            description
                "Configure priority mbs thresholds";
            container min-thresh-separation {
              description
                  "configure min threshold separation";
              leaf size {
                type string;
                description
                    "[0..16777216 | default]";
              } //size

              leaf min-thresh-separation-id {
                type enumeration {
                  enum bytes;
                  enum kilobytes;
                }
              } //min-thresh-separation-id

            } //container min-thresh-separation

            list priority {
              key "level";
              description
                  "Configure Priority Levels";
              leaf level {
                type uint32 {
                  range "1..8";
                }
              } //level

              container mbs-contribution {
                description
                    "Configure mbs size";
                leaf size {
                  type string;
                  description
                      "[0..16777216 | default]";
                } //size

                leaf mbs-contribution-id {
                  type enumeration {
                    enum bytes;
                    enum kilobytes;
                  }
                } //mbs-contribution-id

                leaf fixed {
                  type boolean;
                } //fixed

              } //container mbs-contribution

            } //list priority

          } //container priority-mbs-thresholds

        } //container root

        list tier {
          key "tier";
          description
              "Specify Tier Configuration";
          leaf tier {
            type uint32 {
              range "1..2";
            }
          } //tier

          list arbiter {
            key "arbiter-name";
            description
                "Configure arbiters";
            leaf arbiter-name {
              type string {
                length "1..32";
              }
            } //arbiter-name

            container description {
              description
                  "Descripton for this arbiter";
              leaf description-string {
                type string {
                  length "1..80";
                }
              } //description-string

            } //container description

            container parent {
              description
                  "Specify parent configuration";
              leaf arbiter-name-root {
                type string {
                  length "1..32";
                }
              } //arbiter-name-root

              leaf weight {
                type uint32 {
                  range "1..100";
                }
              } //weight

              leaf level {
                type uint32 {
                  range "1..8";
                }
              } //level

            } //container parent

            container rate {
              description
                  "Configure rate for the arbiter";
              leaf rate {
                type string;
                description
                    "[1..6400000000|max] Kbps";
              } //rate

            } //container rate

          } //list arbiter

        } //list tier

      } //list policer-control-policy

      list port-qos-policy {
        key "port-qos-policy-name";
        description
            "Configure a Port QoS Policy.";
        leaf port-qos-policy-name {
          type string;
          description
              "<name:64 char max>";
        } //port-qos-policy-name

        container description {
          description
              "Description for this port-qos policy.";
          leaf description-string {
            type string {
              length "1..80";
            }
          } //description-string

        } //container description

        container scope {
          description
              "Scope of the policy.";
          leaf exclusive-template {
            type enumeration {
              enum exclusive;
              enum template;
            }
            description
                "keywords - specify type of policy";
          } //exclusive-template

        } //container scope

        list fc {
          key "fc-name";
          description
              "Configure forwarding-class mappings";
          leaf fc-name {
            type enumeration {
              enum be;
              enum l2;
              enum af;
              enum l1;
              enum h2;
              enum ef;
              enum h1;
              enum nc;
            }
            description
                "be|l2|af|l1|h2|ef|h1|nc - keywords";
          } //fc-name

          container queue {
            description
                "Specify the queue to forward this FC traffic";
            leaf queue-id {
              type int32 {
                range "1..8";
              }
            } //queue-id

          } //container queue

        } //list fc

        list queue {
          key "queue-id";
          description
              "Queue Configurations.";
          leaf queue-id {
            type int32 {
              range "1..8";
            }
          } //queue-id

          container adaptation-rule {
            description
                "Specify the adaptation rules";
            leaf pir {
              type enumeration {
                enum max;
                enum min;
                enum closest;
              }
            } //pir

            leaf cir {
              type enumeration {
                enum max;
                enum min;
                enum closest;
              }
            } //cir

          } //container adaptation-rule

          container queue-mgmt {
            description
                "Queue Management determines the queue management policy attached to this queue";
            leaf queue-mgmt {
              type string {
              }
              description
                  "[64 chars max]";
            } //queue-mgmt

          } //container queue-mgmt

          container wrr-weights {
            description
                "To attach wrr-weights identifier";
            leaf wrr-weights-id {
              type uint32 {
                range "1..8";
              }
            } //wrr-weights-id

          } //container wrr-weights

          container scheduler-mode {
            description
                "Specifies scheduler mode of this queue";
            leaf scheduler-mode {
              type enumeration {
                enum wfq;
                enum strict-priority;
              }
            } //scheduler-mode

            container percent-rate {
              description
                  "Specify PIR and CIR in percent";
              leaf pir-percentage {
                type string;
                description
                    "[0.01..100.00]";
              } //pir-percentage

              leaf cir {
                type string;
                description
                    "[0.00..100.00]";
              } //cir

            } //container percent-rate

            container pir-weight {
              description
                  "Specifies the pir weight";
              leaf pir-weight {
                type uint32 {
                  range "1..255";
                }
              } //pir-weight

            } //container pir-weight

          } //container scheduler-mode

        } //list queue

        list wrr-weights {
          key "wrr-weights-id";
          description
              "Configure a unicast multicast weighted fair queue.";
          leaf wrr-weights-id {
            type uint32 {
              range "1..8";
            }
          } //wrr-weights-id

          container mc-weight {
            description
                "Configure multicast weights";
            leaf mc-weight {
              type uint32 {
                range "1..255";
              }
            } //mc-weight

          } //container mc-weight

          container uc-weight {
            description
                "Configure unicast weight";
            leaf uc-weight {
              type uint32 {
                range "1..255";
              }
            } //uc-weight

          } //container uc-weight

        } //list wrr-weights

      } //list port-qos-policy

      list port-scheduler-policy {
        key "port-scheduler-name";
        description
            "Configure a port scheduler policy";
        leaf port-scheduler-name {
          type string {
            length "1..32";
          }
        } //port-scheduler-name

        container description {
          description
              "Description for this policy";
          leaf description-string {
            type string {
              length "1..80";
            }
          } //description-string

        } //container description

        leaf dist-lag-rate-shared {
          type boolean;
          description
              "Enable absolute rate sharing in distribute lag mode";
        }

        list level {
          key "priority-level";
          description
              "Configure priority level parameters";
          leaf priority-level {
            type uint32 {
              range "1..8";
            }
          } //priority-level

          leaf rate {
            type string;
            description
                "[1..6400000000|max] Kbps";
          } //rate

          leaf percent-rate {
            type string;
            description
                "[0.01..100.00]";
          } //percent-rate

          leaf cir {
            type string;
            description
                "[0..6400000000|max] Kbps";
          } //cir

          leaf percent-cir {
            type string;
            description
                "[0.00..100.00]";
          } //percent-cir

          leaf group {
            type string;
          } //group

          leaf weight {
            type uint32 {
              range "1..100";
            }
          } //weight

          leaf monitor-threshold {
            type uint32 {
              range "0..100";
            }
          } //monitor-threshold

        } //list level

        container max-rate {
          description
              "Configure the maximum rate";
          leaf pir-rate {
            type string;
            description
                "[1..6400000000|max] Kbps";
          } //pir-rate

          leaf percent {
            type string;
            description
                "[0.01..100.00]";
          } //percent

        } //container max-rate

        container monitor-threshold {
          description
              "Configure monitor threshold percentage";
          leaf percent {
            type uint32 {
              range "0..100";
            }
          } //percent

        } //container monitor-threshold

        container orphan-override {
          description
              "Configure port scheduler policy orphan settings";
          leaf weight {
            type uint32 {
              range "0..100";
            }
          } //weight

          leaf level {
            type uint8 {
              range "1..8";
            }
          } //level

          leaf cir-weight {
            type uint32 {
              range "0..1000";
            }
            description
                "[0..100]";
          } //cir-weight

          leaf cir-level {
            type uint8 {
              range "0..8";
            }
          } //cir-level

        } //container orphan-override

        list group {
          key "name";
          description
              "Configure port-scheduler-policy group";
          leaf name {
            type string {
              length "1..32";
            }
          } //name

          container monitor-threshold {
            description
                "Configure monitor threshold percentage";
            leaf percent {
              type uint32 {
                range "0..100";
              }
            } //percent

          } //container monitor-threshold

          container percent-rate {
            description
                "Specify percent rates (CIR and PIR)";
            leaf pir-percent {
              type string;
              description
                  "[0.01..100.00]";
            } //pir-percent

            leaf cir {
              type string;
              description
                  "[0.00..100.00]";
            } //cir

          } //container percent-rate

          container rate {
            description
                "Specify rates (CIR and PIR)";
            leaf pir-rate {
              type string;
              description
                  "[1..6400000000|max] Kbps";
            } //pir-rate

            leaf cir {
              type string;
              description
                  "[0..6400000000|max] Kbps";
            } //cir

          } //container rate

        } //list group

      } //list port-scheduler-policy

      list post-policer-mapping {
        key "mapping-policy-name";
        description
            "Configure a post policer mapping policy";
        leaf mapping-policy-name {
          type string;
        } //mapping-policy-name

        container description {
          description
              "Description for this policy";
          leaf description-string {
            type string {
              length "1..80";
            }
          } //description-string

        } //container description

        list fc {
          key "fc-name profile";
          description
              "Specify FC and profile mapping";
          leaf fc-name {
            type enumeration {
              enum be;
              enum l2;
              enum af;
              enum l1;
              enum h2;
              enum ef;
              enum h1;
              enum nc;
            }
            description
                "be|l2|af|l1|h2|ef|h1|nc - keywords";
          } //fc-name

          leaf profile {
            type enumeration {
              enum in;
              enum out;
              enum exceed;
              enum inplus;
            }
          } //profile

          container maps-to {
            description
                "Specify mapped FC and profile";
            leaf fc {
              type enumeration {
                enum be;
                enum l2;
                enum af;
                enum l1;
                enum h2;
                enum ef;
                enum h1;
                enum nc;
              }
              description
                  "be|l2|af|l1|h2|ef|h1|nc - keywords";
            } //fc

            leaf profile {
              type enumeration {
                enum in;
                enum out;
                enum exceed;
                enum inplus;
              }
            } //profile

          } //container maps-to

        } //list fc

      } //list post-policer-mapping

      list queue-group-redirect-list {
        key "redirect-list-name";
        description
            "Configure a queue-group redirect list";
        leaf redirect-list-name {
          type string;
        } //redirect-list-name

        list match {
          key "field-value";
          description
              "Specify match value for redirecting traffic";
          leaf field-value {
            type string;
            description
                "Attribute field-value for match";
          } //field-value

          leaf instance {
            type uint16 {
              range "1..65535";
            }
          } //instance

        } //list match

        container type {
          description
              "Specify type of redirect list";
          leaf type-id {
            type enumeration {
              enum vxlan-vni;
            }
          } //type-id

        } //container type

      } //list queue-group-redirect-list

      container queue-group-templates {
        description
            "Configure QoS queue groups";
        container egress {
          description
              "Configure QoS egress queue groups";
          list queue-group {
            key "queue-group-name";
            description
                "Configure QoS egress queue-group";
            leaf queue-group-name {
              type string {
                length "1..32";
              }
            } //queue-group-name

            container description {
              description
                  "Configure description for the QoS egress queue-group";
              leaf description-string {
                type string {
                  length "1..80";
                }
              } //description-string

            } //container description

            container hs-attachment-policy {
              description
                  "Specify HS attachment policy";
              leaf policy-name {
                type string;
              } //policy-name

            } //container hs-attachment-policy

            leaf queues-hqos-manageable {
              type boolean;
              description
                  "Enable/Disable HQoS Manageable Queues";
            }

            list fc {
              key "fc-name";
              description
                  "Configure forwarding-class to queue mappings";
              leaf fc-name {
                type enumeration {
                  enum be;
                  enum l2;
                  enum af;
                  enum l1;
                  enum h2;
                  enum ef;
                  enum h1;
                  enum nc;
                }
                description
                    "be|l2|af|l1|h2|ef|h1|nc - keywords";
              } //fc-name

              container queue {
                description
                    "Specify the unicast-queue";
                leaf queue-id {
                  type int32 {
                    range "1..8";
                  }
                } //queue-id

              } //container queue

            } //list fc

            list hs-wrr-group {
              key "group-id";
              description
                  "Configure HS WRR Group";
              leaf group-id {
                type uint16 {
                  range "1..2";
                }
                description
                    "[1..2]";
              } //group-id

              container adaptation-rule {
                description
                    "Specify the PIR adaptation rules";
                leaf pir {
                  type enumeration {
                    enum max;
                    enum min;
                    enum closest;
                  }
                } //pir

              } //container adaptation-rule

              container hs-class-weight {
                description
                    "Specify class weight";
                leaf weight {
                  type enumeration {
                    enum 1;
                    enum 2;
                    enum 4;
                    enum 8;
                  }
                } //weight

              } //container hs-class-weight

              container percent-rate {
                description
                    "Specify percent rate";
                leaf percent {
                  type string;
                  description
                      "[0.01..100.00]";
                } //percent

              } //container percent-rate

              container rate {
                description
                    "Specify rates (PIR)";
                leaf rate {
                  type string;
                  description
                      "Attribute rate for rate";
                } //rate

              } //container rate

            } //list hs-wrr-group

            container hsmda-queues {
              description
                  "Configure HSMDA queues";
              container low-burst-max-class {
                description
                    "Specify low burst max class";
                leaf class {
                  type uint32 {
                    range "1..8";
                  }
                } //class

              } //container low-burst-max-class

              container packet-byte-offset {
                description
                    "Specify a packet offset for HSMDA queue accounting";
                leaf add {
                  type uint32 {
                    range "1..31";
                  }
                } //add

                leaf subtract {
                  type string;
                  description
                      "Attribute sub-bytes for packet-byte-offset";
                } //subtract

              } //container packet-byte-offset

              container wrr-policy {
                description
                    "Configure egress Hsmda-wrr policy";
                leaf wrr-policy-name {
                  type string {
                    length "1..32";
                  }
                } //wrr-policy-name

              } //container wrr-policy

              list queue {
                key "queue-id";
                description
                    "Configure a specific HSMDA queue";
                leaf queue-id {
                  type int32 {
                    range "1..8";
                  }
                } //queue-id

                container adaptation-rule {
                  description
                      "Specify the PIR adaptation rules";
                  leaf pir {
                    type enumeration {
                      enum max;
                      enum min;
                      enum closest;
                    }
                  } //pir

                } //container adaptation-rule

                container burst-limit {
                  description
                      "Specify the Queue Burst limit";
                  leaf size {
                    type uint32 {
                      range "1..1000000";
                    }
                    description
                        "[1..1000000]";
                  } //size

                  leaf bytes-kilobytes {
                    type enumeration {
                      enum bytes;
                      enum kilobytes;
                    }
                  } //bytes-kilobytes

                } //container burst-limit

                container mbs {
                  description
                      "Specify MBS rate";
                  leaf size {
                    type string;
                    description
                        "[0..2625 kilobytes | 0..2688000 bytes | default]";
                  } //size

                  leaf bytes-kilobytes {
                    type enumeration {
                      enum bytes;
                      enum kilobytes;
                    }
                  } //bytes-kilobytes

                } //container mbs

                container rate {
                  description
                      "Specify PIR rates";
                  leaf pir-rate {
                    type string;
                    description
                        "[1..100000000|max] Kbps";
                  } //pir-rate

                } //container rate

                container slope-policy {
                  description
                      "Specify slope policy";
                  leaf hsmda-slope-policy-name {
                    type string {
                      length "1..32";
                    }
                  } //hsmda-slope-policy-name

                } //container slope-policy

                container wrr-weight {
                  description
                      "Specify wrr-weight";
                  leaf weight {
                    type int32 {
                      range "1..32";
                    }
                    description
                        "Attribute weight for wrr-weight";
                  } //weight

                } //container wrr-weight

              } //list queue

            } //container hsmda-queues

            list policer {
              key "policer-id";
              description
                  "Configure QoS egress queue-group policer";
              leaf policer-id {
                type uint32 {
                  range "1..8";
                }
              } //policer-id

              container adaptation-rule {
                description
                    "Specify the CIR and PIR adaptation rules";
                leaf pir {
                  type enumeration {
                    enum max;
                    enum min;
                    enum closest;
                  }
                } //pir

                leaf cir {
                  type enumeration {
                    enum max;
                    enum min;
                    enum closest;
                  }
                } //cir

              } //container adaptation-rule

              container adv-config-policy {
                description
                    "Configure advanced configuration policy";
                leaf adv-config-policy-name {
                  type string {
                    length "1..32";
                  }
                } //adv-config-policy-name

              } //container adv-config-policy

              container cbs {
                description
                    "Specify CBS size";
                leaf size {
                  type string;
                  description
                      "[0..16777216 | default]";
                } //size

                leaf bytes-kilobytes {
                  type enumeration {
                    enum bytes;
                    enum kilobytes;
                  }
                } //bytes-kilobytes

              } //container cbs

              container description {
                description
                    "Configure description for the QoS egress queue-group policer";
                leaf description-string {
                  type string {
                    length "1..80";
                  }
                } //description-string

              } //container description

              leaf enable-exceed-pir {
                type boolean;
                description
                    "Enable/Disable Exceed PIR";
              }

              container high-prio-only {
                description
                    "Specify high priority only percent-of-mbs";
                leaf percent {
                  type string;
                  description
                      "[0..100 | default]";
                } //percent

              } //container high-prio-only

              container mbs {
                description
                    "Specify MBS size";
                leaf size {
                  type string;
                  description
                      "[0..16777216 | default]";
                } //size

                leaf bytes-kilobytes {
                  type enumeration {
                    enum bytes;
                    enum kilobytes;
                  }
                } //bytes-kilobytes

              } //container mbs

              container packet-byte-offset {
                description
                    "Specify packet byte offset";
                leaf add {
                  type uint32 {
                    range "0..31";
                  }
                } //add

                leaf subtract {
                  type string;
                  description
                      "Attribute sub-bytes for packet-byte-offset";
                } //subtract

              } //container packet-byte-offset

              container parent {
                description
                    "Specify the scheduler to which this policer feeds";
                leaf arbiter-name {
                  type string {
                    length "1..32";
                  }
                } //arbiter-name

                leaf weight {
                  type uint32 {
                    range "1..100";
                  }
                } //weight

                leaf level {
                  type uint32 {
                    range "1..8";
                  }
                } //level

              } //container parent

              leaf profile-capped {
                type boolean;
                description
                    "Configure Profile Cap";
              }

              container rate {
                description
                    "Specify rates (CIR and PIR)";
                leaf pir-rate {
                  type string;
                  description
                      "[1..2000000000|max] Kbps";
                } //pir-rate

                leaf cir {
                  type string;
                  description
                      "[0..2000000000|max] Kbps";
                } //cir

              } //container rate

              container stat-mode {
                description
                    "Specify Stat Mode for the policer";
                leaf stat-mode {
                  type enumeration {
                    enum no-stats;
                    enum minimal;
                    enum offered-profile-no-cir;
                    enum offered-profile-cir;
                    enum offered-total-cir;
                    enum offered-limited-capped-cir;
                    enum offered-profile-capped-cir;
                    enum offered-total-cir-exceed;
                    enum offered-four-profile-no-cir;
                    enum offered-total-cir-four-profile;
                  }
                } //stat-mode

              } //container stat-mode

            } //list policer

            list queue {
              key "queue-id";
              description
                  "Configure a queue";
              leaf queue-id {
                type int32 {
                  range "1..8";
                }
              } //queue-id

              leaf queue-type {
                type enumeration {
                  enum expedite;
                  enum best-effort;
                }
                description
                    "expedite|best-effort - keywords";
              } //queue-type

              container adaptation-rule {
                description
                    "Specify the CIR and PIR adaptation rules";
                leaf pir {
                  type enumeration {
                    enum max;
                    enum min;
                    enum closest;
                  }
                } //pir

                leaf cir {
                  type enumeration {
                    enum max;
                    enum min;
                    enum closest;
                  }
                } //cir

              } //container adaptation-rule

              container adv-config-policy {
                description
                    "Configure advanced configuration policy";
                leaf adv-config-policy-name {
                  type string {
                    length "1..32";
                  }
                } //adv-config-policy-name

              } //container adv-config-policy

              container burst-limit {
                description
                    "Specify burst limit";
                leaf size {
                  type string;
                  description
                      "Attribute size for burst-limit";
                } //size

                leaf bytes-kilobytes {
                  type enumeration {
                    enum bytes;
                    enum kilobytes;
                  }
                } //bytes-kilobytes

              } //container burst-limit

              container cbs {
                description
                    "Specify CBS size";
                leaf size-in-kbytes {
                  type string;
                  description
                      "Attribute size-in-kbytes for cbs";
                } //size-in-kbytes

              } //container cbs

              leaf dynamic-mbs {
                type boolean;
                description
                    "Enable/disable Dynamic MBS";
              }

              container hi-low-prio-only {
                status "obsolete";
                description
                    "Specify high-low priority only burst size";
                leaf percent {
                  type string;
                  description
                      "[0..100 | default]";
                } //percent

              } //container hi-low-prio-only

              container high-prio-only {
                status "obsolete";
                description
                    "Specify high priority only burst size";
                leaf percent {
                  type string;
                  description
                      "[0..100 | default]";
                } //percent

              } //container high-prio-only

              leaf hs-alt-port-class-pool {
                type boolean;
                description
                    "Specify HS alternate class port pool policy";
              }

              container hs-class-weight {
                description
                    "Specify HS class weight";
                leaf weight {
                  type enumeration {
                    enum 1;
                    enum 2;
                    enum 4;
                    enum 8;
                  }
                } //weight

              } //container hs-class-weight

              container hs-wred-queue {
                description
                    "Configure WRED queue";
                leaf policy {
                  type string {
                    length "1..32";
                  }
                } //policy

              } //container hs-wred-queue

              container hs-wrr-weight {
                description
                    "Specify HS WRR weight";
                leaf weight {
                  type uint16 {
                    range "1..127";
                  }
                  description
                      "[1..127]";
                } //weight

              } //container hs-wrr-weight

              container mbs {
                description
                    "Specify MBS size";
                leaf size {
                  type string;
                  description
                      "Attribute size for mbs";
                } //size

                leaf bytes-kilobytes {
                  type enumeration {
                    enum bytes;
                    enum kilobytes;
                  }
                  description
                      "keyword";
                } //bytes-kilobytes

              } //container mbs

              container packet-byte-offset {
                description
                    "Specify packet byte offset";
                leaf add {
                  type uint32 {
                    range "0..31";
                  }
                } //add

                leaf subtract {
                  type string;
                  description
                      "Attribute sub-bytes for packet-byte-offset";
                } //subtract

              } //container packet-byte-offset

              container parent {
                description
                    "Specify the scheduler to which this queue feeds";
                leaf scheduler-name {
                  type string {
                    length "1..32";
                  }
                } //scheduler-name

                leaf weight {
                  type uint32 {
                    range "0..100";
                  }
                } //weight

                leaf level {
                  type uint32 {
                    range "1..8";
                  }
                } //level

                leaf cir-weight {
                  type uint32 {
                    range "0..100";
                  }
                } //cir-weight

                leaf cir-level {
                  type uint32 {
                    range "0..8";
                  }
                } //cir-level

              } //container parent

              container percent-rate {
                description
                    "Specify Percent rates (CIR and PIR)";
                leaf pir-percent {
                  type string;
                  description
                      "[0.01..100.00]";
                } //pir-percent

                leaf cir {
                  type string;
                  description
                      "[0.00..100.00]";
                } //cir

              } //container percent-rate

              container pool {
                description
                    "Configure named pool for this queue";
                leaf pool-name {
                  type string {
                    length "1..32";
                  }
                  description
                      "[max 32 chars]";
                } //pool-name

              } //container pool

              container port-parent {
                description
                    "Specify the port-scheduler to which this queue feeds";
                leaf weight {
                  type uint32 {
                    range "0..100";
                  }
                } //weight

                leaf level {
                  type uint32 {
                    range "1..8";
                  }
                } //level

                leaf cir-weight {
                  type uint32 {
                    range "0..100";
                  }
                } //cir-weight

                leaf cir-level {
                  type uint32 {
                    range "0..8";
                  }
                } //cir-level

              } //container port-parent

              container queue-delay {
                description
                    "Specify Queue Delay";
                leaf ms {
                  type uint16 {
                    range "1..5000";
                  }
                } //ms

              } //container queue-delay

              container rate {
                description
                    "Specify rates (CIR and PIR)";
                leaf pir-rate {
                  type string;
                  description
                      "Attribute pir-rate for rate";
                } //pir-rate

                leaf cir {
                  type string;
                  description
                      "Attribute cir-rate for rate";
                } //cir

              } //container rate

              container wred-queue {
                description
                    "Configure WRED queue";
                leaf policy {
                  type string {
                    length "1..32";
                  }
                } //policy

                leaf mode {
                  type enumeration {
                    enum native;
                    enum pool-per-queue;
                  }
                } //mode

                leaf slope-usage {
                  type enumeration {
                    enum default;
                    enum exceed-low;
                  }
                } //slope-usage

              } //container wred-queue

              container drop-tail {
                description
                    "Specify drop tail";
                container exceed {
                  description
                      "Specify exceed drop-tail";
                  container percent-reduction-from-mbs {
                    description
                        "Specify exceed drop tail percent reduction from MBS";
                    leaf percent {
                      type string;
                      description
                          "[0..100|default]";
                    } //percent

                  } //container percent-reduction-from-mbs

                } //container exceed

                container high {
                  description
                      "Specify high drop-tail";
                  container percent-reduction-from-mbs {
                    description
                        "Specify high drop tail percent reduction from MBS";
                    leaf percent {
                      type string;
                      description
                          "[0..100|default]";
                    } //percent

                  } //container percent-reduction-from-mbs

                } //container high

                container highplus {
                  description
                      "Specify highplus drop-tail";
                  container percent-reduction-from-mbs {
                    description
                        "Specify highplus drop tail percent reduction from MBS";
                    leaf percent {
                      type string;
                      description
                          "[0..100|default]";
                    } //percent

                  } //container percent-reduction-from-mbs

                } //container highplus

                container low {
                  description
                      "Specify low drop-tail";
                  container percent-reduction-from-mbs {
                    description
                        "Specify low drop tail percent reduction from MBS";
                    leaf percent {
                      type string;
                      description
                          "[0..100|default]";
                    } //percent

                  } //container percent-reduction-from-mbs

                } //container low

              } //container drop-tail

              container xp-specific {
                status "obsolete";
                description
                    "Configure IOM3-XP specific information";
                container packet-byte-offset {
                  status "obsolete";
                  description
                      "Specify packet byte offset";
                  leaf add {
                    type uint32 {
                      range "0..31";
                    }
                  } //add

                  leaf subtract {
                    type string;
                    description
                        "Attribute sub-bytes for packet-byte-offset";
                  } //subtract

                } //container packet-byte-offset

                container wred-queue {
                  status "obsolete";
                  description
                      "Configure WRED queue";
                  leaf policy {
                    type string {
                      length "1..32";
                    }
                  } //policy

                } //container wred-queue

              } //container xp-specific

            } //list queue

          } //list queue-group

        } //container egress

        container ingress {
          description
              "Configure QoS ingress queue groups";
          list queue-group {
            key "queue-group-name";
            description
                "Configure QoS ingress queue-group";
            leaf queue-group-name {
              type string {
                length "1..32";
              }
            } //queue-group-name

            container description {
              description
                  "Configure description for the QoS ingress queue-group";
              leaf description-string {
                type string {
                  length "1..80";
                }
              } //description-string

            } //container description

            list policer {
              key "policer-id";
              description
                  "Configure QoS ingress queue-group policer";
              leaf policer-id {
                type uint32 {
                  range "1..32";
                }
              } //policer-id

              container adaptation-rule {
                description
                    "Specify the CIR and PIR adaptation rules";
                leaf pir {
                  type enumeration {
                    enum max;
                    enum min;
                    enum closest;
                  }
                } //pir

                leaf cir {
                  type enumeration {
                    enum max;
                    enum min;
                    enum closest;
                  }
                } //cir

              } //container adaptation-rule

              container adv-config-policy {
                description
                    "Configure advanced configuration policy";
                leaf adv-config-policy-name {
                  type string {
                    length "1..32";
                  }
                } //adv-config-policy-name

              } //container adv-config-policy

              container cbs {
                description
                    "Specify CBS size";
                leaf size {
                  type string;
                  description
                      "[0..16777216 | default]";
                } //size

                leaf bytes-kilobytes {
                  type enumeration {
                    enum bytes;
                    enum kilobytes;
                  }
                } //bytes-kilobytes

              } //container cbs

              container description {
                description
                    "Configure description for the QoS ingress queue-group policer";
                leaf description-string {
                  type string {
                    length "1..80";
                  }
                } //description-string

              } //container description

              container high-prio-only {
                description
                    "Specify high priority only percent-of-mbs";
                leaf percent {
                  type string;
                  description
                      "[0..100 | default]";
                } //percent

              } //container high-prio-only

              container mbs {
                description
                    "Specify MBS size";
                leaf size {
                  type string;
                  description
                      "[0..16777216 | default]";
                } //size

                leaf bytes-kilobytes {
                  type enumeration {
                    enum bytes;
                    enum kilobytes;
                  }
                } //bytes-kilobytes

              } //container mbs

              container packet-byte-offset {
                description
                    "Specify packet byte offset";
                leaf add {
                  type uint32 {
                    range "0..31";
                  }
                } //add

                leaf subtract {
                  type uint32 {
                    range "1..32";
                  }
                } //subtract

              } //container packet-byte-offset

              container parent {
                description
                    "Specify the scheduler to which this policer feeds";
                leaf arbiter-name {
                  type string {
                    length "1..32";
                  }
                } //arbiter-name

                leaf weight {
                  type uint32 {
                    range "1..100";
                  }
                } //weight

                leaf level {
                  type uint32 {
                    range "1..8";
                  }
                } //level

              } //container parent

              leaf profile-capped {
                type boolean;
                description
                    "Configure Profile Cap";
              }

              container rate {
                description
                    "Specify rates (CIR and PIR)";
                leaf pir-rate {
                  type string;
                  description
                      "[1..2000000000|max] Kbps";
                } //pir-rate

                leaf cir {
                  type string;
                  description
                      "[0..2000000000|max] Kbps";
                } //cir

              } //container rate

              container stat-mode {
                description
                    "Specify Stat Mode for the policer";
                leaf stat-mode {
                  type enumeration {
                    enum no-stats;
                    enum minimal;
                    enum offered-profile-no-cir;
                    enum offered-priority-no-cir;
                    enum offered-limited-profile-cir;
                    enum offered-profile-cir;
                    enum offered-priority-cir;
                    enum offered-total-cir;
                    enum offered-profile-capped-cir;
                    enum offered-limited-capped-cir;
                  }
                } //stat-mode

              } //container stat-mode

            } //list policer

            list queue {
              key "queue-id";
              description
                  "Configure a queue";
              leaf queue-id {
                type int32 {
                  range "1..32";
                }
              } //queue-id

              leaf multipoint {
                type boolean;
                description
                    "keyword - mandatory while creating a multipoint queue";
              } //multipoint

              leaf queue-type {
                type enumeration {
                  enum expedite;
                  enum best-effort;
                }
                description
                    "expedite|best-effort - keywords";
              } //queue-type

              leaf queue-mode {
                type enumeration {
                  enum profile-mode;
                  enum priority-mode;
                }
                description
                    "profile-mode|priority-mode - keywords";
              } //queue-mode

              container adaptation-rule {
                description
                    "Specify the information rate adaptation rules";
                leaf pir {
                  type enumeration {
                    enum max;
                    enum min;
                    enum closest;
                  }
                } //pir

                leaf cir {
                  type enumeration {
                    enum max;
                    enum min;
                    enum closest;
                  }
                } //cir

                leaf fir {
                  type enumeration {
                    enum max;
                    enum min;
                    enum closest;
                  }
                } //fir

              } //container adaptation-rule

              container adv-config-policy {
                description
                    "Configure advanced configuration policy";
                leaf adv-config-policy-name {
                  type string {
                    length "1..32";
                  }
                } //adv-config-policy-name

              } //container adv-config-policy

              container burst-limit {
                description
                    "Specify burst limit";
                leaf size {
                  type string;
                  description
                      "Attribute size for burst-limit";
                } //size

                leaf bytes-kilobytes {
                  type enumeration {
                    enum bytes;
                    enum kilobytes;
                  }
                } //bytes-kilobytes

              } //container burst-limit

              container cbs {
                description
                    "Specify CBS size";
                leaf size-in-kbytes {
                  type string;
                  description
                      "Attribute size-in-kbytes for cbs";
                } //size-in-kbytes

              } //container cbs

              leaf cir-non-profiling {
                type boolean;
                description
                    "CIR non profiling";
              }

              container high-prio-only {
                status "obsolete";
                description
                    "Specify high priority only burst size";
                leaf percent {
                  type string;
                  description
                      "[0..100 | default]";
                } //percent

              } //container high-prio-only

              container mbs {
                description
                    "Specify MBS size";
                leaf size {
                  type string;
                  description
                      "Attribute size for mbs";
                } //size

                leaf bytes-kilobytes {
                  type enumeration {
                    enum bytes;
                    enum kilobytes;
                  }
                  description
                      "keyword";
                } //bytes-kilobytes

              } //container mbs

              container packet-byte-offset {
                description
                    "Specify packet byte offset";
                leaf add {
                  type uint32 {
                    range "0..30";
                  }
                  description
                      "[0..30] - Only even values are supported";
                } //add

                leaf subtract {
                  type uint32 {
                    range "0..32";
                  }
                  description
                      "[0..32] - Only even values are supported";
                } //subtract

              } //container packet-byte-offset

              container parent {
                description
                    "Specify the scheduler to which this queue feeds";
                leaf scheduler-name {
                  type string {
                    length "1..32";
                  }
                } //scheduler-name

                leaf weight {
                  type uint32 {
                    range "0..100";
                  }
                } //weight

                leaf level {
                  type uint32 {
                    range "1..8";
                  }
                } //level

                leaf cir-weight {
                  type uint32 {
                    range "0..100";
                  }
                } //cir-weight

                leaf cir-level {
                  type uint32 {
                    range "0..8";
                  }
                } //cir-level

              } //container parent

              container pool {
                description
                    "Configure named pool for this queue";
                leaf pool-name {
                  type string {
                    length "1..32";
                  }
                } //pool-name

              } //container pool

              container rate {
                description
                    "Specify information rates";
                leaf pir-rate {
                  type string;
                  description
                      "Attribute pir-rate for rate";
                } //pir-rate

                leaf cir {
                  type string;
                  description
                      "Attribute cir-rate for rate";
                } //cir

                leaf fir {
                  type string;
                  description
                      "Attribute fir-rate for rate";
                } //fir

                leaf police {
                  type boolean;
                } //police

              } //container rate

              container drop-tail {
                description
                    "Specify drop tail";
                container low {
                  description
                      "Specify low drop-tail";
                  container percent-reduction-from-mbs {
                    description
                        "Specify low drop tail percent reduction from MBS";
                    leaf percent {
                      type string;
                      description
                          "[0..100|default]";
                    } //percent

                  } //container percent-reduction-from-mbs

                } //container low

              } //container drop-tail

            } //list queue

          } //list queue-group

        } //container ingress

      } //container queue-group-templates

      list queue-mgmt-policy {
        key "queue-mgmt-name";
        description
            "Configure a queue-mgmt-policy";
        leaf queue-mgmt-name {
          type string;
          description
              "<name:64 char max>";
        } //queue-mgmt-name

        container description {
          description
              "Description for the queue-mgmt policy policy";
          leaf description-string {
            type string {
              length "1..80";
            }
          } //description-string

        } //container description

        container mbs {
          description
              "Configure MBS Size";
          leaf size-in-kilobytes {
            type uint32 {
              range "1..1500000";
            }
          } //size-in-kilobytes

        } //container mbs

        container scope {
          description
              "Configure scope of the policy";
          leaf exclusive-template {
            type enumeration {
              enum exclusive;
              enum template;
            }
            description
                "keywords - specify type of policy";
          } //exclusive-template

        } //container scope

        container time-average-factor {
          description
              "Configure time average factor";
          leaf value {
            type uint32 {
              range "0..31";
            }
          } //value

        } //container time-average-factor

        container high-slope {
          presence
              "Configure high-prio RED slope parameters";
          container max-avg {
            description
                "Configure max average";
            leaf percent {
              type uint32 {
                range "0..100";
              }
            } //percent

          } //container max-avg

          container max-prob {
            description
                "Configure max probability";
            leaf percent {
              type uint32 {
                range "1..99";
              }
            } //percent

          } //container max-prob

          leaf shutdown {
            type boolean;
            description
                "Administratively enable/disable high slope";
          }

          container start-avg {
            description
                "Configure starting average";
            leaf percent {
              type uint32 {
                range "0..100";
              }
            } //percent

          } //container start-avg

        } //container high-slope

        container low-slope {
          presence
              "Configure low-prio RED slope parameters";
          container max-avg {
            description
                "Configure max average";
            leaf percent {
              type uint32 {
                range "0..100";
              }
            } //percent

          } //container max-avg

          container max-prob {
            description
                "Configure max probability";
            leaf percent {
              type uint32 {
                range "1..99";
              }
            } //percent

          } //container max-prob

          leaf shutdown {
            type boolean;
            description
                "Administratively enable/disable low slope";
          }

          container start-avg {
            description
                "Configure starting average";
            leaf percent {
              type uint32 {
                range "0..100";
              }
            } //percent

          } //container start-avg

        } //container low-slope

      } //list queue-mgmt-policy

      list sap-egress {
        key "policy-id";
        description
            "Configure sap-egress policy";
        leaf policy-id {
          type string;
          description
              "[1..65535]|<name:64 char max>";
        } //policy-id

        leaf name {
          type string {
            length "1..64";
          }
        } //name

        container description {
          description
              "Description for this sap-egress policy";
          leaf description-string {
            type string {
              length "1..80";
            }
          } //description-string

        } //container description

        list dot1p {
          key "dot1p-priority";
          description
              "Specify 802.1 priority mappings";
          leaf dot1p-priority {
            type int32 {
              range "0..7";
            }
          } //dot1p-priority

          leaf fc {
            type enumeration {
              enum be;
              enum l2;
              enum af;
              enum l1;
              enum h2;
              enum ef;
              enum h1;
              enum nc;
            }
          } //fc

          leaf profile {
            type enumeration {
              enum in;
              enum out;
              enum use-de;
              enum exceed;
              enum inplus;
            }
          } //profile

        } //list dot1p

        container dscp {
          description
              "Specify DSCP mappings";
          leaf-list dscp-name {
            type string {
              length "1..32";
            }
            max-elements 8;
            description
                "Attribute dscp-name for dscp";
          } //dscp-name

          leaf hsmda-counter-override {
            type uint32 {
              range "1..8";
            }
          } //hsmda-counter-override

          leaf fc {
            type enumeration {
              enum be;
              enum l2;
              enum af;
              enum l1;
              enum h2;
              enum ef;
              enum h1;
              enum nc;
            }
          } //fc

          leaf profile {
            type enumeration {
              enum in;
              enum out;
              enum exceed;
              enum inplus;
            }
          } //profile

        } //container dscp

        leaf ethernet-ctag {
          type boolean;
          description
              "Configure ethernet ctag value";
        }

        container hs-attachment-policy {
          description
              "Specify HS attachment policy";
          leaf policy-name {
            type string;
          } //policy-name

        } //container hs-attachment-policy

        container parent-location {
          description
              "Configure parent location";
          leaf default-sla {
            type enumeration {
              enum default;
              enum sla;
            }
            description
                "keywords - specify parent location";
          } //default-sla

        } //container parent-location

        leaf policers-hqos-manageable {
          type boolean;
          description
              "Enable/Disable HQoS Manageable Policers";
        }

        container post-policer-mapping {
          description
              "Configure post policer mapping policy";
          leaf mapping-policy-name {
            type string;
          } //mapping-policy-name

        } //container post-policer-mapping

        list prec {
          key "ip-prec-value";
          description
              "Specify IP precedence mappings";
          leaf ip-prec-value {
            type int32 {
              range "0..7";
            }
          } //ip-prec-value

          leaf hsmda-counter-override {
            type uint32 {
              range "1..8";
            }
          } //hsmda-counter-override

          leaf fc {
            type enumeration {
              enum be;
              enum l2;
              enum af;
              enum l1;
              enum h2;
              enum ef;
              enum h1;
              enum nc;
            }
          } //fc

          leaf profile {
            type enumeration {
              enum in;
              enum out;
              enum exceed;
              enum inplus;
            }
          } //profile

        } //list prec

        container scope {
          description
              "Specify scope of the policy";
          leaf exclusive-template {
            type enumeration {
              enum exclusive;
              enum template;
            }
            description
                "keywords - specify type of policy";
          } //exclusive-template

        } //container scope

        container sub-insert-shared-pccrule {
          description
              "Configure insert point for shared PCC-rules";
          leaf start-entry {
            type uint32 {
              range "1..65535";
            }
          } //start-entry

          leaf count {
            type uint32 {
              range "1..65535";
            }
          } //count

        } //container sub-insert-shared-pccrule

        container dynamic-policer {
          description
              "Configure qos sap-egress dynamic-policer";
          container cbs {
            description
                "Specify CBS size for sap-egress dynamic-policer";
            leaf size {
              type string;
              description
                  "[0..16777216 | default]";
            } //size

            leaf bytes-kilobytes {
              type enumeration {
                enum bytes;
                enum kilobytes;
              }
            } //bytes-kilobytes

          } //container cbs

          container mbs {
            description
                "Specify MBS size for sap-egress dynamic-policer";
            leaf size {
              type string;
              description
                  "[0..16777216 | default]";
            } //size

            leaf bytes-kilobytes {
              type enumeration {
                enum bytes;
                enum kilobytes;
              }
            } //bytes-kilobytes

          } //container mbs

          container packet-byte-offset {
            description
                "Specify packet byte offset for sap-egress dynamic-policer";
            leaf add {
              type uint32 {
                range "0..31";
              }
            } //add

            leaf subtract {
              type uint32 {
                range "1..64";
              }
            } //subtract

          } //container packet-byte-offset

          container parent {
            description
                "Specify the arbiter to which this sap-egress dynamic-policer feeds";
            leaf arbiter-name {
              type string {
                length "1..32";
              }
            } //arbiter-name

            leaf weight {
              type uint32 {
                range "1..100";
              }
            } //weight

            leaf level {
              type uint32 {
                range "1..8";
              }
            } //level

          } //container parent

          container range {
            description
                "Configure sap-egress dynamic-policer";
            leaf start-entry {
              type uint32 {
                range "1..63";
              }
            } //start-entry

            leaf count {
              type uint32 {
                range "1..63";
              }
            } //count

          } //container range

          container stat-mode {
            description
                "Specify Stat Mode for sap-egress dynamic-policer";
            leaf stat-mode {
              type enumeration {
                enum no-stats;
                enum minimal;
                enum offered-profile-no-cir;
                enum offered-profile-cir;
                enum offered-total-cir;
                enum offered-limited-capped-cir;
                enum offered-profile-capped-cir;
              }
            } //stat-mode

          } //container stat-mode

        } //container dynamic-policer

        list fc {
          key "fc-name";
          description
              "Configure forwarding-class mappings";
          leaf fc-name {
            type enumeration {
              enum be;
              enum l2;
              enum af;
              enum l1;
              enum h2;
              enum ef;
              enum h1;
              enum nc;
            }
            description
                "be|l2|af|l1|h2|ef|h1|nc - keywords";
          } //fc-name

          container de-mark {
            description
                "Specify DE value for marking";
            leaf force {
              type int32 {
                range "0..1";
              }
            } //force

          } //container de-mark

          container de-mark-inner {
            description
                "Specify DE value for marking Inner Tag";
            leaf force {
              type int32 {
                range "0..1";
              }
            } //force

          } //container de-mark-inner

          container de-mark-outer {
            description
                "Specify DE value for marking Outer Tag";
            leaf force {
              type int32 {
                range "0..1";
              }
            } //force

          } //container de-mark-outer

          container dot1p {
            description
                "Specify the dot1p value to be used";
            leaf dot1p-value {
              type int32 {
                range "0..7";
              }
            } //dot1p-value

            leaf in-profile {
              type string;
              description
                  "dot1p-value";
            } //in-profile

            leaf out-profile {
              type string;
              description
                  "dot1p-value";
            } //out-profile

            leaf exceed-profile {
              type string;
              description
                  "dot1p-value";
            } //exceed-profile

          } //container dot1p

          container dot1p-inner {
            description
                "Specify the inner-tag dot1p value to be used";
            leaf dot1p-value {
              type string;
            } //dot1p-value

            leaf in-profile {
              type string;
              description
                  "dot1p-value";
            } //in-profile

            leaf out-profile {
              type string;
              description
                  "dot1p-value";
            } //out-profile

          } //container dot1p-inner

          container dot1p-outer {
            description
                "Specify the outer-tag dot1p value to be used";
            leaf dot1p-value {
              type string;
            } //dot1p-value

            leaf in-profile {
              type string;
              description
                  "dot1p-value";
            } //in-profile

            leaf out-profile {
              type string;
              description
                  "dot1p-value";
            } //out-profile

            leaf exceed-profile {
              type string;
              description
                  "dot1p-value";
            } //exceed-profile

          } //container dot1p-outer

          container dscp {
            description
                "Specify DSCP mappings";
            leaf dscp-name {
              type string {
                length "1..32";
              }
              description
                  "Attribute dscp-name for dscp";
            } //dscp-name

            leaf in-profile {
              type string {
                length "1..32";
              }
              description
                  "dscp-name";
            } //in-profile

            leaf out-profile {
              type string {
                length "1..32";
              }
              description
                  "dscp-name";
            } //out-profile

            leaf exceed-profile {
              type string {
                length "1..32";
              }
              description
                  "dscp-name";
            } //exceed-profile

          } //container dscp

          container policer {
            description
                "Specify Policer Information";
            leaf policer-id {
              type uint32 {
                range "1..63";
              }
            } //policer-id

            leaf group {
              type string {
                length "1..32";
              }
            } //group

            leaf queue {
              type uint32 {
                range "1..8";
              }
            } //queue

            leaf instance {
              type uint16 {
                range "1..65535";
              }
            } //instance

            leaf port-redirect-group-queue {
              type boolean;
            } //port-redirect-group-queue

          } //container policer

          container prec {
            description
                "Specify IP precedence mappings";
            leaf ip-prec-value {
              type int32 {
                range "0..7";
              }
            } //ip-prec-value

            leaf in-profile {
              type int32 {
                range "0..7";
              }
              description
                  "ip-prec-value";
            } //in-profile

            leaf out-profile {
              type int32 {
                range "0..7";
              }
              description
                  "ip-prec-value";
            } //out-profile

            leaf exceed-profile {
              type int32 {
                range "0..7";
              }
              description
                  "ip-prec-value";
            } //exceed-profile

          } //container prec

          container queue {
            description
                "Specify the queue to forward this FC traffic";
            leaf queue-id {
              type int32 {
                range "1..8";
              }
            } //queue-id

            leaf group {
              type string {
                length "1..32";
              }
            } //group

            leaf instance {
              type uint16 {
                range "1..65535";
              }
            } //instance

            leaf port-redirect-group-queue {
              type boolean;
            } //port-redirect-group-queue

          } //container queue

          container hsmda {
            description
                "Specify the HSMDA queues to forward this FC traffic";
            container queue {
              description
                  "Specify the HSMDA queue to forward this FC traffic";
              leaf hsmda-queue-id {
                type uint32 {
                  range "1..8";
                }
              } //hsmda-queue-id

              leaf port-redirect-group-queue {
                type boolean;
              } //port-redirect-group-queue

            } //container queue

          } //container hsmda

        } //list fc

        list hs-wrr-group {
          key "group-id";
          description
              "Configure HS WRR Group";
          leaf group-id {
            type uint16 {
              range "1..2";
            }
            description
                "[1..2]";
          } //group-id

          container adaptation-rule {
            description
                "Specify the PIR adaptation rules";
            leaf pir {
              type enumeration {
                enum max;
                enum min;
                enum closest;
              }
            } //pir

          } //container adaptation-rule

          container hs-class-weight {
            description
                "Specify class weight";
            leaf weight {
              type enumeration {
                enum 1;
                enum 2;
                enum 4;
                enum 8;
              }
            } //weight

          } //container hs-class-weight

          container percent-rate {
            description
                "Specify percent rate";
            leaf percent {
              type string;
              description
                  "[0.01..100.00]";
            } //percent

          } //container percent-rate

          container rate {
            description
                "Specify rates (PIR)";
            leaf rate {
              type string;
              description
                  "Attribute rate for rate";
            } //rate

          } //container rate

        } //list hs-wrr-group

        container hsmda-queues {
          description
              "Configure HSMDA queues";
          container low-burst-max-class {
            description
                "Specify low burst max class";
            leaf class {
              type uint32 {
                range "1..8";
              }
            } //class

          } //container low-burst-max-class

          container packet-byte-offset {
            description
                "Specify a packet offset for HSMDA queue accounting";
            leaf add {
              type uint32 {
                range "1..31";
              }
            } //add

            leaf subtract {
              type string;
              description
                  "Attribute sub-bytes for packet-byte-offset";
            } //subtract

          } //container packet-byte-offset

          container wrr-policy {
            description
                "Configure egress Hsmda-wrr policy";
            leaf wrr-policy-name {
              type string {
                length "1..32";
              }
            } //wrr-policy-name

          } //container wrr-policy

          list queue {
            key "queue-id";
            description
                "Configure a specific HSMDA queue";
            leaf queue-id {
              type int32 {
                range "1..8";
              }
            } //queue-id

            container adaptation-rule {
              description
                  "Specify the PIR adaptation rules";
              leaf pir {
                type enumeration {
                  enum max;
                  enum min;
                  enum closest;
                }
              } //pir

            } //container adaptation-rule

            container burst-limit {
              description
                  "Specify the Queue Burst limit";
              leaf size {
                type uint32 {
                  range "1..1000000";
                }
                description
                    "[1..1000000]";
              } //size

              leaf bytes-kilobytes {
                type enumeration {
                  enum bytes;
                  enum kilobytes;
                }
              } //bytes-kilobytes

            } //container burst-limit

            container mbs {
              description
                  "Specify MBS rate";
              leaf size {
                type string;
                description
                    "[0..2625 kilobytes | 0..2688000 bytes | default]";
              } //size

              leaf mbs-id {
                type enumeration {
                  enum bytes;
                  enum kilobytes;
                }
              } //mbs-id

            } //container mbs

            container rate {
              description
                  "Specify PIR rates";
              leaf pir-rate {
                type string;
                description
                    "[1..100000000|max] Kbps";
              } //pir-rate

            } //container rate

            container slope-policy {
              description
                  "Specify slope policy";
              leaf hsmda-slope-policy-name {
                type string {
                  length "1..32";
                }
              } //hsmda-slope-policy-name

            } //container slope-policy

            container wrr-weight {
              description
                  "Specify wrr-weight";
              leaf weight {
                type int32 {
                  range "1..32";
                }
                description
                    "Attribute weight for wrr-weight";
              } //weight

            } //container wrr-weight

          } //list queue

        } //container hsmda-queues

        container ip-criteria {
          presence
              "Configure IP match criteria";
          container renum {
            description
                "Renumber an entry";
            leaf old-entry-id {
              type uint32 {
                range "1..65535";
              }
            } //old-entry-id

            leaf new-entry-id {
              type uint32 {
                range "1..65535";
              }
            } //new-entry-id

          } //container renum

          list entry {
            key "entry-id";
            description
                "Configure an IP based policy entry";
            leaf entry-id {
              type uint32 {
                range "1..65535";
              }
            } //entry-id

            container action {
              description
                  "Specify action fc, policer, port queue-group redirection, queue and priority";
              leaf hsmda-counter-override {
                type uint32 {
                  range "1..8";
                }
              } //hsmda-counter-override

              leaf fc {
                type enumeration {
                  enum be;
                  enum l2;
                  enum af;
                  enum l1;
                  enum h2;
                  enum ef;
                  enum h1;
                  enum nc;
                }
              } //fc

              leaf profile {
                type enumeration {
                  enum in;
                  enum out;
                  enum exceed;
                  enum inplus;
                }
              } //profile

              leaf policer {
                type uint32 {
                  range "1..63";
                }
              } //policer

              leaf port-redirect-group-queue {
                type boolean;
                description
                    "keyword";
              } //port-redirect-group-queue

              leaf queue {
                type int32 {
                  range "1..8";
                }
              } //queue

              leaf use-fc-mapped-queue {
                type boolean;
              } //use-fc-mapped-queue

            } //container action

            container description {
              description
                  "Description for this entry";
              leaf description-string {
                type string {
                  length "1..80";
                }
              } //description-string

            } //container description

            container match {
              description
                  "Specify IP match criteria for this policy";
              leaf protocol {
                type string;
                description
                    "Attribute protocol-id for match";
              } //protocol

              container dscp {
                description
                    "Specify DSCP match";
                leaf dscp-name {
                  type string {
                    length "1..32";
                  }
                  description
                      "Attribute dscp-name for dscp";
                } //dscp-name

              } //container dscp

              container dst-ip {
                description
                    "Specify destination IP and mask match";
                leaf ip-address-mask {
                  type inet:ip-prefix;
                  description
                      "<ip-address>/<mask>";
                } //ip-address-mask

                leaf ip-address {
                  type inet:ip-address;
                  description
                      "Attribute ip-address for dst-ip";
                } //ip-address

                leaf ipv4-address-mask {
                  type string;
                  description
                      "a.b.c.d any address mask expressed as dotted quad [0..255]";
                } //ipv4-address-mask

                leaf ip-prefix-list {
                  type string {
                    length "1..32";
                  }
                } //ip-prefix-list

              } //container dst-ip

              container dst-port {
                description
                    "Specify destination TCP/UDP port match";
                leaf lt-gt-eq {
                  type enumeration {
                    enum lt;
                    enum gt;
                    enum eq;
                  }
                  description
                      "operators";
                } //lt-gt-eq

                leaf dst-port-number {
                  type string;
                  description
                      "Attribute dst-port-number for dst-port";
                } //dst-port-number

                leaf-list range {
                  type string;
                  max-elements 2;
                  description
                      "dst-port-number";
                } //range

              } //container dst-port

              container fragment {
                description
                    "Specify match criteria applies to IP fragments";
                leaf true-false {
                  type enumeration {
                    enum true;
                    enum false;
                  }
                  description
                      "keywords - specify fragment match";
                } //true-false

              } //container fragment

              container src-ip {
                description
                    "Specify source IP and mask match";
                leaf ip-address-mask {
                  type inet:ip-prefix;
                  description
                      "<ip-address>/<mask>";
                } //ip-address-mask

                leaf ip-address {
                  type inet:ip-address;
                  description
                      "Attribute ip-address for src-ip";
                } //ip-address

                leaf ipv4-address-mask {
                  type string;
                  description
                      "a.b.c.d any address mask expressed as dotted quad [0..255]";
                } //ipv4-address-mask

                leaf ip-prefix-list {
                  type string {
                    length "1..32";
                  }
                } //ip-prefix-list

              } //container src-ip

              container src-port {
                description
                    "Specify source TCP/UDP port match";
                leaf lt-gt-eq {
                  type enumeration {
                    enum lt;
                    enum gt;
                    enum eq;
                  }
                  description
                      "operators";
                } //lt-gt-eq

                leaf src-port-number {
                  type string;
                  description
                      "Attribute src-port-number for src-port";
                } //src-port-number

                leaf-list range {
                  type string;
                  max-elements 2;
                  description
                      "src-port-number";
                } //range

              } //container src-port

            } //container match

          } //list entry

        } //container ip-criteria

        container ipv6-criteria {
          presence
              "Configure IPv6 match criteria";
          container renum {
            description
                "Renumber an entry";
            leaf old-entry-id {
              type uint32 {
                range "1..65535";
              }
            } //old-entry-id

            leaf new-entry-id {
              type uint32 {
                range "1..65535";
              }
            } //new-entry-id

          } //container renum

          list entry {
            key "entry-id";
            description
                "Configure an IPv6 based policy entry";
            leaf entry-id {
              type uint32 {
                range "1..65535";
              }
            } //entry-id

            container action {
              description
                  "Specify action fc, policer, port queue-group redirection, queue and priority";
              leaf fc {
                type enumeration {
                  enum be;
                  enum l2;
                  enum af;
                  enum l1;
                  enum h2;
                  enum ef;
                  enum h1;
                  enum nc;
                }
              } //fc

              leaf hsmda-counter-override {
                type uint32 {
                  range "1..8";
                }
              } //hsmda-counter-override

              leaf profile {
                type enumeration {
                  enum in;
                  enum out;
                  enum exceed;
                  enum inplus;
                }
              } //profile

              leaf policer {
                type uint32 {
                  range "1..63";
                }
              } //policer

              leaf port-redirect-group-queue {
                type boolean;
                description
                    "keyword";
              } //port-redirect-group-queue

              leaf queue {
                type int32 {
                  range "1..8";
                }
              } //queue

              leaf use-fc-mapped-queue {
                type boolean;
              } //use-fc-mapped-queue

            } //container action

            container description {
              description
                  "Description for this entry";
              leaf description-string {
                type string {
                  length "1..80";
                }
              } //description-string

            } //container description

            container match {
              description
                  "Specify IPv6 match criteria for this policy";
              leaf next-header {
                type string;
                description
                    "Attribute next-header for match";
              } //next-header

              container dscp {
                description
                    "Specify DSCP match";
                leaf dscp-name {
                  type string {
                    length "1..32";
                  }
                  description
                      "Attribute dscp-name for dscp";
                } //dscp-name

              } //container dscp

              container dst-ip {
                description
                    "Specify destination IPv6 address and mask match";
                leaf ipv6-address-prefix-length {
                  type string;
                  description
                      "<ipv6-address>/<prefix-length>";
                } //ipv6-address-prefix-length

                leaf ipv6-address {
                  type inet:ipv6-address;
                  description
                      "Attribute ipv6-address for dst-ip";
                } //ipv6-address

                leaf ipv6-address-mask {
                  type inet:ipv6-address;
                  description
                      "Attribute ipv6-address-mask for dst-ip";
                } //ipv6-address-mask

              } //container dst-ip

              container dst-port {
                description
                    "Specify destination TCP/UDP port match";
                leaf lt-gt-eq {
                  type enumeration {
                    enum lt;
                    enum gt;
                    enum eq;
                  }
                  description
                      "operators";
                } //lt-gt-eq

                leaf dst-port-number {
                  type string;
                  description
                      "Attribute dst-port-number for dst-port";
                } //dst-port-number

                leaf-list range {
                  type string;
                  max-elements 2;
                  description
                      "dst-port-number";
                } //range

              } //container dst-port

              container src-ip {
                description
                    "Specify source IPv6 address and mask match";
                leaf ipv6-address-prefix-length {
                  type string;
                  description
                      "<ipv6-address>/<prefix-length>";
                } //ipv6-address-prefix-length

                leaf ipv6-address {
                  type inet:ipv6-address;
                  description
                      "Attribute ipv6-address for src-ip";
                } //ipv6-address

                leaf ipv6-address-mask {
                  type inet:ipv6-address;
                  description
                      "Attribute ipv6-address-mask for src-ip";
                } //ipv6-address-mask

              } //container src-ip

              container src-port {
                description
                    "Specify source TCP/UDP port match";
                leaf lt-gt-eq {
                  type enumeration {
                    enum lt;
                    enum gt;
                    enum eq;
                  }
                  description
                      "operators";
                } //lt-gt-eq

                leaf src-port-number {
                  type string;
                  description
                      "Attribute src-port-number for src-port";
                } //src-port-number

                leaf-list range {
                  type string;
                  max-elements 2;
                  description
                      "src-port-number";
                } //range

              } //container src-port

            } //container match

          } //list entry

        } //container ipv6-criteria

        list policer {
          key "policer-id";
          description
              "Configure Policer for this policy";
          leaf policer-id {
            type uint32 {
              range "1..63";
            }
          } //policer-id

          container adaptation-rule {
            description
                "Specify the CIR and PIR adaptation rules";
            leaf pir {
              type enumeration {
                enum max;
                enum min;
                enum closest;
              }
            } //pir

            leaf cir {
              type enumeration {
                enum max;
                enum min;
                enum closest;
              }
            } //cir

          } //container adaptation-rule

          container adv-config-policy {
            description
                "Configure advanced configuration policy";
            leaf adv-config-policy-name {
              type string {
                length "1..32";
              }
            } //adv-config-policy-name

          } //container adv-config-policy

          container cbs {
            description
                "Specify CBS size";
            leaf size {
              type string;
              description
                  "[0..16777216 | default]";
            } //size

            leaf cbs-id {
              type enumeration {
                enum bytes;
                enum kilobytes;
              }
            } //cbs-id

          } //container cbs

          container description {
            description
                "Description for this policer";
            leaf description-string {
              type string {
                length "1..80";
              }
            } //description-string

          } //container description

          leaf enable-dscp-prec-remarking {
            type boolean;
            description
                "Enable/Disable DSCP and Prec Remarking";
          }

          leaf enable-exceed-pir {
            type boolean;
            description
                "Enable/Disable Exceed PIR";
          }

          container high-prio-only {
            description
                "Specify high priority only percent-of-mbs";
            leaf percent {
              type string;
              description
                  "[0..100 | default]";
            } //percent

          } //container high-prio-only

          container mbs {
            description
                "Specify MBS size";
            leaf size {
              type string;
              description
                  "[0..16777216 | default]";
            } //size

            leaf mbs-id {
              type enumeration {
                enum bytes;
                enum kilobytes;
              }
            } //mbs-id

          } //container mbs

          container packet-byte-offset {
            description
                "Specify packet byte offset";
            leaf add {
              type uint32 {
                range "0..31";
              }
            } //add

            leaf subtract {
              type string;
              description
                  "Attribute sub-bytes for packet-byte-offset";
            } //subtract

          } //container packet-byte-offset

          container parent {
            description
                "Specify the arbiter to which this policer feeds";
            leaf arbiter-name {
              type string {
                length "1..32";
              }
            } //arbiter-name

            leaf weight {
              type uint32 {
                range "1..100";
              }
            } //weight

            leaf level {
              type uint32 {
                range "1..8";
              }
            } //level

          } //container parent

          container percent-rate {
            description
                "Specify percent rates (CIR and PIR)";
            leaf pir-percent {
              type string;
              description
                  "[0.01..100.00]";
            } //pir-percent

            leaf cir {
              type string;
              description
                  "[0.00..100.00]";
            } //cir

          } //container percent-rate

          container port-parent {
            description
                "Specify the port-scheduler to which this policer feeds";
            leaf weight {
              type uint32 {
                range "0..100";
              }
            } //weight

            leaf level {
              type uint32 {
                range "1..8";
              }
            } //level

            leaf cir-weight {
              type uint32 {
                range "0..100";
              }
            } //cir-weight

            leaf cir-level {
              type uint32 {
                range "0..8";
              }
            } //cir-level

          } //container port-parent

          leaf profile-capped {
            type boolean;
            description
                "Configure Profile Cap";
          }

          leaf profile-out-preserve {
            type boolean;
            description
                "Configure Profile Out Preserve";
          }

          container rate {
            description
                "Specify rates (CIR and PIR)";
            leaf pir-rate {
              type string;
              description
                  "[1..6400000000|max] Kbps";
            } //pir-rate

            leaf cir {
              type string;
              description
                  "[0..6400000000|max] Kbps";
            } //cir

          } //container rate

          container scheduler-parent {
            description
                "Specify the scheduler to which this policer feeds";
            leaf scheduler-name {
              type string {
                length "1..32";
              }
            } //scheduler-name

            leaf weight {
              type uint32 {
                range "0..100";
              }
            } //weight

            leaf level {
              type uint32 {
                range "1..8";
              }
            } //level

            leaf cir-weight {
              type uint32 {
                range "0..100";
              }
            } //cir-weight

            leaf cir-level {
              type uint32 {
                range "0..8";
              }
            } //cir-level

          } //container scheduler-parent

          container stat-mode {
            description
                "Specify Stat Mode for the policer";
            leaf stat-mode {
              type enumeration {
                enum no-stats;
                enum minimal;
                enum offered-profile-no-cir;
                enum offered-profile-cir;
                enum offered-total-cir;
                enum offered-limited-capped-cir;
                enum offered-profile-capped-cir;
                enum offered-total-cir-exceed;
                enum offered-four-profile-no-cir;
                enum offered-total-cir-four-profile;
              }
            } //stat-mode

          } //container stat-mode

        } //list policer

        list queue {
          key "queue-id";
          description
              "Configure a queue";
          leaf queue-id {
            type int32 {
              range "1..8";
            }
          } //queue-id

          leaf queue-type {
            type enumeration {
              enum expedite;
              enum best-effort;
              enum auto-expedite;
            }
            description
                "expedite|best-effort|auto-expedite - keywords";
          } //queue-type

          container adaptation-rule {
            description
                "Specify the CIR and PIR adaptation rules";
            leaf pir {
              type enumeration {
                enum max;
                enum min;
                enum closest;
              }
            } //pir

            leaf cir {
              type enumeration {
                enum max;
                enum min;
                enum closest;
              }
            } //cir

          } //container adaptation-rule

          container adv-config-policy {
            description
                "Configure advanced configuration policy";
            leaf adv-config-policy-name {
              type string {
                length "1..32";
              }
            } //adv-config-policy-name

          } //container adv-config-policy

          container avg-frame-overhead {
            description
                "Configure average frame overhead";
            leaf percentage {
              type string;
              description
                  "[0.00..100.00]";
            } //percentage

          } //container avg-frame-overhead

          container burst-limit {
            description
                "Specify burst limit";
            leaf size {
              type string;
              description
                  "Attribute size for burst-limit";
            } //size

            leaf bytes-kilobytes {
              type enumeration {
                enum bytes;
                enum kilobytes;
              }
            } //bytes-kilobytes

          } //container burst-limit

          container cbs {
            description
                "Specify CBS size";
            leaf size-in-kbytes {
              type string;
              description
                  "Attribute size-in-kbytes for cbs";
            } //size-in-kbytes

          } //container cbs

          container hi-low-prio-only {
            status "obsolete";
            description
                "Specify high-low priority only burst size";
            leaf percent {
              type string;
              description
                  "[0..100 | default]";
            } //percent

          } //container hi-low-prio-only

          container high-prio-only {
            status "obsolete";
            description
                "Specify high priority only burst size";
            leaf percent {
              type string;
              description
                  "[0..100 | default]";
            } //percent

          } //container high-prio-only

          leaf hs-alt-port-class-pool {
            type boolean;
            description
                "Enable/disable HS alternate port class pool";
          }

          container hs-class-weight {
            description
                "Specify HS class weight";
            leaf weight {
              type enumeration {
                enum 1;
                enum 2;
                enum 4;
                enum 8;
              }
            } //weight

          } //container hs-class-weight

          container hs-wred-queue {
            description
                "Configure WRED queue";
            leaf policy {
              type string {
                length "1..32";
              }
            } //policy

          } //container hs-wred-queue

          container hs-wrr-weight {
            description
                "Specify HS WRR weight";
            leaf weight {
              type uint16 {
                range "1..127";
              }
              description
                  "[1..127]";
            } //weight

          } //container hs-wrr-weight

          container mbs {
            description
                "Specify MBS size";
            leaf size {
              type string;
              description
                  "Attribute size for mbs";
            } //size

            leaf bytes-kilobytes {
              type enumeration {
                enum bytes;
                enum kilobytes;
              }
              description
                  "keyword";
            } //bytes-kilobytes

          } //container mbs

          container packet-byte-offset {
            description
                "Specify packet byte offset";
            leaf add {
              type uint32 {
                range "0..32";
              }
            } //add

            leaf subtract {
              type uint32 {
                range "0..64";
              }
            } //subtract

          } //container packet-byte-offset

          container parent {
            description
                "Specify the scheduler to which this queue feeds";
            leaf scheduler-name {
              type string {
                length "1..32";
              }
            } //scheduler-name

            leaf weight {
              type uint32 {
                range "0..100";
              }
            } //weight

            leaf level {
              type uint32 {
                range "1..8";
              }
            } //level

            leaf cir-weight {
              type uint32 {
                range "0..100";
              }
            } //cir-weight

            leaf cir-level {
              type uint32 {
                range "0..8";
              }
            } //cir-level

          } //container parent

          container percent-rate {
            description
                "Specify percent rates (CIR and PIR)";
            leaf pir-percent {
              type string;
              description
                  "[0.01..100.00]";
            } //pir-percent

            leaf cir {
              type string;
              description
                  "[0.00..100.00]";
            } //cir

            leaf percent-rate-id {
              type enumeration {
                enum port-limit;
                enum local-limit;
                enum reference-port-limit;
              }
              default "port-limit";
              description
                  "Attribute port-limit|local-limit|reference-port-limit for percent-rate";
            } //percent-rate-id

          } //container percent-rate

          container pool {
            description
                "Configure named pool for this queue";
            leaf pool-name {
              type string {
                length "1..32";
              }
            } //pool-name

          } //container pool

          container port-parent {
            description
                "Specify the port-scheduler to which this queue feeds";
            leaf weight {
              type uint32 {
                range "0..100";
              }
            } //weight

            leaf level {
              type uint32 {
                range "1..8";
              }
            } //level

            leaf cir-weight {
              type uint32 {
                range "0..100";
              }
            } //cir-weight

            leaf cir-level {
              type uint32 {
                range "0..8";
              }
            } //cir-level

          } //container port-parent

          container rate {
            description
                "Specify rates (CIR and PIR)";
            leaf pir-rate {
              type string;
              description
                  "Attribute pir-rate for rate";
            } //pir-rate

            leaf cir {
              type string;
              description
                  "Attribute cir-rate for rate";
            } //cir

          } //container rate

          container wred-queue {
            description
                "Configure WRED queue";
            leaf policy {
              type string {
                length "1..32";
              }
            } //policy

            leaf mode {
              type enumeration {
                enum native;
                enum pool-per-queue;
              }
            } //mode

            leaf slope-usage {
              type enumeration {
                enum default;
                enum exceed-low;
              }
            } //slope-usage

          } //container wred-queue

          container drop-tail {
            description
                "Specify drop tail";
            container exceed {
              description
                  "Specify exceed drop-tail";
              container percent-reduction-from-mbs {
                description
                    "Specify exceed drop tail percent reduction from MBS";
                leaf percent {
                  type string;
                  description
                      "[0..100|default]";
                } //percent

              } //container percent-reduction-from-mbs

            } //container exceed

            container high {
              description
                  "Specify high drop-tail";
              container percent-reduction-from-mbs {
                description
                    "Specify high drop tail percent reduction from MBS";
                leaf percent {
                  type string;
                  description
                      "[0..100|default]";
                } //percent

              } //container percent-reduction-from-mbs

            } //container high

            container highplus {
              description
                  "Specify highplus drop-tail";
              container percent-reduction-from-mbs {
                description
                    "Specify highplus drop tail percent reduction from MBS";
                leaf percent {
                  type string;
                  description
                      "[0..100|default]";
                } //percent

              } //container percent-reduction-from-mbs

            } //container highplus

            container low {
              description
                  "Specify low drop-tail";
              container percent-reduction-from-mbs {
                description
                    "Specify low drop tail percent reduction from MBS";
                leaf percent {
                  type string;
                  description
                      "[0..100|default]";
                } //percent

              } //container percent-reduction-from-mbs

            } //container low

          } //container drop-tail

          container xp-specific {
            status "obsolete";
            description
                "Configure IOM3-XP specific information";
            container packet-byte-offset {
              status "obsolete";
              description
                  "Specify packet byte offset";
              leaf add {
                type uint32 {
                  range "0..32";
                }
              } //add

              leaf subtract {
                type uint32 {
                  range "0..64";
                }
              } //subtract

            } //container packet-byte-offset

            container wred-queue {
              status "obsolete";
              description
                  "Configure WRED queue";
              leaf policy {
                type string {
                  length "1..32";
                }
              } //policy

            } //container wred-queue

          } //container xp-specific

        } //list queue

      } //list sap-egress

      list sap-ingress {
        key "policy-id";
        description
            "Configure sap-ingress policy";
        leaf policy-id {
          type string;
          description
              "[1..65535]|<name:64 char max>";
        } //policy-id

        leaf name {
          type string {
            length "1..64";
          }
        } //name

        container default-fc {
          description
              "Configure default forwarding class for this policy";
          leaf fc {
            type string;
            description
                "Attribute fc for default-fc";
          } //fc

        } //container default-fc

        container default-priority {
          description
              "Configure default priority for this policy";
          leaf low-high {
            type enumeration {
              enum low;
              enum high;
            }
            description
                "keyword - specifies the priority";
          } //low-high

        } //container default-priority

        container description {
          description
              "Description for this policy";
          leaf description-string {
            type string {
              length "1..80";
            }
          } //description-string

        } //container description

        list dot1p {
          key "dot1p-priority";
          description
              "Specify 802.1 priority mappings";
          leaf dot1p-priority {
            type int32 {
              range "0..7";
            }
          } //dot1p-priority

          leaf fc {
            type string;
            description
                "Attribute fc for dot1p";
          } //fc

          leaf priority {
            type enumeration {
              enum low;
              enum high;
            }
            description
                "keyword - specifies the priority";
          } //priority

        } //list dot1p

        container dscp {
          description
              "Specify DSCP mappings";
          leaf-list dscp-name {
            type string {
              length "1..32";
            }
            max-elements 8;
            description
                "Attribute dscp-name for dscp";
          } //dscp-name

          leaf fc {
            type string;
            description
                "Attribute fc for dscp";
          } //fc

          leaf priority {
            type enumeration {
              enum low;
              enum high;
            }
            description
                "keyword - specifies the priority";
          } //priority

        } //container dscp

        container ingress-classification-policy {
          description
              "Attach ingress classification policy";
          leaf name {
            type string {
              length "1..64";
            }
          } //name

        } //container ingress-classification-policy

        list lsp-exp {
          key "lsp-exp-value";
          description
              "Specify EXP Bits mappings";
          leaf lsp-exp-value {
            type int32 {
              range "0..7";
            }
          } //lsp-exp-value

          leaf fc {
            type string;
            description
                "Attribute fc for lsp-exp";
          } //fc

          leaf priority {
            type enumeration {
              enum low;
              enum high;
            }
            description
                "keyword - specifies the priority";
          } //priority

        } //list lsp-exp

        container policy-name {
          status "obsolete";
          description
              "Configure a name to the policy";
          leaf policy-name {
            type string;
          } //policy-name

        } //container policy-name

        list prec {
          key "ip-prec-value";
          description
              "Specify IP precedence mappings";
          leaf ip-prec-value {
            type int32 {
              range "0..7";
            }
          } //ip-prec-value

          leaf fc {
            type string;
            description
                "Attribute fc for prec";
          } //fc

          leaf priority {
            type enumeration {
              enum low;
              enum high;
            }
            description
                "keyword - specifies the priority";
          } //priority

        } //list prec

        container scope {
          description
              "Specify scope of the policy";
          leaf exclusive-template {
            type enumeration {
              enum exclusive;
              enum template;
            }
            description
                "keywords - specify type of policy";
          } //exclusive-template

        } //container scope

        container sub-insert-shared-pccrule {
          description
              "Configure insert point for shared PCC-rules";
          leaf start-entry {
            type uint32 {
              range "1..65535";
            }
          } //start-entry

          leaf count {
            type uint32 {
              range "1..65535";
            }
          } //count

        } //container sub-insert-shared-pccrule

        container dynamic-policer {
          description
              "Configure qos sap-ingress dynamic-policer";
          container cbs {
            description
                "Specify CBS size for sap-ingress dynamic-policer";
            leaf size {
              type string;
              description
                  "[0..16777216 | default]";
            } //size

            leaf bytes-kilobytes {
              type enumeration {
                enum bytes;
                enum kilobytes;
              }
            } //bytes-kilobytes

          } //container cbs

          container mbs {
            description
                "Specify MBS size for sap-ingress dynamic-policer";
            leaf size {
              type string;
              description
                  "[0..16777216 | default]";
            } //size

            leaf bytes-kilobytes {
              type enumeration {
                enum bytes;
                enum kilobytes;
              }
            } //bytes-kilobytes

          } //container mbs

          container packet-byte-offset {
            description
                "Specify packet byte offset for sap-ingress dynamic-policer";
            leaf add {
              type uint32 {
                range "0..31";
              }
            } //add

            leaf subtract {
              type uint32 {
                range "1..32";
              }
            } //subtract

          } //container packet-byte-offset

          container parent {
            description
                "Specify the arbiter to which this sap-ingress dynamic-policer feeds";
            leaf arbiter-name {
              type string {
                length "1..32";
              }
            } //arbiter-name

            leaf weight {
              type uint32 {
                range "1..100";
              }
            } //weight

            leaf level {
              type uint32 {
                range "1..8";
              }
            } //level

          } //container parent

          container range {
            description
                "Configure sap-ingress dynamic-policer";
            leaf start-entry {
              type uint32 {
                range "1..63";
              }
            } //start-entry

            leaf count {
              type uint32 {
                range "1..63";
              }
            } //count

          } //container range

          container stat-mode {
            description
                "Specify Stat Mode for sap-ingress dynamic-policer";
            leaf stat-mode {
              type enumeration {
                enum no-stats;
                enum minimal;
                enum offered-profile-no-cir;
                enum offered-priority-no-cir;
                enum offered-profile-cir;
                enum offered-priority-cir;
                enum offered-total-cir;
                enum offered-limited-profile-cir;
                enum offered-profile-capped-cir;
                enum offered-limited-capped-cir;
              }
            } //stat-mode

          } //container stat-mode

        } //container dynamic-policer

        list fc {
          key "fc";
          description
              "Configure forwarding-class to queue mappings";
          leaf fc {
            type string;
            description
                "Attribute fc for fc";
          } //fc

          container broadcast-policer {
            description
                "Specify Broadcast policer";
            leaf policer-id {
              type uint32 {
                range "1..63";
              }
            } //policer-id

            leaf fp-redirect-group {
              type boolean;
            } //fp-redirect-group

          } //container broadcast-policer

          container broadcast-queue {
            description
                "Specify the broadcast-queue";
            leaf queue-id {
              type int32 {
                range "1..32";
              }
            } //queue-id

            leaf group {
              type string {
                length "1..32";
              }
            } //group

          } //container broadcast-queue

          leaf de-1-out-profile {
            type boolean;
            description
                "Classify frames as out-profile on DE=1";
          }

          container egress-fc {
            description
                "Specify the egress override FC";
            leaf fc-name {
              type enumeration {
                enum be;
                enum l2;
                enum af;
                enum l1;
                enum h2;
                enum ef;
                enum h1;
                enum nc;
              }
              default "be";
            } //fc-name

          } //container egress-fc

          container in-remark {
            description
                "Specify the in-profile remarking";
            leaf dscp {
              type string {
                length "1..32";
              }
              description
                  "Attribute dscp-name for in-remark";
            } //dscp

            leaf prec {
              type int32 {
                range "0..7";
              }
            } //prec

          } //container in-remark

          container multicast-policer {
            description
                "Specify Multicast policer";
            leaf policer-id {
              type uint32 {
                range "1..63";
              }
            } //policer-id

            leaf fp-redirect-group {
              type boolean;
            } //fp-redirect-group

          } //container multicast-policer

          container multicast-queue {
            description
                "Specify the multicast-queue";
            leaf queue-id {
              type int32 {
                range "1..32";
              }
            } //queue-id

            leaf group {
              type string {
                length "1..32";
              }
            } //group

          } //container multicast-queue

          container out-remark {
            description
                "Specify the out-profile remarking";
            leaf dscp {
              type string {
                length "1..32";
              }
              description
                  "Attribute dscp-name for out-remark";
            } //dscp

            leaf prec {
              type int32 {
                range "0..7";
              }
            } //prec

          } //container out-remark

          container policer {
            description
                "Specify Policer";
            leaf policer-id {
              type uint32 {
                range "1..63";
              }
            } //policer-id

            leaf fp-redirect-group {
              type boolean;
            } //fp-redirect-group

          } //container policer

          container profile {
            description
                "Specify the profile to be assigned";
            leaf in-out {
              type enumeration {
                enum in;
                enum out;
              }
              description
                  "keywords - specify type of marking to be done";
            } //in-out

          } //container profile

          container queue {
            description
                "Specify the unicast-queue";
            leaf queue-id {
              type int32 {
                range "1..32";
              }
            } //queue-id

            leaf group {
              type string {
                length "1..32";
              }
            } //group

          } //container queue

          container unknown-policer {
            description
                "Specify Unknown policer";
            leaf policer-id {
              type uint32 {
                range "1..63";
              }
            } //policer-id

            leaf fp-redirect-group {
              type boolean;
            } //fp-redirect-group

          } //container unknown-policer

          container unknown-queue {
            description
                "Specify the unknown-queue";
            leaf queue-id {
              type int32 {
                range "1..32";
              }
            } //queue-id

            leaf group {
              type string {
                length "1..32";
              }
            } //group

          } //container unknown-queue

        } //list fc

        container ip-criteria {
          presence
              "Configure IP match criteria";
          container renum {
            description
                "Renumber an entry";
            leaf old-entry-id {
              type uint32 {
                range "1..65535";
              }
            } //old-entry-id

            leaf new-entry-id {
              type uint32 {
                range "1..65535";
              }
            } //new-entry-id

          } //container renum

          container type {
            description
                "Set the IP criteria type";
            leaf filter-type {
              type enumeration {
                enum normal;
                enum vxlan-vni;
              }
            } //filter-type

          } //container type

          list entry {
            key "entry-id";
            description
                "Configure an IP based policy entry";
            leaf entry-id {
              type uint32 {
                range "1..65535";
              }
              description
                  "Attribute entry-id for entry";
            } //entry-id

            container action {
              description
                  "Specify action fc, policer and priority";
              leaf fc {
                type string;
                description
                    "Attribute fc for action";
              } //fc

              leaf priority {
                type enumeration {
                  enum low;
                  enum high;
                }
                description
                    "keyword - specifies the priority";
              } //priority

              leaf policer {
                type uint32 {
                  range "1..63";
                }
              } //policer

            } //container action

            container description {
              description
                  "Description for this entry";
              leaf description-string {
                type string {
                  length "1..80";
                }
              } //description-string

            } //container description

            container match {
              description
                  "Specify IP match criteria for this policy";
              leaf protocol {
                type string;
                description
                    "Attribute protocol-id for match";
              } //protocol

              container dscp {
                description
                    "Specify DSCP match";
                leaf dscp-name {
                  type string {
                    length "1..32";
                  }
                  description
                      "Attribute dscp-name for dscp";
                } //dscp-name

              } //container dscp

              container dst-ip {
                description
                    "Specify destination IP and mask match";
                leaf ip-address-mask {
                  type inet:ip-prefix;
                  description
                      "<ip-address>/<mask>";
                } //ip-address-mask

                leaf ip-address {
                  type inet:ip-address;
                  description
                      "Attribute ip-address for dst-ip";
                } //ip-address

                leaf ipv4-address-mask {
                  type string;
                  description
                      "a.b.c.d any address mask expressed as dotted quad [0..255]";
                } //ipv4-address-mask

                leaf ip-prefix-list {
                  type string {
                    length "1..32";
                  }
                } //ip-prefix-list

              } //container dst-ip

              container dst-port {
                description
                    "Specify destination TCP/UDP port match";
                leaf dst-port-id {
                  type enumeration {
                    enum lt;
                    enum gt;
                    enum eq;
                  }
                  description
                      "Attribute for dst-port";
                } //dst-port-id

                leaf dst-port-number {
                  type string;
                  description
                      "Attribute dst-port-number for dst-port";
                } //dst-port-number

                leaf-list range {
                  type string;
                  max-elements 2;
                  description
                      "dst-port-number";
                } //range

              } //container dst-port

              container fragment {
                description
                    "Specify match criteria applies to IP fragments";
                leaf true-false {
                  type enumeration {
                    enum true;
                    enum false;
                  }
                  description
                      "keywords - specify fragment match";
                } //true-false

              } //container fragment

              container src-ip {
                description
                    "Specify source IP and mask match";
                leaf ip-address-mask {
                  type inet:ip-prefix;
                  description
                      "Attribute ip-address/mask for src-ip";
                } //ip-address-mask

                leaf src-ip-id {
                  type inet:ip-address;
                  description
                      "ip-address";
                } //src-ip-id

                leaf src-ip-string-2 {
                  type string;
                  description
                      "netmask";
                } //src-ip-string-2

                leaf ip-prefix-list {
                  type string {
                    length "1..32";
                  }
                } //ip-prefix-list

              } //container src-ip

              container src-port {
                description
                    "Specify source TCP/UDP port match";
                leaf src-port-id {
                  type enumeration {
                    enum lt;
                    enum gt;
                    enum eq;
                  }
                  description
                      "Attribute for src-port";
                } //src-port-id

                leaf src-port-number {
                  type string;
                  description
                      "Attribute src-port-number for src-port";
                } //src-port-number

                leaf-list range {
                  type string;
                  max-elements 2;
                  description
                      "src-port-number";
                } //range

              } //container src-port

              container vxlan-vni {
                description
                    "Specify VxLan VNI match";
                leaf eq {
                  type string;
                  description
                      "Attribute vni-id for vxlan-vni";
                } //eq

                leaf-list range {
                  type string;
                  max-elements 2;
                  description
                      "vni-id";
                } //range

              } //container vxlan-vni

            } //container match

          } //list entry

        } //container ip-criteria

        container ipv6-criteria {
          presence
              "Configure IPv6 match criteria";
          container renum {
            description
                "Renumber an entry";
            leaf old-entry-id {
              type uint32 {
                range "1..65535";
              }
            } //old-entry-id

            leaf new-entry-id {
              type uint32 {
                range "1..65535";
              }
            } //new-entry-id

          } //container renum

          container type {
            description
                "Set the IPv6 criteria type";
            leaf filter-type {
              type enumeration {
                enum normal;
                enum vxlan-vni;
              }
            } //filter-type

          } //container type

          list entry {
            key "entry-id";
            description
                "Configure an IPv6 based policy entry";
            leaf entry-id {
              type uint32 {
                range "1..65535";
              }
              description
                  "Attribute entry-id for entry";
            } //entry-id

            container action {
              description
                  "Specify action fc, policer and priority";
              leaf fc {
                type string;
                description
                    "Attribute fc for action";
              } //fc

              leaf priority {
                type enumeration {
                  enum low;
                  enum high;
                }
              } //priority

              leaf policer {
                type uint32 {
                  range "1..63";
                }
              } //policer

            } //container action

            container description {
              description
                  "Description for this entry";
              leaf description-string {
                type string {
                  length "1..80";
                }
              } //description-string

            } //container description

            container match {
              description
                  "Specify IPv6 match criteria for this policy";
              leaf next-header {
                type string;
                description
                    "Attribute next-header for match";
              } //next-header

              container dscp {
                description
                    "Specify DSCP match";
                leaf dscp-name {
                  type string {
                    length "1..32";
                  }
                  description
                      "Attribute dscp-name for dscp";
                } //dscp-name

              } //container dscp

              container dst-ip {
                description
                    "Specify destination IPv6 address and mask match";
                leaf ipv6-address-prefix-length {
                  type string;
                  description
                      "<ipv6-address>/<prefix-length>";
                } //ipv6-address-prefix-length

                leaf ipv6-address {
                  type inet:ipv6-address;
                  description
                      "Attribute ipv6-address for dst-ip";
                } //ipv6-address

                leaf ipv6-address-mask {
                  type inet:ipv6-address;
                  description
                      "Attribute ipv6-address-mask for dst-ip";
                } //ipv6-address-mask

              } //container dst-ip

              container dst-port {
                description
                    "Specify destination TCP/UDP port match";
                leaf dst-port-id {
                  type enumeration {
                    enum lt;
                    enum gt;
                    enum eq;
                  }
                  description
                      "Attribute for dst-port";
                } //dst-port-id

                leaf dst-port-number {
                  type string;
                  description
                      "Attribute dst-port-number for dst-port";
                } //dst-port-number

                leaf-list range {
                  type string;
                  max-elements 2;
                  description
                      "dst-port-number";
                } //range

              } //container dst-port

              container fragment {
                description
                    "Specify match criteria applies to IPv6 fragments";
                leaf true-false-first-only-non-first-only {
                  type enumeration {
                    enum true;
                    enum false;
                    enum first-only;
                    enum non-first-only;
                  }
                  description
                      "keywords - specify fragment match";
                } //true-false-first-only-non-first-only

              } //container fragment

              container src-ip {
                description
                    "Specify source IPv6 address and mask match";
                leaf ipv6-address-prefix-length {
                  type string;
                  description
                      "<ipv6-address>/<prefix-length>";
                } //ipv6-address-prefix-length

                leaf ipv6-address {
                  type inet:ipv6-address;
                  description
                      "Attribute ipv6-address for src-ip";
                } //ipv6-address

                leaf ipv6-address-mask {
                  type inet:ipv6-address;
                  description
                      "Attribute ipv6-address-mask for src-ip";
                } //ipv6-address-mask

              } //container src-ip

              container src-port {
                description
                    "Specify source TCP/UDP port match";
                leaf src-port-id {
                  type enumeration {
                    enum lt;
                    enum gt;
                    enum eq;
                  }
                  description
                      "Attribute for src-port";
                } //src-port-id

                leaf src-port-number {
                  type string;
                  description
                      "Attribute src-port-number for src-port";
                } //src-port-number

                leaf-list range {
                  type string;
                  max-elements 2;
                  description
                      "src-port-number";
                } //range

              } //container src-port

              container vxlan-vni {
                description
                    "Specify VxLan VNI match";
                leaf eq {
                  type string;
                  description
                      "Attribute vni-id for vxlan-vni";
                } //eq

                leaf-list range {
                  type string;
                  max-elements 2;
                  description
                      "vni-id";
                } //range

              } //container vxlan-vni

            } //container match

          } //list entry

        } //container ipv6-criteria

        container mac-criteria {
          presence
              "Configure MAC match criteria";
          container renum {
            description
                "Renumber an entry";
            leaf old-entry-id {
              type uint32 {
                range "1..65535";
              }
            } //old-entry-id

            leaf new-entry-id {
              type uint32 {
                range "1..65535";
              }
            } //new-entry-id

          } //container renum

          container type {
            description
                "Set the mac-criteria filter type";
            leaf filter-type {
              type enumeration {
                enum normal;
                enum vid;
              }
            } //filter-type

          } //container type

          list entry {
            key "entry-id";
            description
                "Configure a MAC based policy entry";
            leaf entry-id {
              type uint32 {
                range "1..65535";
              }
              description
                  "Attribute entry-id for entry";
            } //entry-id

            container action {
              description
                  "Specify action fc, policer and priority";
              leaf fc {
                type string;
                description
                    "Attribute fc for action";
              } //fc

              leaf priority {
                type enumeration {
                  enum low;
                  enum high;
                }
                description
                    "keywords - specify priority";
              } //priority

              leaf policer {
                type uint32 {
                  range "1..63";
                }
              } //policer

            } //container action

            container description {
              description
                  "Description for this entry";
              leaf description-string {
                type string {
                  length "1..80";
                }
              } //description-string

            } //container description

            container match {
              description
                  "Specify MAC match criteria for this policy";
              leaf frame-type {
                type enumeration {
                  enum 802dot3;
                  enum 802dot2-llc;
                  enum 802dot2-snap;
                  enum ethernet-II;
                  enum atm;
                }
                description
                    "Attribute frame-type for match";
              } //frame-type

              container atm-vci {
                description
                    "Specify ATM VC Identifier to match";
                leaf vc-id {
                  type uint32 {
                    range "1..65535";
                  }
                } //vc-id

              } //container atm-vci

              container dot1p {
                description
                    "Specify 802.1P priority and mask to match";
                leaf dot1p-value {
                  type string;
                } //dot1p-value

                leaf dot1p-mask {
                  type string;
                  description
                      "[0..7] - accepts decimal hex or binary";
                } //dot1p-mask

              } //container dot1p

              container dsap {
                description
                    "Specify DSAP value and mask to match";
                leaf dsap-value {
                  type string;
                  description
                      "[0..255] - accepts decimal hex or binary";
                } //dsap-value

                leaf dsap-mask {
                  type string;
                  description
                      "[0..255] - accepts decimal hex or binary";
                } //dsap-mask

              } //container dsap

              container dst-mac {
                description
                    "Specify destination MAC address and mask to match";
                leaf dest-ieee-address {
                  type alu:ieee-address;
                  description
                      "xx:xx:xx:xx:xx:xx OR xx-xx-xx-xx-xx-xx";
                } //dest-ieee-address

                leaf ieee-address-mask {
                  type string;
                  description
                      "xx:xx:xx:xx:xx:xx OR xx-xx-xx-xx-xx-xx";
                } //ieee-address-mask

              } //container dst-mac

              container etype {
                description
                    "Specify ethernet-type match";
                leaf t0x0600..0xffff {
                  type string;
                  description
                      "[1536..65535] - accepts in decimal or hex";
                } //t0x0600..0xffff

              } //container etype

              container inner-tag {
                description
                    "Configure vid inner tag match condition";
                leaf value {
                  type string;
                  description
                      "[0..4095] decimal or [0x0..0xFFF] hex";
                } //value

                leaf vid-mask {
                  type string;
                  description
                      "[1..4095] decimal or [0x1..0xFFF] hex";
                } //vid-mask

              } //container inner-tag

              container outer-tag {
                description
                    "Configure vid outer tag match condition";
                leaf value {
                  type string;
                  description
                      "[0..4095] decimal or [0x0..0xFFF] hex";
                } //value

                leaf vid-mask {
                  type string;
                  description
                      "[1..4095] decimal or [0x1..0xFFF] hex";
                } //vid-mask

              } //container outer-tag

              container snap-oui {
                description
                    "Specify snap-oui match";
                leaf zero-non-zero {
                  type enumeration {
                    enum zero;
                    enum non-zero;
                  }
                  description
                      "keywords - specify snap-oui match";
                } //zero-non-zero

              } //container snap-oui

              container snap-pid {
                description
                    "Specify snap-pid match";
                leaf snap-pid {
                  type string;
                  description
                      "[0..65535] - accepts decimal or hex";
                } //snap-pid

              } //container snap-pid

              container src-mac {
                description
                    "Specify source MAC and mask to match";
                leaf ieee-address {
                  type alu:ieee-address;
                  description
                      "xx:xx:xx:xx:xx:xx OR xx-xx-xx-xx-xx-xx";
                } //ieee-address

                leaf ieee-address-mask {
                  type string;
                  description
                      "xx:xx:xx:xx:xx:xx OR xx-xx-xx-xx-xx-xx";
                } //ieee-address-mask

              } //container src-mac

              container ssap {
                description
                    "Specify SSAP value and mask to match";
                leaf ssap-value {
                  type string;
                  description
                      "[0..255] - accepts decimal hex or binary";
                } //ssap-value

                leaf ssap-mask {
                  type string;
                  description
                      "[0..255] - accepts decimal hex or binary";
                } //ssap-mask

              } //container ssap

            } //container match

          } //list entry

        } //container mac-criteria

        list policer {
          key "policer-id";
          description
              "Configure Policer for this policy";
          leaf policer-id {
            type uint32 {
              range "1..63";
            }
            description
                "Attribute policer-id for policer";
          } //policer-id

          container adaptation-rule {
            description
                "Specify the CIR and PIR adaptation rules";
            leaf pir {
              type enumeration {
                enum max;
                enum min;
                enum closest;
              }
            } //pir

            leaf cir {
              type enumeration {
                enum max;
                enum min;
                enum closest;
              }
            } //cir

          } //container adaptation-rule

          container adv-config-policy {
            description
                "Configure advanced configuration policy";
            leaf adv-config-policy-name {
              type string {
                length "1..32";
              }
            } //adv-config-policy-name

          } //container adv-config-policy

          container cbs {
            description
                "Specify CBS size";
            leaf size {
              type string;
              description
                  "[0..16777216 | default]";
            } //size

            leaf cbs-id {
              type enumeration {
                enum bytes;
                enum kilobytes;
              }
            } //cbs-id

          } //container cbs

          container description {
            description
                "Description for this policer";
            leaf description-string {
              type string {
                length "1..80";
              }
            } //description-string

          } //container description

          container high-prio-only {
            description
                "Specify high priority only percent-of-mbs";
            leaf percent {
              type string;
              description
                  "[0..100 | default]";
            } //percent

          } //container high-prio-only

          container mbs {
            description
                "Specify MBS size";
            leaf size {
              type string;
              description
                  "[0..16777216 | default]";
            } //size

            leaf mbs-id {
              type enumeration {
                enum bytes;
                enum kilobytes;
              }
            } //mbs-id

          } //container mbs

          container packet-byte-offset {
            description
                "Specify packet byte offset";
            leaf add {
              type uint32 {
                range "0..31";
              }
            } //add

            leaf subtract {
              type uint32 {
                range "1..32";
              }
            } //subtract

          } //container packet-byte-offset

          container parent {
            description
                "Specify the arbiter to which this policer feeds";
            leaf arbiter-name {
              type string {
                length "1..32";
              }
            } //arbiter-name

            leaf weight {
              type uint32 {
                range "1..100";
              }
            } //weight

            leaf level {
              type uint32 {
                range "1..8";
              }
            } //level

          } //container parent

          container percent-rate {
            description
                "Specify percent rates (CIR and PIR)";
            leaf pir-percent {
              type string;
              description
                  "[0.01..100.00]";
            } //pir-percent

            leaf cir {
              type string;
              description
                  "[0.00..100.00]";
            } //cir

          } //container percent-rate

          leaf profile-capped {
            type boolean;
            description
                "Configure Profile Cap";
          }

          container rate {
            description
                "Specify rates (CIR and PIR)";
            leaf pir-rate {
              type string;
              description
                  "[1..6400000000|max] Kbps";
            } //pir-rate

            leaf cir {
              type string;
              description
                  "[0..6400000000|max] Kbps";
            } //cir

          } //container rate

          container stat-mode {
            description
                "Specify Stat Mode for the policer";
            leaf stat-mode {
              type enumeration {
                enum no-stats;
                enum minimal;
                enum offered-profile-no-cir;
                enum offered-priority-no-cir;
                enum offered-profile-cir;
                enum offered-priority-cir;
                enum offered-total-cir;
                enum offered-limited-profile-cir;
                enum offered-profile-capped-cir;
                enum offered-limited-capped-cir;
                enum offered-profile-with-discards;
              }
            } //stat-mode

          } //container stat-mode

        } //list policer

        list queue {
          key "queue-id";
          description
              "Configure a queue";
          leaf queue-id {
            type int32 {
              range "1..32";
            }
          } //queue-id

          leaf multipoint {
            type boolean;
            description
                "keyword - mandatory while creating a multipoint queue";
          } //multipoint

          leaf queue-type {
            type enumeration {
              enum expedite;
              enum best-effort;
              enum auto-expedite;
            }
            description
                "expedite|best-effort|auto-expedite - keywords";
          } //queue-type

          leaf queue-mode {
            type enumeration {
              enum profile-mode;
              enum priority-mode;
            }
            description
                "profile-mode|priority-mode - keywords";
          } //queue-mode

          container adaptation-rule {
            description
                "Specify the information rate adaptation rules";
            leaf pir {
              type enumeration {
                enum max;
                enum min;
                enum closest;
              }
            } //pir

            leaf cir {
              type enumeration {
                enum max;
                enum min;
                enum closest;
              }
            } //cir

            leaf fir {
              type enumeration {
                enum max;
                enum min;
                enum closest;
              }
            } //fir

          } //container adaptation-rule

          container adv-config-policy {
            description
                "Configure advanced configuration policy";
            leaf adv-config-policy-name {
              type string {
                length "1..32";
              }
            } //adv-config-policy-name

          } //container adv-config-policy

          container burst-limit {
            description
                "Specify burst limit";
            leaf size {
              type string;
              description
                  "Attribute size for burst-limit";
            } //size

            leaf bytes-kilobytes {
              type enumeration {
                enum bytes;
                enum kilobytes;
              }
            } //bytes-kilobytes

          } //container burst-limit

          container cbs {
            description
                "Specify CBS size";
            leaf size-in-kbytes {
              type string;
              description
                  "Attribute size-in-kbytes for cbs";
            } //size-in-kbytes

          } //container cbs

          leaf cir-non-profiling {
            type boolean;
            description
                "CIR non profiling";
          }

          container high-prio-only {
            status "obsolete";
            description
                "Specify high priority only burst size";
            leaf percent {
              type string;
              description
                  "[0..100 | default]";
            } //percent

          } //container high-prio-only

          container mbs {
            description
                "Specify MBS size";
            leaf size {
              type string;
              description
                  "Attribute size for mbs";
            } //size

            leaf bytes-kilobytes {
              type enumeration {
                enum bytes;
                enum kilobytes;
              }
              description
                  "keyword";
            } //bytes-kilobytes

          } //container mbs

          container packet-byte-offset {
            description
                "Specify packet byte offset";
            leaf add {
              type uint32 {
                range "0..30";
              }
              description
                  "[0..30] - Only even values are supported";
            } //add

            leaf subtract {
              type uint32 {
                range "0..32";
              }
              description
                  "[0..32] - Only even values are supported";
            } //subtract

          } //container packet-byte-offset

          container parent {
            description
                "Specify the scheduler to which this queue feeds";
            leaf scheduler-name {
              type string {
                length "1..32";
              }
            } //scheduler-name

            leaf weight {
              type uint32 {
                range "0..100";
              }
            } //weight

            leaf level {
              type uint32 {
                range "1..8";
              }
            } //level

            leaf cir-weight {
              type uint32 {
                range "0..100";
              }
            } //cir-weight

            leaf cir-level {
              type uint32 {
                range "0..8";
              }
            } //cir-level

          } //container parent

          container percent-rate {
            description
                "Specify percent information rates";
            leaf pir-percent {
              type string;
              description
                  "[0.01..100.00]";
            } //pir-percent

            leaf cir {
              type string;
              description
                  "[0.00..100.00]";
            } //cir

            leaf fir {
              type string;
              description
                  "[0.00..100.00]";
            } //fir

            leaf police {
              type boolean;
            } //police

            leaf percent-rate-id {
              type enumeration {
                enum port-limit;
                enum local-limit;
                enum reference-port-limit;
              }
              default "port-limit";
              description
                  "Attribute port-limit|local-limit|reference-port-limit for percent-rate";
            } //percent-rate-id

          } //container percent-rate

          container pool {
            description
                "Configure named pool for this queue";
            leaf pool-name {
              type string {
                length "1..32";
              }
            } //pool-name

          } //container pool

          container rate {
            description
                "Specify information rates";
            leaf pir-rate {
              type string;
              description
                  "Attribute pir-rate for rate";
            } //pir-rate

            leaf cir {
              type string;
              description
                  "Attribute cir-rate for rate";
            } //cir

            leaf fir {
              type string;
              description
                  "Attribute fir-rate for rate";
            } //fir

            leaf police {
              type boolean;
            } //police

          } //container rate

          container drop-tail {
            description
                "Specify drop tail";
            container low {
              description
                  "Specify low drop-tail";
              container percent-reduction-from-mbs {
                description
                    "Specify low drop tail percent reduction from MBS";
                leaf percent {
                  type string;
                  description
                      "[0..100|default]";
                } //percent

              } //container percent-reduction-from-mbs

            } //container low

          } //container drop-tail

        } //list queue

      } //list sap-ingress

      list scheduler-policy {
        key "scheduler-policy-name";
        description
            "Configure a scheduler-policy";
        leaf scheduler-policy-name {
          type string {
            length "1..32";
          }
        } //scheduler-policy-name

        container description {
          description
              "Description for this policy";
          leaf description-string {
            type string {
              length "1..80";
            }
          } //description-string

        } //container description

        leaf frame-based-accounting {
          type boolean;
          description
              "Configure frame-based accounting for queues";
        }

        list tier {
          key "tier";
          description
              "Configure schedulers in a particular tier";
          leaf tier {
            type uint32 {
              range "1..3";
            }
          } //tier

          container parent-location {
            description
                "Configure parent location";
            leaf parent-loc {
              type enumeration {
                enum none;
                enum sub;
                enum vport;
              }
            } //parent-loc

          } //container parent-location

          list scheduler {
            key "scheduler-name";
            description
                "Configure a scheduler";
            leaf scheduler-name {
              type string {
                length "1..32";
              }
            } //scheduler-name

            container description {
              description
                  "Description for this policy";
              leaf description-string {
                type string {
                  length "1..80";
                }
              } //description-string

            } //container description

            leaf limit-unused-bandwidth {
              type boolean;
              description
                  "Specify whether to enable limit unused bandwidth";
            }

            container parent {
              description
                  "Specify the scheduler to which this scheduler feeds";
              leaf scheduler-name {
                type string {
                  length "1..32";
                }
              } //scheduler-name

              leaf weight {
                type uint32 {
                  range "0..100";
                }
              } //weight

              leaf level {
                type uint32 {
                  range "1..8";
                }
              } //level

              leaf cir-weight {
                type uint32 {
                  range "0..100";
                }
              } //cir-weight

              leaf cir-level {
                type uint32 {
                  range "0..8";
                }
              } //cir-level

            } //container parent

            container port-parent {
              description
                  "Specify the port-scheduler to which this scheduler feeds";
              leaf weight {
                type uint32 {
                  range "0..100";
                }
              } //weight

              leaf level {
                type uint32 {
                  range "1..8";
                }
              } //level

              leaf cir-weight {
                type uint32 {
                  range "0..100";
                }
              } //cir-weight

              leaf cir-level {
                type uint32 {
                  range "0..8";
                }
              } //cir-level

            } //container port-parent

            container rate {
              description
                  "Specify rates (CIR and PIR)";
              leaf pir-rate {
                type string;
                description
                    "[1..6400000000|max] Kbps";
              } //pir-rate

              leaf cir {
                type string;
                description
                    "[0..6400000000|sum|max] Kbps";
              } //cir

            } //container rate

          } //list scheduler

        } //list tier

      } //list scheduler-policy

      list shared-queue {
        key "policy-name";
        description
            "Configure shared-queue policy";
        leaf policy-name {
          type string {
            length "1..32";
          }
        } //policy-name

        container description {
          description
              "Description for this policy";
          leaf description-string {
            type string {
              length "1..80";
            }
          } //description-string

        } //container description

        list fc {
          key "fc-name";
          description
              "Configure forwarding-class to queue mappings";
          leaf fc-name {
            type enumeration {
              enum be;
              enum l2;
              enum af;
              enum l1;
              enum h2;
              enum ef;
              enum h1;
              enum nc;
            }
            description
                "be|l2|af|l1|h2|ef|h1|nc - keywords";
          } //fc-name

          container broadcast-queue {
            description
                "Specify the broadcast-queue";
            leaf queue-id {
              type int32 {
                range "9..32";
              }
            } //queue-id

          } //container broadcast-queue

          container multicast-queue {
            description
                "Specify the multicast-queue";
            leaf queue-id {
              type int32 {
                range "9..32";
              }
            } //queue-id

          } //container multicast-queue

          container queue {
            description
                "Specify the unicast-queue";
            leaf queue-id {
              type int32 {
                range "1..8";
              }
            } //queue-id

          } //container queue

          container unknown-queue {
            description
                "Specify the unknown-queue";
            leaf queue-id {
              type int32 {
                range "9..32";
              }
            } //queue-id

          } //container unknown-queue

        } //list fc

        list queue {
          key "queue-id";
          description
              "Configure a queue";
          leaf queue-id {
            type int32 {
              range "1..32";
            }
          } //queue-id

          leaf queue-type {
            type enumeration {
              enum expedite;
              enum best-effort;
              enum auto-expedite;
            }
            description
                "expedite|best-effort|auto-expedite - keywords";
          } //queue-type

          leaf multipoint {
            type boolean;
            description
                "keyword - create a multipoint queue";
          } //multipoint

          container cbs {
            description
                "Specify CBS size";
            leaf percent {
              type uint32 {
                range "0..100";
              }
            } //percent

          } //container cbs

          container high-prio-only {
            status "obsolete";
            description
                "Specify high priority only burst size";
            leaf percent {
              type string;
              description
                  "[0..100 | default]";
            } //percent

          } //container high-prio-only

          container mbs {
            description
                "Specify MBS size";
            leaf percent {
              type uint32 {
                range "0..100";
              }
            } //percent

          } //container mbs

          container pool {
            description
                "Configure named pool for this queue";
            leaf pool-name {
              type string {
                length "1..32";
              }
            } //pool-name

          } //container pool

          container rate {
            description
                "Specify information rates";
            leaf pir-percent {
              type uint32 {
                range "1..100";
              }
            } //pir-percent

            leaf cir {
              type uint32 {
                range "0..100";
              }
            } //cir

            leaf fir {
              type uint32 {
                range "0..100";
              }
            } //fir

          } //container rate

          container drop-tail {
            description
                "Specify drop tail";
            container low {
              description
                  "Specify low drop-tail";
              container percent-reduction-from-mbs {
                description
                    "Specify low drop tail percent reduction from MBS";
                leaf percent {
                  type string;
                  description
                      "[0..100|default]";
                } //percent

              } //container percent-reduction-from-mbs

            } //container low

          } //container drop-tail

        } //list queue

      } //list shared-queue

      list slope-policy {
        key "name";
        description
            "Configure a slope-policy";
        leaf name {
          type string {
            length "1..32";
          }
        } //name

        container description {
          description
              "Description for the slope policy policy";
          leaf description-string {
            type string {
              length "1..80";
            }
          } //description-string

        } //container description

        container time-average-factor {
          description
              "Configure time average factor";
          leaf value {
            type uint32 {
              range "0..15";
            }
          } //value

        } //container time-average-factor

        container exceed-slope {
          presence
              "Configure exceed-prio RED slope parameters";
          container max-avg {
            description
                "Configure max average";
            leaf percent {
              type uint32 {
                range "0..100";
              }
            } //percent

          } //container max-avg

          container max-prob {
            description
                "Configure max probability";
            leaf percent {
              type uint32 {
                range "0..100";
              }
            } //percent

          } //container max-prob

          leaf shutdown {
            type boolean;
            description
                "Administratively enable/disable exceed slope";
          }

          container start-avg {
            description
                "Configure starting average";
            leaf percent {
              type uint32 {
                range "0..100";
              }
            } //percent

          } //container start-avg

        } //container exceed-slope

        container high-slope {
          presence
              "Configure high-prio RED slope parameters";
          container max-avg {
            description
                "Configure max average";
            leaf percent {
              type uint32 {
                range "0..100";
              }
            } //percent

          } //container max-avg

          container max-prob {
            description
                "Configure max probability";
            leaf percent {
              type uint32 {
                range "0..100";
              }
            } //percent

          } //container max-prob

          leaf shutdown {
            type boolean;
            description
                "Administratively enable/disable high slope";
          }

          container start-avg {
            description
                "Configure starting average";
            leaf percent {
              type uint32 {
                range "0..100";
              }
            } //percent

          } //container start-avg

        } //container high-slope

        container highplus-slope {
          presence
              "Configure high-plus-prio RED slope parameters";
          container max-avg {
            description
                "Configure max average";
            leaf percent {
              type uint32 {
                range "0..100";
              }
            } //percent

          } //container max-avg

          container max-prob {
            description
                "Configure max probability";
            leaf percent {
              type uint32 {
                range "0..100";
              }
            } //percent

          } //container max-prob

          leaf shutdown {
            type boolean;
            description
                "Administratively enable/disable exceed slope";
          }

          container start-avg {
            description
                "Configure starting average";
            leaf percent {
              type uint32 {
                range "0..100";
              }
            } //percent

          } //container start-avg

        } //container highplus-slope

        container low-slope {
          presence
              "Configure low-prio RED slope parameters";
          container max-avg {
            description
                "Configure max average";
            leaf percent {
              type uint32 {
                range "0..100";
              }
            } //percent

          } //container max-avg

          container max-prob {
            description
                "Configure max probability";
            leaf percent {
              type uint32 {
                range "0..100";
              }
            } //percent

          } //container max-prob

          leaf shutdown {
            type boolean;
            description
                "Administratively enable/disable low slope";
          }

          container start-avg {
            description
                "Configure starting average";
            leaf percent {
              type uint32 {
                range "0..100";
              }
            } //percent

          } //container start-avg

        } //container low-slope

      } //list slope-policy

      list vlan-qos-policy {
        key "vlan-qos-policy-name";
        description
            "Configure a vlan-qos-policy";
        leaf vlan-qos-policy-name {
          type string;
          description
              "<name:64 char max>";
        } //vlan-qos-policy-name

        container description {
          description
              "Description for the vlan qos policy policy";
          leaf description-string {
            type string {
              length "1..80";
            }
          } //description-string

        } //container description

        container scope {
          description
              "Scope of the policy";
          leaf exclusive-template {
            type enumeration {
              enum exclusive;
              enum template;
            }
          } //exclusive-template

        } //container scope

        container stat-mode {
          description
              "Statistics-mode of this policy";
          leaf stat-mode {
            type enumeration {
              enum no-stats;
              enum enqueued-with-discards;
            }
          } //stat-mode

        } //container stat-mode

        list cir-weight-profile {
          key "profile-id";
          description
              "To configure weight profile";
          leaf profile-id {
            type uint32 {
              range "1..2";
            }
          } //profile-id

          container weight {
            description
                "To configure weight of this policy";
            leaf weight {
              type uint32 {
                range "1..1024";
              }
            } //weight

          } //container weight

        } //list cir-weight-profile

        list fc {
          key "fc-name";
          description
              "Configure forwarding-class mappings";
          leaf fc-name {
            type enumeration {
              enum be;
              enum l2;
              enum af;
              enum l1;
              enum h2;
              enum ef;
              enum h1;
              enum nc;
            }
            description
                "be|l2|af|l1|h2|ef|h1|nc - keywords";
          } //fc-name

          container queue {
            description
                "Specify the queue to forward this FC traffic";
            leaf queue-id {
              type int32 {
                range "1..8";
              }
            } //queue-id

          } //container queue

        } //list fc

        list queue {
          key "queue-id";
          description
              "Queue configurations";
          leaf queue-id {
            type uint32 {
              range "1..8";
            }
          } //queue-id

          container adaptation-rule {
            description
                "To configure adaptation rule";
            leaf pir {
              type enumeration {
                enum max;
                enum min;
                enum closest;
              }
            } //pir

            leaf cir {
              type enumeration {
                enum max;
                enum min;
                enum closest;
              }
            } //cir

          } //container adaptation-rule

          container queue-mgmt {
            description
                "Queue Management determines the queue management policy attached to this queue";
            leaf queue-mgmt {
              type string {
              }
              description
                  "[64 chars max]";
            } //queue-mgmt

          } //container queue-mgmt

          container queue-type {
            description
                "Queue-type of this queue";
            leaf queue-type {
              type enumeration {
                enum best-effort;
                enum expedite-hi;
                enum expedite-lo;
              }
            } //queue-type

            container cir-weight-profile {
              description
                  "To attach cir-weight-profile id";
              leaf cir-weight-profile-id {
                type uint32 {
                  range "1..2";
                }
              } //cir-weight-profile-id

            } //container cir-weight-profile

            container percent-rate {
              description
                  "Specify PIR and CIR in percent";
              leaf pir-percentage {
                type string;
                description
                    "[0.01..100.00]";
              } //pir-percentage

              leaf cir {
                type string;
                description
                    "[0.00..100.00]";
              } //cir

            } //container percent-rate

          } //container queue-type

        } //list queue

      } //list vlan-qos-policy

    } //container qos

  } //grouping alu-conf-qos-r13

} //module  alu-conf-qos-r13
