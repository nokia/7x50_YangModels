module alu-conf-grpencryp-r13 {
  yang-version "1";

  namespace "urn:alcatel-lucent.com:sros:ns:yang:conf-grpencryp-r13";

  prefix "conf-grpencryp-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure group encryption parameters on SR 
       OS based routers. 
       
       Copyright 2014-2015 Alcatel-Lucent, 2016 Nokia. All rights reserved. 
       Reproduction of this document is authorized on the condition that the 
       foregoing copyright notice is included. 
       
       This alu-conf-grpencryp-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-grpencryp-r13 {
    container group-encryption {
      description
          "Configure group encryption parameters";
      container group-encryption-label {
        description
            "Configure system encryption label";
        leaf encryption-label {
          type uint32 {
            range "32..2047";
          }
          description
              "Attribute encryption-label for group-encryption-label";
        } //encryption-label

      } //container group-encryption-label

      list encryption-keygroup {
        key "keygroup-id";
        description
            "Configure encryption keygroup";
        leaf keygroup-id {
          type string;
          description
              "Attribute keygroup-id for encryption-keygroup";
        } //keygroup-id

        container active-outbound-sa {
          description
              "Configure active outbound SA for this encryption keygroup";
          leaf spi {
            type uint32 {
              range "1..1023";
            }
          } //spi

        } //container active-outbound-sa

        container description {
          description
              "Configure description for this encryption keygroup";
          leaf description-string {
            type string {
              length "1..80";
            }
          } //description-string

        } //container description

        container esp-auth-algorithm {
          description
              "Configure authentication algorithm for this encryption keygroup";
          leaf esp-auth-algorithm-id {
            type enumeration {
              enum sha256;
              enum sha512;
            }
          } //esp-auth-algorithm-id

        } //container esp-auth-algorithm

        container esp-encryption-algorithm {
          description
              "Configure encryption algorithm for this encryption keygroup";
          leaf esp-encryption-algorithm-id {
            type enumeration {
              enum aes128;
              enum aes256;
            }
          } //esp-encryption-algorithm-id

        } //container esp-encryption-algorithm

        container keygroup-name {
          description
              "Configure a name to the keygroup";
          leaf keygroup-name {
            type string;
          } //keygroup-name

        } //container keygroup-name

        list security-association {
          key "spi";
          description
              "Configure security association for this encryption keygroup";
          leaf spi {
            type uint32 {
              range "1..1023";
            }
          } //spi

          leaf authentication-key {
            type string;
            description
                "[0x0..0xFFFFFFFF...(max 128 hex nibbles)]";
          } //authentication-key

          leaf encryption-key {
            type string;
            description
                "[0x0..0xFFFFFFFF...(max 64 hex nibbles)]";
          } //encryption-key

          leaf crypto {
            type boolean;
          } //crypto

        } //list security-association

      } //list encryption-keygroup

    } //container group-encryption

  } //grouping alu-conf-grpencryp-r13

} //module  alu-conf-grpencryp-r13
