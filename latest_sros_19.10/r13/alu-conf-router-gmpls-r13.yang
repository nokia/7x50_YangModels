module alu-conf-router-gmpls-r13 {
  yang-version "1";

  namespace "urn:alcatel-lucent.com:sros:ns:yang:conf-router-gmpls-r13";

  prefix "conf-router-gmpls-r13";

  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure GMPLS on SR OS based routers. 
       
       Copyright 2014-2015 Alcatel-Lucent, 2016 Nokia. All rights reserved. 
       Reproduction of this document is authorized on the condition that the 
       foregoing copyright notice is included. 
       
       This alu-conf-router-gmpls-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-router-gmpls-r13 {
    container gmpls {
      presence
          "Configure GMPLS";
      container gr-helper-time {
        description
            "Configure restart and recovery interval";
        leaf max-recovery {
          type int32 {
            range "1..1800";
          }
          default 300;
          description
              "[1..1800] Default - 300 seconds";
        } //max-recovery

        leaf max-restart {
          type int32 {
            range "1..300";
          }
          default 180;
          description
              "[1..300] Default - 180 seconds";
        } //max-restart

      } //container gr-helper-time

      container keep-multiplier {
        description
            "Keep-multiplier used to declare a reservation or neighbor as down";
        leaf number {
          type uint16 {
            range "1..255";
          }
          default 3;
          description
              "[1..255] Default - 3";
        } //number

      } //container keep-multiplier

      container lsp-init-retry-timeout {
        description
            "Configure LSP initial retry timeout";
        leaf seconds {
          type uint32 {
            range "10..600";
          }
          default 30;
          description
              "[10..600] Default - 30";
        } //seconds

      } //container lsp-init-retry-timeout

      container rapid-retransmit-time {
        description
            "Configure rapid retransmission interval for reliable delivery of GMPLS 
             messages";
        leaf hundred-milliseconds {
          type uint32 {
            range "1..100";
          }
          default 5;
          description
              "[1..100] Default - 5";
        } //hundred-milliseconds

      } //container rapid-retransmit-time

      container rapid-retry-limit {
        description
            "Configure rapid retry limit for reliable delivery of GMPLS messages";
        leaf limit {
          type uint32 {
            range "1..6";
          }
          default 3;
          description
              "[1..6] Default - 3";
        } //limit

      } //container rapid-retry-limit

      container refresh-time {
        description
            "Interval between successive Path refresh Resv refresh and Srefresh messages";
        leaf seconds {
          type uint32 {
            range "1..65535";
          }
          default 30;
          description
              "[1..65535] Default - 30";
        } //seconds

      } //container refresh-time

      leaf shutdown {
        type boolean;
        description
            "Administratively enable/disable the GMPLS instance";
      }

      list lsp {
        key "lsp-name";
        description
            "Creates an LSP that will be signaled dynamically";
        leaf lsp-name {
          type string {
            length "1..32";
          }
        } //lsp-name

        leaf lsp-type {
          type enumeration {
            enum gmpls-uni;
          }
        } //lsp-type

        container e2e-protection-type {
          description
              "Configures the end to end protection type for this LSP.";
          leaf protection-type {
            type enumeration {
              enum unprotected;
              enum one-to-n;
              enum sbr;
            }
            description
                "Attribute protection-type for e2e-protection-type";
          } //protection-type

        } //container e2e-protection-type

        container encoding-type {
          description
              "Configure the encoding type of the payload for this LSP.";
          leaf encoding-type {
            type enumeration {
              enum line;
            }
          } //encoding-type

        } //container encoding-type

        container generalized-pid {
          description
              "Configure generalized pid for this LSP.";
          leaf generalized-pid {
            type enumeration {
              enum ethernet;
            }
          } //generalized-pid

        } //container generalized-pid

        container retry-limit {
          description
              "Max number of attempts made to reestablish the LSP after it has failed.";
          leaf number {
            type uint16 {
              range "0..10000";
            }
            default 0;
            description
                "[0..10000] Default - 0";
          } //number

        } //container retry-limit

        container retry-timer {
          description
              "Time between attempts to reestablish the LSP after it has failed.";
          leaf seconds {
            type uint32 {
              range "1..600";
            }
            default 30;
            description
                "[1..600] Default - 30";
          } //seconds

        } //container retry-timer

        container revert-timer {
          description
              "Configure revert timer for this LSP.";
          leaf seconds {
            type uint32 {
              range "0..1800";
            }
            default 0;
            description
                "[0..1800] Default - 0";
          } //seconds

        } //container revert-timer

        leaf shutdown {
          type boolean;
          description
              "Administratively enable/disable the LSP.";
        }

        container switching-type {
          description
              "Configure switching type for this LSP.";
          leaf switching-type {
            type enumeration {
              enum dcsc;
            }
          } //switching-type

        } //container switching-type

        container to {
          description
              "IP address of the egress router for the LSP";
          leaf ip-address {
            type inet:ip-address;
          } //ip-address

        } //container to

        list protect-path {
          key "path-name";
          description
              "Configure the protection path";
          leaf path-name {
            type string {
              length "1..32";
            }
          } //path-name

          container bandwidth {
            description
                "Configure bandwidth for this LSP path.";
            leaf signal-type {
              type enumeration {
                enum ds0;
                enum ds1;
                enum e1;
                enum ds2;
                enum e2;
                enum ethernet;
                enum e3;
                enum ds3;
                enum sts-1;
                enum fast-ethernet;
                enum e4;
                enum fc-0-133m;
                enum oc-3/stm-1;
                enum fc-0-266m;
                enum fc-0-531m;
                enum oc-12/stm-4;
                enum gige;
                enum fc-0-1062m;
                enum oc-48/stm-16;
                enum oc-192/stm-64;
                enum 10gige-ieee;
                enum oc-768/stm-256;
                enum 100gige-ieee;
              }
            } //signal-type

          } //container bandwidth

          container exclude-srlg {
            description
                "Configure srlg group that are excluded for this protect path.";
            leaf-list group-name {
              type string {
                length "1..32";
              }
              max-elements 5;
            } //group-name

          } //container exclude-srlg

          container peer {
            description
                "Configure peer to be used for this LSP path";
            leaf peer-node-id {
              type string {
              }
              description
                  "a.b.c.d|<1..4294967295>";
            } //peer-node-id

          } //container peer

          container segment-protection-type {
            description
                "Configure Segment protection type for this LSP path.";
            leaf segment-protection-type {
              type enumeration {
                enum unprotected;
                enum sbr;
                enum gr;
                enum sncp;
                enum prc;
              }
            } //segment-protection-type

          } //container segment-protection-type

          leaf shutdown {
            type boolean;
            description
                "Administratively enable/disable the LSP protect-path";
          }

        } //list protect-path

        list working-path {
          key "path-name";
          description
              "Configure the working path";
          leaf path-name {
            type string {
              length "1..32";
            }
          } //path-name

          container bandwidth {
            description
                "Configure bandwidth for this LSP path.";
            leaf signal-type {
              type enumeration {
                enum ds0;
                enum ds1;
                enum e1;
                enum ds2;
                enum e2;
                enum ethernet;
                enum e3;
                enum ds3;
                enum sts-1;
                enum fast-ethernet;
                enum e4;
                enum fc-0-133m;
                enum oc-3/stm-1;
                enum fc-0-266m;
                enum fc-0-531m;
                enum oc-12/stm-4;
                enum gige;
                enum fc-0-1062m;
                enum oc-48/stm-16;
                enum oc-192/stm-64;
                enum 10gige-ieee;
                enum oc-768/stm-256;
                enum 100gige-ieee;
              }
            } //signal-type

          } //container bandwidth

          container exclude-srlg {
            description
                "Configure srlg group that are excluded for this protect path.";
            leaf-list group-name {
              type string {
                length "1..32";
              }
              max-elements 5;
            } //group-name

          } //container exclude-srlg

          container peer {
            description
                "Configure peer to be used for this LSP path";
            leaf peer-node-id {
              type string {
              }
              description
                  "a.b.c.d|<1..4294967295>";
            } //peer-node-id

          } //container peer

          container segment-protection-type {
            description
                "Configure Segment protection type for this LSP path.";
            leaf segment-protection-type {
              type enumeration {
                enum unprotected;
                enum sbr;
                enum gr;
                enum sncp;
                enum prc;
              }
            } //segment-protection-type

          } //container segment-protection-type

          leaf shutdown {
            type boolean;
            description
                "Administratively enable/disable the LSP working-path";
          }

        } //list working-path

      } //list lsp

      list path {
        key "path-name";
        description
            "Configure the path to be used for a GLSP";
        leaf path-name {
          type string {
            length "1..32";
          }
        } //path-name

        list hop {
          key "hop-index";
          description
              "Configure the IP address of the hops that the GMPLS should traverse on its way 
               to the egress";
          leaf hop-index {
            type uint32 {
              range "1..1024";
            }
          } //hop-index

          leaf node-id {
            type string {
            }
            description
                "a.b.c.d|<1..4294967295>";
          } //node-id

          leaf te-link {
            type uint32 {
              range "1..4294967295";
            }
          } //te-link

          leaf strict-loose {
            type enumeration {
              enum strict;
              enum loose;
            }
            description
                "keywords";
          } //strict-loose

        } //list hop

        leaf shutdown {
          type boolean;
          description
              "Administratively enable/disable the GMPLS path.";
        }

      } //list path

      list peer {
        key "peer-node-id";
        description
            "Configure peer to be used for GMPLS";
        leaf peer-node-id {
          type string {
            length "1..15";
          }
          description
              "a.b.c.d|<1..4294967295>";
        } //peer-node-id

        container hello-interval {
          description
              "Configure the hello interval for this GMPLS peer instance";
          leaf milli-seconds {
            type uint32 {
              range "0..60000";
            }
            description
                "[0..60000] - only multiples of 1000 allowed";
          } //milli-seconds

        } //container hello-interval

        container lsp-hold-timer {
          description
              "Configure Hold Timer for this GMPLS peer instance.";
          leaf seconds {
            type uint32 {
              range "5..300";
            }
            default 60;
            description
                "[5..300] Default - 60";
          } //seconds

        } //container lsp-hold-timer

        leaf shutdown {
          type boolean;
          description
              "Administratively enable/disable the GMPLS peer instance";
        }

      } //list peer

      list te-link {
        key "te-link-id";
        description
            "Configure LMP Traffic Engineering (TE) link information";
        leaf te-link-id {
          type string {
            length "1..32";
          }
          description
              "[1..4294967295]|<te-link-name>";
        } //te-link-id

        leaf shutdown {
          type boolean;
          description
              "Administratively enable/disable the TE link";
        }

      } //list te-link

    } //container gmpls

  } //grouping alu-conf-router-gmpls-r13

} //module  alu-conf-router-gmpls-r13
