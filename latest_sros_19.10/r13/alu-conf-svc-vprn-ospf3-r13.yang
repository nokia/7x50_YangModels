module alu-conf-svc-vprn-ospf3-r13 {
  yang-version "1";

  namespace "urn:alcatel-lucent.com:sros:ns:yang:conf-svc-vprn-ospf3-r13";

  prefix "conf-svc-vprn-ospf3-r13";

  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure OSPFv3 for VPRN services on SR OS 
       based routers. 
       
       Copyright 2014-2015 Alcatel-Lucent, 2016 Nokia. All rights reserved. 
       Reproduction of this document is authorized on the condition that the 
       foregoing copyright notice is included. 
       
       This alu-conf-svc-vprn-ospf3-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2021-08-11";

  grouping alu-conf-svc-vprn-ospf3-r13 {
    list ospf3 {
      key "ospf-instance";
      description
          "Configure OSPFv3 for VPRN services";
      leaf router-id-create {
        type inet:ip-address;
        description
            "<ip-address>";
      } //router-id-create

      leaf ospf-instance {
        type uint32 {
          range "0..127";
        }
        description
            "Attribute ospf-instance for ospf3";
      } //ospf-instance

      container advertise-router-capability {
        description
            "Enable/disable router advertisement capabilities";
        leaf advertise-router-capability-id {
          type enumeration {
            enum link;
            enum area;
            enum as;
          }
        } //advertise-router-capability-id

      } //container advertise-router-capability

      container export {
        description
            "Configure export route policies to determine which routes are exported from 
             the route table";
        leaf-list policy-name {
          type string {
            length "1..32";
          }
          max-elements 5;
        } //policy-name

      } //container export

      container export-limit {
        description
            "Maximum number of routes (prefixes) that can be exported into OSPF3 from the 
             route table.";
        leaf number {
          type uint32 {
            range "1..4294967295";
          }
        } //number

        leaf log {
          type uint16 {
            range "1..100";
          }
        } //log

      } //container export-limit

      container external-db-overflow {
        description
            "Limit on number of AS-external-LSAs in LSDB and wait time before processing 
             these if limit is exceeded";
        leaf limit {
          type int64 {
            range "-1..2147483647";
          }
          description
              "[0..2147483647]";
        } //limit

        leaf interval {
          type int32 {
            range "0..2147483647";
          }
          description
              "[0..2147483647] seconds";
        } //interval

      } //container external-db-overflow

      container external-preference {
        description
            "Preference for OSPF3 external routes";
        leaf preference {
          type uint16 {
            range "1..255";
          }
          default 150;
        } //preference

      } //container external-preference

      leaf ignore-dn-bit {
        type boolean;
        description
            "Enable/disable whether this instance of OSPF3 will ignore the DN bit for OSPF3 
             LSA packets";
      }

      container import {
        description
            "Configure import route policies to determine which routes are imported into 
             the route table";
        leaf-list policy-name {
          type string {
            length "1..32";
          }
          max-elements 5;
        } //policy-name

      } //container import

      leaf loopfree-alternate {
        type boolean;
        status "obsolete";
        description
            "Enable/disable loopfree-alternate for OSPF3";
      }

      container loopfree-alternate-exclude {
        status "obsolete";
        description
            "Configure LFA exclude policies";
        leaf-list prefix-policy {
          type string {
            length "1..32";
          }
          max-elements 5;
        } //prefix-policy

      } //container loopfree-alternate-exclude

      leaf multicast-import {
        type boolean;
        description
            "Enable/disable submission of routes into the multicast Route Table Manager by 
             OSPF3";
      }

      container overload {
        description
            "Configure the local router so that it appears to be overloaded";
        leaf timeout {
          type uint32 {
            range "60..1800";
          }
        } //timeout

      } //container overload

      leaf overload-include-ext-1 {
        type boolean;
        description
            "Enable/disable OSPF maximum metric usage for external type-1 routes in case of 
             overload";
      }

      leaf overload-include-ext-2 {
        type boolean;
        description
            "Enable/disable OSPF maximum metric usage for external type-2 routes in case of 
             overload";
      }

      leaf overload-include-stub {
        type boolean;
        description
            "Enable/disable OSPF3 maximum metric usage for stub advertisement in case of 
             overload";
      }

      container overload-on-boot {
        description
            "Configure the local router so that it appears to be overloaded at boot up";
        leaf timeout {
          type uint32 {
            range "60..1800";
          }
        } //timeout

      } //container overload-on-boot

      container preference {
        description
            "Preference for OSPF3 internal routes";
        leaf preference {
          type uint16 {
            range "1..255";
          }
          default 10;
        } //preference

      } //container preference

      container reference-bandwidth {
        description
            "Reference bandwidth that provides a reference for the default costing of 
             interfaces";
        leaf bandwidth-in-kbps {
          type uint32 {
            range "1..4000000000";
          }
        } //bandwidth-in-kbps

        leaf bandwidth-in-kbps-1 {
          type string;
          description
              "Attribute bandwidth-in-kbps for reference-bandwidth";
        } //bandwidth-in-kbps-1

        leaf zbps {
          type uint32 {
            range "1..18";
          }
        } //zbps

        leaf ebps {
          type uint32 {
            range "1..999";
          }
        } //ebps

        leaf pbps {
          type uint32 {
            range "1..999";
          }
        } //pbps

        leaf tbps {
          type string;
          description
              "Attribute Tera-bps for reference-bandwidth";
        } //tbps

        leaf gbps {
          type uint32 {
            range "1..999";
          }
        } //gbps

        leaf mbps {
          type uint32 {
            range "1..999";
          }
        } //mbps

        leaf kbps {
          type uint32 {
            range "1..999";
          }
        } //kbps

      } //container reference-bandwidth

      list rib-priority {
        key "high";
        description
            "Configure RIB priority for OSPF";
        leaf high {
          type boolean;
        } //high

        leaf prefix-list-name {
          type string {
            length "1..32";
          }
        } //prefix-list-name

      } //list rib-priority

      container router-id {
        description
            "Configure router-id for OSPF3";
        leaf ip-address {
          type inet:ip-address;
        } //ip-address

      } //container router-id

      container rtr-adv-lsa-limit {
        description
            "Configure max LSA's we accept from 1 advertising router";
        leaf rtr-adv-lsa-limit-id {
          type uint32 {
            range "1..4294967295";
          }
        } //rtr-adv-lsa-limit-id

        leaf log-only {
          type boolean;
        } //log-only

        leaf threshold {
          type uint32 {
            range "0..100";
          }
        } //threshold

        leaf overload-timeout {
          type boolean;
        } //overload-timeout

        leaf seconds {
          type uint32 {
            range "1..1800";
          }
        } //seconds

        leaf forever {
          type boolean;
        } //forever

      } //container rtr-adv-lsa-limit

      leaf shutdown {
        type boolean;
        description
            "Administratively enable/disable the OSPF3 instance";
      }

      leaf suppress-dn-bit {
        type boolean;
        description
            "Enable/disable whether this instance of OSPF3 will suppress setting the DN bit 
             for OSPF3 LSA packets";
      }

      leaf unicast-import-disable {
        type boolean;
        description
            "Enable/disable submission of routes into the unicast Route Table Manager by 
             OSPF3";
      }

      list area {
        key "area-id";
        description
            "Configure an OSPF3 area";
        leaf area-id {
          type string;
          description
              "<ip-address> | [0..4294967295]";
        } //area-id

        leaf advertise-router-capability {
          type boolean;
          description
              "Enable/disable router advertisement capabilities";
        }

        list area-range {
          key "ipv4-prefix-mask---ipv6-prefix-prefix-length";
          description
              "Create/delete address ranges on an ABR for route summarization or suppression";
          leaf ipv4-prefix-mask---ipv6-prefix-prefix-length {
            type string;
            description
                "Attribute ipv4-prefix/mask | ipv6-prefix/prefix-length for area-range";
          } //ipv4-prefix-mask---ipv6-prefix-prefix-length

          leaf advertise-not-advertise {
            type enumeration {
              enum advertise;
              enum not-advertise;
            }
            description
                "keywords";
          } //advertise-not-advertise

        } //list area-range

        leaf blackhole-aggregate {
          type boolean;
          description
              "Add/Remove low priority blackhole route to avoid loops";
        }

        container export {
          description
              "Configure export policies to determine whether a route is exported as summary 
               type 3/inter-area-prefix-LSA from this Area to another Area";
          leaf-list policy-name {
            type string {
              length "1..32";
            }
            max-elements 5;
          } //policy-name

        } //container export

        container import {
          description
              "Configure import policies to determine whether a route is imported as summary 
               type 3/inter-area-prefix-LSA from another Area into this Area";
          leaf-list policy-name {
            type string {
              length "1..32";
            }
            max-elements 5;
          } //policy-name

        } //container import

        container key-rollover-interval {
          description
              "Configure the key rollover interval";
          leaf key-rollover-interval {
            type uint32 {
              range "10..300";
            }
          } //key-rollover-interval

        } //container key-rollover-interval

        leaf loopfree-alternate-exclude {
          type boolean;
          description
              "Enable/disable IP fast re-route capability for OSPF at area level";
        }

        list interface {
          key "ip-int-name";
          description
              "Configure OSPF3 on an IP interface";
          leaf ip-int-name {
            type string {
              length "1..32";
            }
          } //ip-int-name

          leaf secondary {
            type boolean;
          } //secondary

          leaf advertise-router-capability {
            type boolean;
            description
                "Enable/disable router advertisement capabilities";
          }

          container authentication {
            description
                "Configure OSPFv3 confidentiality authentication";
            leaf inbound {
              type string {
                length "1..32";
              }
            } //inbound

            leaf outbound {
              type string {
                length "1..32";
              }
              description
                  "sa-name";
            } //outbound

            leaf bidirectional {
              type string {
                length "1..32";
              }
              description
                  "sa-name";
            } //bidirectional

          } //container authentication

          container bfd-enable {
            description
                "Enable BFD";
            leaf remain-down-on-failure {
              type boolean;
              description
                  "keyword - Forces adjacency down on BFD failure";
            } //remain-down-on-failure

          } //container bfd-enable

          container dead-interval {
            description
                "Time OSPF3 waits without receiving hello packets before declaring a neighbor 
                 down";
            leaf seconds {
              type uint32 {
                range "2..65535";
              }
            } //seconds

          } //container dead-interval

          container hello-interval {
            description
                "Time interval between OSPF3 hellos issued on the interface";
            leaf seconds {
              type uint32 {
                range "1..65535";
              }
            } //seconds

          } //container hello-interval

          container interface-type {
            description
                "Configure the interface type to be either broadcast or point-to-point";
            leaf interface-type-id {
              type enumeration {
                enum broadcast;
                enum point-to-point;
                enum non-broadcast;
              }
            } //interface-type-id

          } //container interface-type

          container lfa-policy-map {
            description
                "Configure a route-next-hop template";
            leaf route-nh-template {
              type string {
                length "1..32";
              }
            } //route-nh-template

          } //container lfa-policy-map

          leaf loopfree-alternate-exclude {
            type boolean;
            description
                "Enable/disable IP fast re-route capability for OSPF at interface level (only 
                 valid for primary interface)";
          }

          container lsa-filter-out {
            description
                "Configure LSA flooding reduction";
            leaf all-except-own-rtrlsa-except-own-rtrlsa-and-defaults {
              type enumeration {
                enum all;
                enum except-own-rtrlsa;
                enum except-own-rtrlsa-and-defaults;
              }
            } //all-except-own-rtrlsa-except-own-rtrlsa-and-defaults

          } //container lsa-filter-out

          container metric {
            description
                "Configure an explicit route cost metric for the interface";
            leaf metric {
              type uint32 {
                range "1..65535";
              }
            } //metric

          } //container metric

          container mtu {
            description
                "Enter the mtu to be used by OSPF3 for this logical interface";
            leaf bytes {
              type uint32 {
                range "512..9198";
              }
            } //bytes

            leaf bytes-1 {
              type uint32 {
                range "512..9786";
              }
            } //bytes-1

          } //container mtu

          list neighbor {
            key "ipv6-address";
            description
                "Configure neighbor addresses for the interface";
            leaf ipv6-address {
              type inet:ipv6-address;
            } //ipv6-address

          } //list neighbor

          leaf passive {
            type boolean;
            description
                "Add/remove the passive property to/from the interface";
          }

          container poll-interval {
            description
                "Configure the poll-interval for this interface";
            leaf poll-interval-id {
              type uint32;
            } //poll-interval-id

          } //container poll-interval

          container priority {
            description
                "Priority of the interface that is used in the designated router election on 
                 the subnet";
            leaf number {
              type uint16 {
                range "0..255";
              }
            } //number

          } //container priority

          container retransmit-interval {
            description
                "Time OSPF3 will wait before retransmitting an unacknowledged LSA to a neighbor";
            leaf seconds {
              type uint32 {
                range "1..1800";
              }
            } //seconds

          } //container retransmit-interval

          container rib-priority {
            description
                "Configure RIB priority for OSPF3";
            leaf high {
              type boolean;
            } //high

          } //container rib-priority

          leaf shutdown {
            type boolean;
            description
                "Administratively enable/disable OSPF3 on the interface";
          }

          container transit-delay {
            description
                "Time that it takes to transmit an LSA on the interface";
            leaf seconds {
              type uint32 {
                range "1..1800";
              }
            } //seconds

          } //container transit-delay

        } //list interface

        container nssa {
          presence
              "Configure an OSPF3 Not So Stubby Area (NSSA)";
          list area-range {
            key "ipv4-prefix-mask---ipv6-prefix-prefix-length";
            description
                "Create/delete address ranges for route summarization or suppression";
            leaf ipv4-prefix-mask---ipv6-prefix-prefix-length {
              type string;
              description
                  "Attribute ipv4-prefix/mask | ipv6-prefix/prefix-length for area-range";
            } //ipv4-prefix-mask---ipv6-prefix-prefix-length

            leaf advertise-not-advertise {
              type enumeration {
                enum advertise;
                enum not-advertise;
              }
              description
                  "keywords";
            } //advertise-not-advertise

          } //list area-range

          container originate-default-route {
            description
                "Enable/disable generation of default route and its LSA type (ie-pfx or nssa) 
                 into the NSSA";
            leaf type-nssa {
              type boolean;
            } //type-nssa

            leaf adjacency-check {
              type boolean;
            } //adjacency-check

          } //container originate-default-route

          leaf redistribute-external {
            type boolean;
            description
                "Enable/disable redistribution of external routes into the NSSA";
          }

          leaf summaries {
            type boolean;
            description
                "Enable/disable sending summary (type ie-pfx) LSAs into the NSSA";
          }

        } //container nssa

        container stub {
          presence
              "Configure an OSPF3 stub area";
          container default-metric {
            description
                "Metric used by the ABR for the default route into the stub area";
            leaf metric {
              type uint32 {
                range "1..16777215";
              }
              description
                  "1..16777214";
            } //metric

          } //container default-metric

          leaf summaries {
            type boolean;
            description
                "Enable/disable sending summary (type 3) LSAs into the stub area";
          }

        } //container stub

        list virtual-link {
          key "router-id transit-area";
          description
              "Configure an OSPF3 virtual-link";
          leaf router-id {
            type inet:ip-address;
          } //router-id

          leaf transit-area {
            type string;
            description
                "<ip-address> | [0..4294967295]";
          } //transit-area

          container authentication {
            description
                "Configure OPSFv3 confidentiality authentication";
            leaf inbound {
              type string {
                length "1..32";
              }
            } //inbound

            leaf outbound {
              type string {
                length "1..32";
              }
              description
                  "sa-name";
            } //outbound

            leaf bidirectional {
              type string {
                length "1..32";
              }
              description
                  "sa-name";
            } //bidirectional

          } //container authentication

          container dead-interval {
            description
                "Time OSPF3 waits without receiving hello packets before declaring a 
                 virtual-neighbor down";
            leaf seconds {
              type uint32 {
                range "2..65535";
              }
              default 60;
            } //seconds

          } //container dead-interval

          container hello-interval {
            description
                "Time interval between OSPF3 hellos issued on the virtual-link";
            leaf seconds {
              type uint32 {
                range "1..65535";
              }
            } //seconds

          } //container hello-interval

          container retransmit-interval {
            description
                "Time OSPF3 will wait before retransmitting an unacknowledged LSA to a 
                 virtual-neighbor";
            leaf seconds {
              type uint32 {
                range "1..1800";
              }
            } //seconds

          } //container retransmit-interval

          leaf shutdown {
            type boolean;
            description
                "Administratively enable/disable OSPF3 on the virtual-link";
          }

          container transit-delay {
            description
                "Time that it takes to transmit an LSA on the virtual-link";
            leaf seconds {
              type uint32 {
                range "0..1800";
              }
              default 1;
              description
                  "[1..1800]";
            } //seconds

          } //container transit-delay

        } //list virtual-link

      } //list area

      container graceful-restart {
        presence
            "Enable/disable graceful-restart for OSPF3";
        leaf helper-disable {
          type boolean;
          description
              "Enable/disable graceful restart helper mode for OSPF3";
        }

        leaf strict-lsa-checking {
          type boolean;
          description
              "Enable/disable strict LSA checking during OSPF3 graceful restart";
        }

      } //container graceful-restart

      container loopfree-alternates {
        presence
            "Enable/disable loopfree-alternate for OSPF3";
        container exclude {
          description
              "Configure LFA exclude policies";
          container prefix-policy {
            description
                "Configure LFA exclude prefix policies";
            leaf-list prefix-policy {
              type string {
                length "1..32";
              }
              max-elements 5;
            } //prefix-policy

          } //container prefix-policy

        } //container exclude

      } //container loopfree-alternates

      container timers {
        description
            "Configure OSPF3 timers";
        container incremental-spf-wait {
          description
              "Configure the delay before an incremental SPF calculation is started";
          leaf incremental-spf-wait {
            type uint32 {
              range "0..1000";
            }
            description
                "[0..1000] in milliseconds";
          } //incremental-spf-wait

        } //container incremental-spf-wait

        container lsa-accumulate {
          description
              "Configure the delay to accumulate multiple LSAs before advertising them to 
               neighbors";
          leaf lsa-accumulate {
            type uint32 {
              range "0..1000";
            }
            description
                "[0..1000] in milliseconds";
          } //lsa-accumulate

        } //container lsa-accumulate

        container lsa-arrival {
          description
              "Configure the minimum delay that must pass between receipt of the same LSAs 
               arriving from neighbors";
          leaf lsa-arrival-time {
            type uint32 {
              range "0..600000";
            }
            description
                "[0..600000] in milliseconds";
          } //lsa-arrival-time

        } //container lsa-arrival

        container lsa-generate {
          description
              "Configure the throttling of OSPF3 LSA-generation";
          leaf max-lsa-wait {
            type uint32 {
              range "10..600000";
            }
            description
                "[10..600000] in milliseconds";
          } //max-lsa-wait

          leaf lsa-generate-id {
            type uint32 {
              range "10..600000";
            }
            status "obsolete";
          } //lsa-generate-id

          leaf lsa-generate-id-2 {
            type uint32 {
              range "10..600000";
            }
            status "obsolete";
          } //lsa-generate-id-2

          leaf lsa-initial-wait {
            type uint32 {
              range "10..600000";
            }
            description
                "[10..600000] in milliseconds";
          } //lsa-initial-wait

          leaf lsa-second-wait {
            type uint32 {
              range "10..600000";
            }
            description
                "[10..600000] in milliseconds";
          } //lsa-second-wait

        } //container lsa-generate

        container redistribute-delay {
          description
              "Configure the hold down timer for external routes being redistributed in OSPF";
          leaf redistribute-delay {
            type uint32 {
              range "0..1000";
            }
            description
                "[0..1000] in milliseconds";
          } //redistribute-delay

        } //container redistribute-delay

        container spf-wait {
          description
              "Configure the maximum interval between two consecutive SPF calculations";
          leaf max-spf-wait {
            type uint32 {
              range "10..120000";
            }
            description
                "[10..120000] in milliseconds";
          } //max-spf-wait

          leaf spf-wait-id {
            type uint32 {
              range "10..100000";
            }
            status "obsolete";
          } //spf-wait-id

          leaf spf-wait-id-2 {
            type uint32 {
              range "10..100000";
            }
            status "obsolete";
          } //spf-wait-id-2

          leaf spf-initial-wait {
            type uint32 {
              range "10..100000";
            }
            description
                "[10..100000] in milliseconds";
          } //spf-initial-wait

          leaf spf-second-wait {
            type uint32 {
              range "10..100000";
            }
            description
                "[10..100000] in milliseconds";
          } //spf-second-wait

        } //container spf-wait

      } //container timers

    } //list ospf3

  } //grouping alu-conf-svc-vprn-ospf3-r13

} //module  alu-conf-svc-vprn-ospf3-r13
