module alu-conf-svc-vprn-srcad-r13 {
  yang-version "1";

  namespace "urn:alcatel-lucent.com:sros:ns:yang:conf-svc-vprn-srcad-r13";

  prefix "conf-svc-vprn-srcad-r13";

  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure source addresses within a VPRN for 
       various applications on SR OS based routers. 
       
       Copyright 2014-2015 Alcatel-Lucent, 2016 Nokia. All rights reserved. 
       Reproduction of this document is authorized on the condition that the 
       foregoing copyright notice is included. 
       
       This alu-conf-svc-vprn-srcad-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-svc-vprn-srcad-r13 {
    container source-address {
      description
          "Configure source addresses within a VPRN for various applications";
      list application {
        key "app";
        description
            "Configure application to use source address";
        leaf app {
          type enumeration {
            enum cflowd;
            enum dns;
            enum ftp;
            enum ntp;
            enum ping;
            enum ptp;
            enum radius;
            enum snmptrap;
            enum sntp;
            enum ssh;
            enum syslog;
            enum tacplus;
            enum telnet;
            enum traceroute;
            enum mcreporter;
            enum icmp-error;
          }
        } //app

        leaf ip-int-name-ip-address {
          type string;
          description
              "Attribute ip-int-name|ip-address for application";
        } //ip-int-name-ip-address

      } //list application

      list application6 {
        key "app";
        description
            "Configure application to use source IPv6 address";
        leaf app {
          type enumeration {
            enum cflowd;
            enum dns;
            enum ftp;
            enum ntp;
            enum ping;
            enum ptp;
            enum radius;
            enum snmptrap;
            enum sntp;
            enum ssh;
            enum syslog;
            enum tacplus;
            enum telnet;
            enum traceroute;
            enum mcreporter;
            enum icmp6-error;
          }
        } //app

        leaf ipv6-address {
          type inet:ipv6-address;
          description
              "x:x:x:x:x:x:x:x (eight 16-bit pieces)";
        } //ipv6-address

      } //list application6

    } //container source-address

  } //grouping alu-conf-svc-vprn-srcad-r13

} //module  alu-conf-svc-vprn-srcad-r13
