module alu-conf-svc-vpls-stp-r13 {
  yang-version "1";

  namespace "urn:alcatel-lucent.com:sros:ns:yang:conf-svc-vpls-stp-r13";

  prefix "conf-svc-vpls-stp-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure STP parameters on SR OS based 
       routers. 
       
       Copyright 2014-2015 Alcatel-Lucent, 2016 Nokia. All rights reserved. 
       Reproduction of this document is authorized on the condition that the 
       foregoing copyright notice is included. 
       
       This alu-conf-svc-vpls-stp-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-svc-vpls-stp-r13 {
    container stp {
      description
          "Configure STP parameters";
      list forward-delay {
        key "forward-delay";
        description
            "Configure forward-delay";
        leaf forward-delay {
          type uint32 {
            range "4..30";
          }
        } //forward-delay

      } //list forward-delay

      list hello-time {
        key "hello-time";
        description
            "Configure hello-time";
        leaf hello-time {
          type uint32 {
            range "1..10";
          }
        } //hello-time

      } //list hello-time

      container hold-count {
        description
            "Configure BPDU txmit hold count";
        leaf BPDU-tx-hold-count {
          type uint32 {
            range "1..20";
          }
        } //BPDU-tx-hold-count

      } //container hold-count

      list max-age {
        key "max-age";
        description
            "Configure maximum info age for the stp";
        leaf max-age {
          type uint32 {
            range "6..40";
          }
        } //max-age

      } //list max-age

      container mode {
        description
            "Configure protocol version";
        leaf rstp-comp-dot1w-dot1w-mstp-pmstp {
          type enumeration {
            enum rstp;
            enum comp-dot1w;
            enum dot1w;
            enum mstp;
            enum pmstp;
          }
          description
              "protocol version";
        } //rstp-comp-dot1w-dot1w-mstp-pmstp

      } //container mode

      container mst-max-hops {
        description
            "Configure the max number of hops in a MSTP region";
        leaf hops-count {
          type int32 {
            range "1..40";
          }
        } //hops-count

      } //container mst-max-hops

      container mst-name {
        description
            "Configure the MST region name";
        leaf region-name {
          type string {
            length "1..32";
          }
        } //region-name

      } //container mst-name

      container mst-revision {
        description
            "Configure MST configuration revision";
        leaf revision-number {
          type int32 {
            range "0..65535";
          }
        } //revision-number

      } //container mst-revision

      list priority {
        key "bridge-priority";
        description
            "Configure bridge priority for the stp";
        leaf bridge-priority {
          type uint32 {
            range "0..65535";
          }
        } //bridge-priority

      } //list priority

      leaf shutdown {
        type boolean;
        description
            "Enable/disable spanning tree protocol";
      }

      list mst-instance {
        key "mst-inst-number";
        description
            "Provision a Multiple Spanning Tree instance";
        leaf mst-inst-number {
          type int32 {
            range "1..4094";
          }
        } //mst-inst-number

        container mst-priority {
          description
              "Configure the MST instance bridge priority";
          leaf bridge-priority {
            type int32 {
              range "0..65535";
            }
          } //bridge-priority

        } //container mst-priority

        list vlan-range {
          key "vlan-range";
          description
              "Configure range of VLANs managed by this MSTI";
          leaf vlan-range {
            type string {
              length "1..64";
            }
            description
                "[1..4094] - [1..4094]";
          } //vlan-range

        } //list vlan-range

      } //list mst-instance

    } //container stp

  } //grouping alu-conf-svc-vpls-stp-r13

} //module  alu-conf-svc-vpls-stp-r13
