module alu-conf-port-cellular-r13 {
  yang-version "1";

  namespace "urn:alcatel-lucent.com:sros:ns:yang:conf-port-cellular-r13";

  prefix "conf-port-cellular-r13";

  import alu-conf-port-cell-sim-r13 {
    prefix "conf-port-cell-sim-r13";
  }
  import alu-types {
    prefix "alu";
  }

  alu:alu-major-release "rel19";

  organization "Alcatel-Lucent";

  contact
      "Alcatel-Lucent SR OS Support 
       Web: <http://www.alcatel-lucent.com>";

  description
      "Alcatel-Lucent YANG Data model to configure cellular parameters for a port on 
       SR OS based routers. 
       
       Copyright 2014-2015 Alcatel-Lucent, 2016 Nokia. All rights reserved. 
       Reproduction of this document is authorized on the condition that the 
       foregoing copyright notice is included. 
       
       This alu-conf-port-cellular-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-port-cellular-r13 {
    container cellular {
      description
          "Configure cellular parameters for a port";
      container b125-power-level {
        description
            "Configure the maximum power level for the band 125 radio";
        leaf power-level {
          type uint32 {
            range "1..20";
          }
          default 1;
          description
              "[1..20] - default 1";
        } //power-level

      } //container b125-power-level

      container pdn {
        description
            "Configure Packet Data Networks on a cellular port";
        container pdn-profile {
          description
              "Configure the pdn-profile for this pdn";
          leaf pdn-profile-number {
            type uint32 {
              range "1..2";
            }
          } //pdn-profile-number

        } //container pdn-profile

      } //container pdn

      uses "conf-port-cell-sim-r13:alu-conf-port-cell-sim-r13";
    } //container cellular

  } //grouping alu-conf-port-cellular-r13

} //module  alu-conf-port-cellular-r13
