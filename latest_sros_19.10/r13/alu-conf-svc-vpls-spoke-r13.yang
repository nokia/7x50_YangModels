module alu-conf-svc-vpls-spoke-r13 {
  yang-version "1";

  namespace "urn:alcatel-lucent.com:sros:ns:yang:conf-svc-vpls-spoke-r13";

  prefix "conf-svc-vpls-spoke-r13";

  import alu-conf-svc-vpls-spb-r13 {
    prefix "conf-svc-vpls-spb-r13";
  }
  import alu-types {
    prefix "alu";
  }
  import ietf-inet-types {
    prefix "inet";
  }
  import ietf-yang-types {
    prefix "yang";
  }

  alu:alu-major-release "rel19";

  organization "Alcatel-Lucent";

  contact
      "Alcatel-Lucent SR OS Support 
       Web: <http://www.alcatel-lucent.com>";

  description
      "Alcatel-Lucent YANG Data model to provision spoke SDP bindings for VPLS 
       services on SR OS based routers. 
       
       Copyright 2014-2015 Alcatel-Lucent, 2016 Nokia. All rights reserved. 
       Reproduction of this document is authorized on the condition that the 
       foregoing copyright notice is included. 
       
       This alu-conf-svc-vpls-spoke-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-04-17";

  grouping alu-conf-svc-vpls-spoke-r13 {
    list spoke-sdp {
      key "sdp-id-vc-id";
      description
          "Provision spoke SDP bindings for VPLS services";
      leaf sdp-id-vc-id {
        type string;
        description
            "sdp-id - [1..32767] 
             vc-id - [1..4294967295]";
      } //sdp-id-vc-id

      leaf vc-type {
        type enumeration {
          enum ether;
          enum vlan;
        }
        description
            "keywords";
      } //vc-type

      leaf split-horizon-group {
        type string {
          length "1..32";
        }
      } //split-horizon-group

      leaf endpoint {
        type string {
          length "1..32";
        }
      } //endpoint

      leaf no-endpoint {
        type boolean;
      } //no-endpoint

      leaf root-leaf-tag {
        type boolean;
      } //root-leaf-tag

      leaf leaf-ac {
        type boolean;
      } //leaf-ac

      leaf multicast-source {
        type boolean;
      } //multicast-source

      container accounting-policy {
        description
            "Configure accounting-policy to be used";
        leaf acct-policy-id {
          type uint64 {
            range "1..99";
          }
        } //acct-policy-id

      } //container accounting-policy

      container app-profile {
        description
            "Configure the application profile name";
        leaf app-profile-name {
          type string {
            length "1..32";
          }
        } //app-profile-name

      } //container app-profile

      leaf auto-learn-mac-protect {
        type boolean;
        description
            "Enable/disable automatic update of MAC protect list";
      }

      leaf bfd-enable {
        type boolean;
        description
            "Enable/disable BFD";
      }

      container bfd-template {
        description
            "Configure BFD template";
        leaf bfd-template-string {
          type string {
          }
        } //bfd-template-string

      } //container bfd-template

      leaf block-on-mesh-failure {
        type boolean;
        description
            "Block traffic on mesh-SDP failure";
      }

      container bpdu-translation {
        description
            "Configure the bpdu translation on this spoke SDP";
        leaf bpdu-translation-id {
          type enumeration {
            enum auto;
            enum auto-rw;
            enum pvst;
            enum pvst-rw;
            enum stp;
          }
        } //bpdu-translation-id

      } //container bpdu-translation

      leaf collect-stats {
        type boolean;
        description
            "Enable/disable statistics collection";
      }

      leaf control-word {
        type boolean;
        description
            "Enable/disable setting the CW bit in the label message";
      }

      container cpu-protection {
        description
            "Configure CPU protection";
        leaf policy-id {
          type uint32 {
            range "1..255";
          }
        } //policy-id

        leaf mac-monitoring {
          type boolean;
          description
              "keyword - enable MAC monitoring";
        } //mac-monitoring

        leaf eth-cfm-monitoring {
          type boolean;
          description
              "keyword - enable Ethernet Connectivity Fault Management monitoring";
        } //eth-cfm-monitoring

        leaf aggregate {
          type boolean;
          description
              "keyword - apply the rate limit to the sum of the per peer packet rates";
        } //aggregate

        leaf car {
          type boolean;
          description
              "keyword - Committed Access Rate - ignore Eth-CFM packets when enforcing 
               overall-rate";
        } //car

      } //container cpu-protection

      container description {
        description
            "Set description for spoke-sdp";
        leaf description-string {
          type string {
            length "1..80";
          }
          description
              "80 char max";
        } //description-string

      } //container description

      leaf disable-aging {
        type boolean;
        description
            "Enable/disable aging of MAC addresses";
      }

      leaf disable-learning {
        type boolean;
        description
            "Enable/disable learning of new MAC addresses";
      }

      leaf disable-send-bvpls-evpn-flush {
        type boolean;
        description
            "Enable/disable sending of B-VPLS EVPN flush";
      }

      leaf discard-unknown-source {
        type boolean;
        description
            "Enable/disable discarding of frames with unknown source MAC address";
      }

      leaf entropy-label {
        type boolean;
        description
            "Enable/disable use of entropy-label";
      }

      list fault-propagation-bmac {
        key "mac-name-ieee-address";
        description
            "Configure a backbone MAC address or backbone MAC name for fault propagation";
        leaf mac-name-ieee-address {
          type string {
            length "1..32";
          }
          description
              "32 char max";
        } //mac-name-ieee-address

      } //list fault-propagation-bmac

      container force-qinq-vc-forwarding {
        description
            "Forces qinq-vc-type forwarding in the data-path";
        leaf c-tag-c-tag---s-tag-c-tag {
          type enumeration {
            enum c-tag-c-tag;
            enum s-tag-c-tag;
          }
          description
              "c-tag-c-tag | s-tag-c-tag";
        } //c-tag-c-tag---s-tag-c-tag

      } //container force-qinq-vc-forwarding

      leaf force-vlan-vc-forwarding {
        type boolean;
        description
            "Forces vlan-vc-type forwarding in the data-path";
      }

      container hash-label {
        description
            "Enable/disable use of hash-label";
        leaf signal-capability {
          type boolean;
        } //signal-capability

      } //container hash-label

      leaf ignore-standby-signaling {
        type boolean;
        description
            "Ignore 'standby-bit' received from LDP peer";
      }

      container l2pt-termination {
        description
            "Configure L2PT termination on this spoke SDP";
        leaf cdp {
          type boolean;
          description
              "keyword - cisco discovery protocol";
        } //cdp

        leaf dtp {
          type boolean;
          description
              "keyword - dynamic trunking protocol";
        } //dtp

        leaf pagp {
          type boolean;
          description
              "keyword - port aggregation protocol";
        } //pagp

        leaf stp {
          type boolean;
          description
              "keyword - all spanning tree protocols: stp, rstp, mstp, pvst (default)";
        } //stp

        leaf udld {
          type boolean;
          description
              "keyword - unidirectional link detection";
        } //udld

        leaf vtp {
          type boolean;
          description
              "keyword - virtual trunk protocol";
        } //vtp

      } //container l2pt-termination

      container limit-mac-move {
        description
            "Configure mac move";
        leaf blockable-non-blockable {
          type enumeration {
            enum blockable;
            enum non-blockable;
          }
        } //blockable-non-blockable

      } //container limit-mac-move

      leaf mac-pinning {
        type boolean;
        description
            "Enable/disable MAC address pinning on this spoke SDP";
      }

      container max-nbr-mac-addr {
        description
            "Configure the maximum number of MAC entries in the FDB from this SDP";
        leaf table-size {
          type string;
          description
              "Attribute table-size for max-nbr-mac-addr";
        } //table-size

      } //container max-nbr-mac-addr

      container monitor-oper-group {
        description
            "Configure an Operational-Group to monitor";
        leaf group-name {
          type string {
            length "1..32";
          }
        } //group-name

      } //container monitor-oper-group

      container oper-group {
        description
            "Configure operational-group";
        leaf oper-name {
          type string {
            length "1..32";
          }
        } //oper-name

      } //container oper-group

      container precedence {
        description
            "Configure the spoke-sdp precedence";
        leaf precedence-value {
          type uint32 {
            range "1..4";
          }
          description
              "[1..4] - default is 4";
        } //precedence-value

        leaf primary {
          type boolean;
          description
              "keyword - used to make this the primary spoke-sdp";
        } //primary

      } //container precedence

      leaf pw-status-signaling {
        type boolean;
        description
            "Enable/disable PW Status Signaling for spoke SDP binding";
      }

      container restrict-protected-src {
        description
            "Enable/disable protected src MAC restriction";
        leaf discard-frame {
          type boolean;
          description
              "keyword - discard frame and trap on a protected MAC";
        } //discard-frame

        leaf alarm-only {
          type boolean;
          description
              "keyword: trap on a protected MAC";
        } //alarm-only

      } //container restrict-protected-src

      leaf shutdown {
        type boolean;
        description
            "Administratively enable/disable the spoke SDP binding";
      }

      list static-mac {
        key "ieee-address";
        description
            "Configure a static mac entry";
        leaf ieee-address {
          type string;
          description
              "xx:xx:xx:xx:xx:xx or xx-xx-xx-xx-xx-xx (cannot be all zeros)";
        } //ieee-address

      } //list static-mac

      container transit-policy {
        description
            "Configure transit policy id";
        leaf prefix {
          type uint32 {
            range "1..65535";
          }
        } //prefix

      } //container transit-policy

      list vlan-vc-tag {
        key "vlan-id";
        description
            "Configure VLAN VC tag";
        leaf vlan-id {
          type uint32 {
            range "0..4094";
          }
        } //vlan-id

      } //list vlan-vc-tag

      container control-channel-status {
        description
            "Configure control channel status information";
        leaf acknowledgment {
          type boolean;
          description
              "Enable/disable acknowledgment";
        }

        container refresh-timer {
          description
              "Configure refresh timer";
          leaf seconds {
            type uint32 {
              range "10..65535";
            }
          } //seconds

        } //container refresh-timer

        container request-timer {
          description
              "Configure request-timer for the control channel status";
          leaf request-timer-secs {
            type uint32 {
              range "10..65535";
            }
          } //request-timer-secs

          leaf retry-timer {
            type uint32 {
              range "3..60";
            }
          } //retry-timer

          leaf timeout-multiplier {
            type uint32 {
              range "3..15";
            }
          } //timeout-multiplier

        } //container request-timer

        leaf shutdown {
          type boolean;
          description
              "Administratively enable/disable the control channel status";
        }

      } //container control-channel-status

      container dhcp {
        description
            "Configure DHCP parameters";
        container description {
          description
              "Description for running DHCP";
          leaf description-string {
            type string {
              length "1..80";
            }
          } //description-string

        } //container description

        leaf snoop {
          type boolean;
          description
              "Enable/disable DHCP snooping";
        }

      } //container dhcp

      container egress {
        description
            "Spoke SDP binding egress configuration";
        container filter {
          description
              "Apply egress filter";
          leaf ip {
            type string;
            description
                "[1..65535]|<name:64 char max>";
          } //ip

          leaf mac {
            type string;
            description
                "[1..65535]|<name:64 char max>";
          } //mac

          leaf ipv6 {
            type string;
            description
                "[1..65535]|<name:64 char max>";
          } //ipv6

        } //container filter

        list qos {
          key "network-policy-id";
          description
              "Configure egress qos";
          leaf network-policy-id {
            type uint32 {
              range "1..65535";
            }
          } //network-policy-id

          leaf port-redirect-group {
            type string {
              length "1..32";
            }
          } //port-redirect-group

          leaf instance {
            type uint16 {
              range "1..65535";
            }
          } //instance

        } //list qos

        list vc-label {
          key "egress-vc-label";
          description
              "Configure egress VC label";
          leaf egress-vc-label {
            type int32 {
              range "16..1048575";
            }
          } //egress-vc-label

        } //list vc-label

        container mfib-allowed-mda-destinations {
          description
              "Configure MFIB allowed MDA destinations";
          list mda {
            key "mda-id";
            description
                "Add/remove MDA";
            leaf mda-id {
              type string {
                length "1..4";
              }
              description
                  "Attribute mda-id for mda";
            } //mda-id

          } //list mda

        } //container mfib-allowed-mda-destinations

      } //container egress

      container eth-cfm {
        description
            "Configure CFM parameters";
        leaf collect-lmm-stats {
          type boolean;
          description
              "Enable/Disable the collection of statistics for OAM-PM Loss Measurement 
               Message (LMM) tests";
        }

        list mip {
          key "primary-vlan-enable";
          description
              "Enable/Disable Maintenance Intermediate Points";
          leaf mac {
            type yang:mac-address;
          } //mac

          leaf default-mac {
            type boolean;
            description
                "keyword - Use the default MAC address for the MIP";
          } //default-mac

          leaf primary-vlan-enable {
            type uint32 {
              range "1..4094";
            }
          } //primary-vlan-enable

        } //list mip

        container squelch-ingress-levels {
          description
              "Configure the level(s) of the ETH-CFM PDUs that will be silently discarded";
          leaf t0 {
            type boolean;
            description
                "[0..7]";
          } //t0

          leaf t1 {
            type boolean;
          } //t1

          leaf t2 {
            type boolean;
          } //t2

          leaf t3 {
            type boolean;
          } //t3

          leaf t4 {
            type boolean;
          } //t4

          leaf t5 {
            type boolean;
          } //t5

          leaf t6 {
            type boolean;
          } //t6

          leaf t7 {
            type boolean;
          } //t7

        } //container squelch-ingress-levels

        leaf vmep-filter {
          type boolean;
          description
              "Suppress eth-cfm PDUs based on level lower than or equal to configured Virtual 
               MEP";
        }

        container collect-lmm-fc-stats {
          description
              "Configure the collection of Forwarding Class (FC) aware statistics for OAM-PM 
               Loss Measurement Message (LMM) tests";
          container fc {
            description
                "Configure Forwarding Class (FC) counters without regard for profile";
            leaf-list fc-name {
              type enumeration {
                enum be;
                enum l2;
                enum af;
                enum l1;
                enum h2;
                enum ef;
                enum h1;
                enum nc;
              }
              max-elements 8;
            } //fc-name

          } //container fc

          container fc-in-profile {
            description
                "Configure only in profile Forwarding Class (FC) counters";
            leaf-list fc-name {
              type enumeration {
                enum be;
                enum l2;
                enum af;
                enum l1;
                enum h2;
                enum ef;
                enum h1;
                enum nc;
              }
              max-elements 8;
            } //fc-name

          } //container fc-in-profile

        } //container collect-lmm-fc-stats

        list mep {
          key "mep-id domain association";
          description
              "Configure a CFM Maintenance Endpoint";
          leaf mep-id {
            type int16 {
              range "1..8191";
            }
            description
                "Attribute mep-id for mep";
          } //mep-id

          leaf domain {
            type uint32 {
              range "1..4294967295";
            }
          } //domain

          leaf association {
            type uint32 {
              range "1..4294967295";
            }
          } //association

          leaf direction {
            type enumeration {
              enum up;
              enum down;
            }
            description
                "keywords";
          } //direction

          leaf primary-vlan-enable {
            type boolean;
            description
                "keyword - Provision MEP using MA primary vlan-id";
          } //primary-vlan-enable

          leaf ccm-enable {
            type boolean;
            description
                "Enable/Disable Generation of CCM messages";
          }

          container ccm-ltm-priority {
            description
                "Configure the priority of CCM and LTM messages";
            leaf priority {
              type uint16 {
                range "0..7";
              }
              description
                  "[0..7] - Default highest priority on bridge-port";
            } //priority

          } //container ccm-ltm-priority

          container ccm-padding-size {
            description
                "Insert additional padding in the CCM packets";
            leaf ccm-padding {
              type uint32 {
                range "3..1500";
              }
              description
                  "3..1500 octets";
            } //ccm-padding

          } //container ccm-padding-size

          container description {
            description
                "Add/remove a text description for the MEP";
            leaf description-string {
              type string {
              }
              description
                  "[80 chars max]";
            } //description-string

          } //container description

          container fault-propagation-enable {
            description
                "Configure the Fault Propagation for the MEP";
            leaf use-if-tlv-suspend-ccm {
              type enumeration {
                enum use-if-tlv;
                enum suspend-ccm;
              }
              description
                  "keywords - use interface TLV, or suspend Continuity Check Messages";
            } //use-if-tlv-suspend-ccm

          } //container fault-propagation-enable

          leaf install-mep {
            type boolean;
            description
                "Enable/Disable Installation of the MEP in the forwarding plane";
          }

          leaf lbm-svc-act-responder {
            type boolean;
            description
                "Enable/Disable processing of service activation streams that may be 
                 encapsulated in the ETH-CFM request Loopback Message (LBM) on the MEP";
          }

          container low-priority-defect {
            description
                "Configure the Lowest Priority Defect for the MEP";
            leaf allDef-macRemErrXcon-remErrXcon-errXcon-xcon-noXcon {
              type enumeration {
                enum allDef;
                enum macRemErrXcon;
                enum remErrXcon;
                enum errXcon;
                enum xcon;
                enum noXcon;
              }
              description
                  "keywords";
            } //allDef-macRemErrXcon-remErrXcon-errXcon-xcon-noXcon

          } //container low-priority-defect

          container mac-address {
            description
                "Configure the MAC Address for the MEP";
            leaf mac-address {
              type yang:mac-address;
            } //mac-address

          } //container mac-address

          container one-way-delay-threshold {
            description
                "Configure the one-way-delay test threshold";
            leaf seconds {
              type uint32 {
                range "0..600";
              }
              default 3;
              description
                  "[0..600] Default: 3";
            } //seconds

          } //container one-way-delay-threshold

          leaf shutdown {
            type boolean;
            description
                "Administratively enable/disable the MEP";
          }

          container ais-enable {
            presence
                "Configure the generation and reception of Alarm Indication Signal (AIS) 
                 message parameters";
            container client-meg-level {
              description
                  "Configure the client meg level";
              leaf t1 {
                type boolean;
                description
                    "[1..7]";
              } //t1

              leaf t2 {
                type boolean;
              } //t2

              leaf t3 {
                type boolean;
              } //t3

              leaf t4 {
                type boolean;
              } //t4

              leaf t5 {
                type boolean;
              } //t5

              leaf t6 {
                type boolean;
              } //t6

              leaf t7 {
                type boolean;
              } //t7

            } //container client-meg-level

            leaf interface-support-enable {
              type boolean;
              description
                  "Enable/disable the generation of AIS PDUs based on the associated endpoint 
                   state";
            }

            container interval {
              description
                  "Configure the transmission interval of AIS messages";
              leaf t1-60 {
                type enumeration {
                  enum 1;
                  enum 60;
                }
                default 1;
                description
                    "seconds - Default: 1";
              } //t1-60

            } //container interval

            container low-priority-defect {
              description
                  "Configure the Lowest Priority Defect for the MEP AIS generation";
              leaf allDef---macRemErrXcon {
                type enumeration {
                  enum allDef;
                  enum macRemErrXcon;
                }
                description
                    "keywords";
              } //allDef---macRemErrXcon

            } //container low-priority-defect

            container priority {
              description
                  "Configure the priority of AIS messages originated by the node";
              leaf priority-value {
                type uint32 {
                  range "0..7";
                }
                default 7;
                description
                    "[0..7] - Default: 7";
              } //priority-value

            } //container priority

          } //container ais-enable

          container alarm-notification {
            description
                "Configure the MEP alarm notification parameters";
            container fng-alarm-time {
              description
                  "Configure the Fault Notification Generation (FNG) alarm time";
              leaf time {
                type enumeration {
                  enum 0;
                  enum 250;
                  enum 500;
                  enum 1000;
                }
                default 0;
                description
                    "[0,250,500,1000] centi-seconds - Default: 0";
              } //time

            } //container fng-alarm-time

            container fng-reset-time {
              description
                  "Configure the Fault Notification Generation (FNG) reset time";
              leaf time {
                type enumeration {
                  enum 0;
                  enum 250;
                  enum 500;
                  enum 1000;
                }
                default 0;
                description
                    "[0,250,500,1000] centi-seconds - Default: 0";
              } //time

            } //container fng-reset-time

          } //container alarm-notification

          container csf-enable {
            presence
                "Configure the reception of Client Signal Fail (CSF) message parameters";
            container multiplier {
              description
                  "Configure the multiplier used for timing out CSF";
              leaf multiplier-value {
                type string;
                description
                    "[0.0|2.0 .. 30.0] - Default: 3.5";
              } //multiplier-value

            } //container multiplier

          } //container csf-enable

          container eth-test-enable {
            presence
                "Enable/Disable eth-test functionality on MEP";
            container bit-error-threshold {
              description
                  "Configure the bit error trap threshold";
              leaf bit-errors {
                type uint32 {
                  range "0..11840";
                }
                default 1;
                description
                    "[0..11840] Default: 1";
              } //bit-errors

            } //container bit-error-threshold

            container test-pattern {
              description
                  "Configure the test pattern for eth-test frames";
              leaf all-zeros-all-ones {
                type enumeration {
                  enum all-zeros;
                  enum all-ones;
                }
                default "all-zeros";
                description
                    "keywords - Test pattern - default: all-zeros";
              } //all-zeros-all-ones

              leaf crc-enable {
                type boolean;
                description
                    "keyword - Generate CRC checksum";
              } //crc-enable

            } //container test-pattern

          } //container eth-test-enable

          container grace {
            description
                "Configure the generation and reception of grace period parameters";
            container eth-ed {
              description
                  "Configure the generation and reception of eth-ed grace period parameters";
              container max-rx-defect-window {
                description
                    "Configure/Disable an upper maximum defect window length; when disabled the 
                     advertised value from the peer will be used; when enabled the lower of the 
                     configured value or the advertised value from the peer will be used";
                leaf seconds {
                  type uint32 {
                    range "1..86400";
                  }
                  description
                      "[1..86400] - Default: no max-rx-defect-window";
                } //seconds

              } //container max-rx-defect-window

              container priority {
                description
                    "Configure/Disable the transmission priority value for ETH-ED PDUs; when 
                     disabled the priority value of ccm-ltm-priority associated with this MEP will 
                     be used";
                leaf priority {
                  type int32 {
                    range "0..7";
                  }
                  default 0;
                  description
                      "[0..7] - Default: no priority";
                } //priority

              } //container priority

              leaf rx-eth-ed {
                type boolean;
                description
                    "Enable/Disable the receiving and processing of ETH-ED PDUs";
              }

              leaf tx-eth-ed {
                type boolean;
                description
                    "Enable/Disable the transmission of ETH-ED PDUs";
              }

            } //container eth-ed

            container eth-vsm-grace {
              description
                  "Configure the generation and reception of sros vendor specific message (vsm) 
                   grace period parameters";
              leaf rx-eth-vsm-grace {
                type boolean;
                description
                    "Enable/Disable the receiving and processing of vendor specific message (vsm) 
                     grace period notifications";
              }

              leaf tx-eth-vsm-grace {
                type boolean;
                description
                    "Enable/Disable the transmission of vsm grace period notifications";
              }

            } //container eth-vsm-grace

          } //container grace

        } //list mep

      } //container eth-cfm

      container igmp-snooping {
        description
            "Configure IGMP snooping parameters";
        leaf disable-router-alert-check {
          type boolean;
          description
              "Enable/disable the IGMP router alert check option";
        }

        leaf fast-leave {
          type boolean;
          description
              "Enable/disable IGMP fast-leave processing";
        }

        container import {
          description
              "Import a policy to filter IGMP packets";
          leaf policy-name {
            type string {
              length "1..32";
            }
          } //policy-name

        } //container import

        container last-member-query-interval {
          description
              "Configure the IGMP Last Member Query Interval";
          leaf t1-10-seconds {
            type uint32 {
              range "1..50";
            }
          } //t1-10-seconds

        } //container last-member-query-interval

        container max-num-groups {
          description
              "Configure the max number of multicast groups allowed";
          leaf max-num-groups-id {
            type uint32 {
              range "1..16000";
            }
          } //max-num-groups-id

        } //container max-num-groups

        container max-num-grp-sources {
          description
              "Configure the max number of multicast group sources allowed per group";
          leaf max-num-grp-sources-id {
            type uint16 {
              range "1..32000";
            }
          } //max-num-grp-sources-id

        } //container max-num-grp-sources

        container max-num-sources {
          description
              "Configure the max number of multicast sources allowed per group";
          leaf max-num-sources-id {
            type uint32 {
              range "1..1000";
            }
          } //max-num-sources-id

        } //container max-num-sources

        leaf mrouter-port {
          type boolean;
          description
              "Configure the spoke SDP as a multicast router port";
        }

        container query-interval {
          description
              "Configure the IGMP Query Interval";
          leaf seconds {
            type uint32 {
              range "2..1024";
            }
          } //seconds

        } //container query-interval

        container query-response-interval {
          description
              "Configure the IGMP Query Response Interval";
          leaf seconds {
            type uint32 {
              range "1..1023";
            }
          } //seconds

        } //container query-response-interval

        container robust-count {
          description
              "Configure the IGMP Robustness Variable";
          leaf robust-count {
            type uint32 {
              range "2..7";
            }
          } //robust-count

        } //container robust-count

        leaf send-queries {
          type boolean;
          description
              "Enable/disable generation of IGMP General Queries";
        }

        container version {
          description
              "Configure the version of IGMP";
          leaf version {
            type uint32 {
              range "1..3";
            }
            description
                "[1, 2 or 3]";
          } //version

        } //container version

        container mcac {
          description
              "Configure multicast CAC policy and constraints for this SDP";
          container if-policy {
            description
                "Configure multicast CAC if-policy";
            leaf if-policy-name {
              type string {
                length "1..32";
              }
            } //if-policy-name

          } //container if-policy

          container policy {
            description
                "Enable/disable multicast CAC policy";
            leaf policy-name {
              type string {
                length "1..32";
              }
              description
                  "max 32 chars";
            } //policy-name

          } //container policy

          container unconstrained-bw {
            description
                "Set/reset unconstrained-bw for multicast CAC policy on this SDP";
            leaf bandwidth {
              type int32 {
                range "0..2147483647";
              }
            } //bandwidth

            leaf mandatory-bw {
              type int32 {
                range "0..2147483647";
              }
            } //mandatory-bw

          } //container unconstrained-bw

        } //container mcac

        container static {
          description
              "Add/remove IGMP static group membership";
          list group {
            key "grp-ip-address";
            description
                "Add/remove a static multicast group";
            leaf grp-ip-address {
              type inet:ip-address;
              description
                  "a.b.c.d - multicast group address";
            } //grp-ip-address

            list source {
              key "ip-address";
              description
                  "Add/remove a static multicast source";
              leaf ip-address {
                type inet:ip-address;
              } //ip-address

            } //list source

            leaf starg {
              type boolean;
              description
                  "Add/remove a static starg entry";
            }

          } //list group

        } //container static

      } //container igmp-snooping

      container ingress {
        description
            "Spoke SDP binding ingress configuration";
        container filter {
          description
              "Apply ingress filter";
          leaf ip {
            type string;
            description
                "[1..65535]|<name:64 char max>";
          } //ip

          leaf mac {
            type string;
            description
                "[1..65535]|<name:64 char max>";
          } //mac

          leaf ipv6 {
            type string;
            description
                "[1..65535]|<name:64 char max>";
          } //ipv6

        } //container filter

        list qos {
          key "network-policy-id";
          description
              "Configure ingress qos";
          leaf network-policy-id {
            type uint32 {
              range "1..65535";
            }
          } //network-policy-id

          leaf fp-redirect-group {
            type string {
              length "1..32";
            }
          } //fp-redirect-group

          leaf instance {
            type uint16 {
              range "1..65535";
            }
          } //instance

        } //list qos

        list vc-label {
          key "ingress-vc-label";
          description
              "Configure ingress VC label";
          leaf ingress-vc-label {
            type string;
            description
                "Attribute ingress-vc-label for vc-label";
          } //ingress-vc-label

        } //list vc-label

      } //container ingress

      container mld-snooping {
        description
            "Configure MLD snooping parameters";
        leaf disable-router-alert-check {
          type boolean;
          description
              "Enable/disable the MLD router alert check option";
        }

        leaf fast-leave {
          type boolean;
          description
              "Enable/disable MLD fast-leave processing";
        }

        container import {
          description
              "Import a policy to filter MLD packets";
          leaf policy-name {
            type string {
              length "1..32";
            }
          } //policy-name

        } //container import

        container last-member-query-interval {
          description
              "Configure the MLD Last Member Query Interval";
          leaf t1-10-seconds {
            type uint32 {
              range "1..50";
            }
          } //t1-10-seconds

        } //container last-member-query-interval

        container max-num-groups {
          description
              "Configure the max number of multicast groups allowed";
          leaf max-num-groups-id {
            type uint32 {
              range "1..16000";
            }
          } //max-num-groups-id

        } //container max-num-groups

        leaf mrouter-port {
          type boolean;
          description
              "Configure the spoke SDP as a multicast router port";
        }

        container query-interval {
          description
              "Configure the MLD Query Interval";
          leaf seconds {
            type uint32 {
              range "2..1024";
            }
          } //seconds

        } //container query-interval

        container query-response-interval {
          description
              "Configure the MLD Query Response Interval";
          leaf seconds {
            type uint32 {
              range "1..1023";
            }
          } //seconds

        } //container query-response-interval

        container robust-count {
          description
              "Configure the MLD Robustness Variable";
          leaf robust-count {
            type uint32 {
              range "2..7";
            }
          } //robust-count

        } //container robust-count

        leaf send-queries {
          type boolean;
          description
              "Enable/disable generation of MLD General Queries";
        }

        container version {
          description
              "Configure the version of MLD";
          leaf version {
            type uint32 {
              range "1..2";
            }
            description
                "[1 or 2]";
          } //version

        } //container version

        container mcac {
          description
              "Configure multicast CAC policy and constraints for this SDP";
          container if-policy {
            description
                "Configure multicast CAC if-policy";
            leaf if-policy-name {
              type string {
                length "1..32";
              }
            } //if-policy-name

          } //container if-policy

          container policy {
            description
                "Enable/disable multicast CAC policy";
            leaf policy-name {
              type string {
                length "1..32";
              }
              description
                  "max 32 chars";
            } //policy-name

          } //container policy

          container unconstrained-bw {
            description
                "Set/reset unconstrained-bw for multicast CAC policy on this SDP";
            leaf bandwidth {
              type int32 {
                range "0..2147483647";
              }
            } //bandwidth

            leaf mandatory-bw {
              type int32 {
                range "0..2147483647";
              }
            } //mandatory-bw

          } //container unconstrained-bw

        } //container mcac

        container static {
          description
              "Add/remove MLD static group membership";
          list group {
            key "grp-ipv6-address";
            description
                "Add/remove a static multicast group";
            leaf grp-ipv6-address {
              type inet:ipv6-address;
              description
                  "Attribute grp-ipv6-address for group";
            } //grp-ipv6-address

            list source {
              key "src-ipv6-address";
              description
                  "Add/remove a static multicast source";
              leaf src-ipv6-address {
                type inet:ipv6-address;
                description
                    "Attribute src-ipv6-address for source";
              } //src-ipv6-address

            } //list source

            leaf starg {
              type boolean;
              description
                  "Add/remove a static starg entry";
            }

          } //list group

        } //container static

      } //container mld-snooping

      container mrp {
        description
            "Configure MRP attributes";
        container join-time {
          description
              "Configure timer value in 10th of seconds for sending join-messages";
          leaf join-time {
            type int32 {
              range "1..10";
            }
            description
                "[1-10] tenths of a second";
          } //join-time

        } //container join-time

        container leave-all-time {
          description
              "Configure timer value in 10th of seconds for refreshing all attributes";
          leaf leave-all-time {
            type int32 {
              range "60..300";
            }
            description
                "[60..300] tenths of a second";
          } //leave-all-time

        } //container leave-all-time

        container leave-time {
          description
              "Configure timer value in 10th of seconds to hold attribute in leave-state";
          leaf leave-time {
            type int32 {
              range "30..60";
            }
            description
                "[30..60] tenths of a second";
          } //leave-time

        } //container leave-time

        container mrp-policy {
          description
              "Configure mrp-policy";
          leaf mrp-policy-string {
            type string {
            }
            description
                "policy-name";
          } //mrp-policy-string

        } //container mrp-policy

        container periodic-time {
          description
              "Configure timer value in 10th of seconds for re-transmission of attribute 
               declarations";
          leaf periodic-time {
            type int32 {
              range "10..100";
            }
            description
                "[10..100] tenths of a second";
          } //periodic-time

        } //container periodic-time

        leaf periodic-timer {
          type boolean;
          description
              "Control re-transmission of attribute declarations";
        }

      } //container mrp

      container pim-snooping {
        description
            "Configure PIM snooping parameters";
        container max-num-groups {
          description
              "Configure maximum group for PIM snooping";
          leaf max-num-groups-id {
            type uint32 {
              range "1..16000";
            }
          } //max-num-groups-id

        } //container max-num-groups

      } //container pim-snooping

      container pw-path-id {
        presence
            "Configure PW path identifier information";
        container agi {
          description
              "Configure Attachment Group Identifier";
          leaf attachment-group-identifier {
            type string {
            }
            description
                "<0..4294967295>:<0..4294967295>";
          } //attachment-group-identifier

        } //container agi

        container saii-type2 {
          description
              "Configure Source Attachment Individual Identifier (SAII)";
          leaf global-id-node-id-ac-id {
            type string {
            }
            description
                "Attribute global-id:node-id:ac-id for saii-type2";
          } //global-id-node-id-ac-id

        } //container saii-type2

        container taii-type2 {
          description
              "Configure Target Attachment Individual Identifier (TAII)";
          leaf global-id-node-id-ac-id {
            type string {
            }
            description
                "Attribute global-id:node-id:ac-id for taii-type2";
          } //global-id-node-id-ac-id

        } //container taii-type2

      } //container pw-path-id

      uses "conf-svc-vpls-spb-r13:alu-conf-svc-vpls-spb-r13";
      container static-isid {
        description
            "Configure static ISID ranges";
        list range {
          key "range-id";
          description
              "Configure static ISID range";
          leaf range-id {
            type uint32 {
              range "1..8191";
            }
          } //range-id

          leaf isid {
            type uint32 {
              range "1..16777215";
            }
          } //isid

          leaf to {
            type uint32 {
              range "1..16777215";
            }
            description
                "isid-value";
          } //to

        } //list range

      } //container static-isid

      container stp {
        description
            "Configure STP parameters";
        leaf auto-edge {
          type boolean;
          description
              "Enable/disable automatic detection of edge port";
        }

        leaf edge-port {
          type boolean;
          description
              "Configure spoke-sdp as edge port";
        }

        list link-type {
          key "pt-pt-shared";
          description
              "Configure link type of the spoke-sdp";
          leaf pt-pt-shared {
            type enumeration {
              enum pt-pt;
              enum shared;
            }
            description
                "link type";
          } //pt-pt-shared

        } //list link-type

        list path-cost {
          key "stp-path-cost";
          description
              "Configure path-cost";
          leaf stp-path-cost {
            type uint32 {
              range "1..200000000";
            }
          } //stp-path-cost

        } //list path-cost

        list port-num {
          key "virtual-port-number";
          description
              "Configure virtual port number";
          leaf virtual-port-number {
            type uint64 {
              range "1..2047";
            }
            description
                "[1..2047]";
          } //virtual-port-number

        } //list port-num

        list priority {
          key "stp-priority";
          description
              "Configure stp priority";
          leaf stp-priority {
            type uint32 {
              range "0..255";
            }
          } //stp-priority

        } //list priority

        leaf root-guard {
          type boolean;
          description
              "Enable/disable STP root-guard";
        }

        leaf shutdown {
          type boolean;
          description
              "Enable/disable spanning tree protocol";
        }

      } //container stp

    } //list spoke-sdp

  } //grouping alu-conf-svc-vpls-spoke-r13

} //module  alu-conf-svc-vpls-spoke-r13
