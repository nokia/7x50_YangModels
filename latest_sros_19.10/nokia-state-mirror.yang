submodule nokia-state-mirror {

    yang-version "1.1";

    belongs-to nokia-state { prefix "state"; }

    import ietf-yang-types                { prefix "yang"; }
    import nokia-sros-yang-extensions     { prefix "sros-ext"; }
    import nokia-types-qos                { prefix "types-qos"; }
    import nokia-types-services           { prefix "types-services"; }
    import nokia-types-sros               { prefix "types-sros"; }


    sros-ext:sros-major-release "rel19";

    organization "Nokia";

    contact
        "Nokia SR OS Support
         Web: <http://www.nokia.com>";

    description
        "Nokia YANG Data model with operational state for mirror services on SR OS based routers.

         Copyright 2016 Nokia. All rights reserved. Reproduction of this document
         is authorized on the condition that the foregoing copyright notice is included.

         This nokia-state-mirror YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-10-09";

    grouping state-mirror {
        container mirror {
            description "Enter the mirror context";

            list mirror-dest {
                key "service-name";
                description "Enter the mirror-dest list instance";

                leaf service-name {
                    type types-services:service-name;
                    description "Service name";
                }

                leaf oper-state {
                    type types-sros:oper-state;
                    description "Operational state.";
                }

                list sap {
                    key "sap-id";
                    description "Enter the sap list instance";

                    leaf sap-id {
                        type types-sros:sap;
                        description "SAP identifier";
                    }

                    container statistics {
                        description "Statistics information";

                        container authentication {
                            description "Authentication statistics information";

                            leaf discarded-packets {
                                type yang:counter32;
                                description
                                    "The number of DHCP packets discarded
                                     as result of authentication.";
                            }

                            leaf success-packets {
                                type yang:counter32;
                                description "The number of DHCP packets successfully authenticated.";
                            }

                        } // container authentication

                    } // container statistics

                    container egress {
                        description "Enter the egress context";

                        container qos {
                            description "Enter the qos context";

                            container sap-egress {
                                description "Enter the sap-egress context";

                                container traffic-manager {
                                    description "Traffic manager information";

                                    container statistics {
                                        description "Statistics information";

                                        leaf in-inplus-profile-dropped-packets {
                                            type yang:counter64;
                                            description
                                                "The number of in-profile packets
                                                 discarded by the egress traffic manager due
                                                 to: MBS exceeded, buffer pool limit
                                                 exceeded, etc.";
                                        }

                                        leaf in-inplus-profile-dropped-octets {
                                            type yang:counter64;
                                            description
                                                "The number of in-profile octets
                                                 discarded by the egress traffic manager due
                                                 to: MBS exceeded, buffer pool limit
                                                 exceeded, etc.";
                                        }

                                        leaf out-exceed-profile-dropped-packets {
                                            type yang:counter64;
                                            description
                                                "The number of out-of-profile packets
                                                 discarded by the egress traffic manager due
                                                 to: MBS exceeded, buffer pool limit
                                                 exceeded, etc.";
                                        }

                                        leaf out-exceed-profile-dropped-octets {
                                            type yang:counter64;
                                            description
                                                "The number of out-of-profile packets
                                                 discarded by the egress traffic manager due
                                                 to: MBS exceeded, buffer pool limit
                                                 exceeded, etc.";
                                        }

                                        leaf in-inplus-profile-forwarded-packets {
                                            type yang:counter64;
                                            description
                                                "The number of in-profile packets
                                                 (rate below CIR) forwarded by the
                                                 egress traffic manager.";
                                        }

                                        leaf in-inplus-profile-forwarded-octets {
                                            type yang:counter64;
                                            description
                                                "The number of in-profile octets
                                                 (rate below CIR) forwarded by the
                                                 egress traffic manager.";
                                        }

                                        leaf out-exceed-profile-forwarded-packets {
                                            type yang:counter64;
                                            description
                                                "The number of out-of-profile packets
                                                 (rate above CIR) forwarded by the
                                                 egress traffic manager.";
                                        }

                                        leaf out-exceed-profile-forwarded-octets {
                                            type yang:counter64;
                                            description
                                                "The number of out-of-profile octets
                                                 (rate above CIR) forwarded by the
                                                 egress traffic manager.";
                                        }

                                        leaf aggregate-forwarded-packets {
                                            type yang:counter64;
                                            description
                                                "The aggregate number of in and out-of profile
                                                 packets forwarded by the egress traffic manager.";
                                        }

                                        leaf aggregate-forwarded-octets {
                                            type yang:counter64;
                                            description
                                                "The aggregate number of in and out-of profile
                                                 octets forwarded by the egress traffic manager.";
                                        }

                                        leaf aggregate-dropped-packets {
                                            type yang:counter64;
                                            description
                                                "The aggregate number of in and out-of profile
                                                 packets discarded by the egress traffic manager due
                                                 to: MBS exceeded, buffer pool limit
                                                 exceeded, etc.";
                                        }

                                        leaf aggregate-dropped-octets {
                                            type yang:counter64;
                                            description
                                                "The aggregate number of in and out-of profile
                                                 octets discarded by the egress traffic manager due
                                                 to: MBS exceeded, buffer pool limit
                                                 exceeded, etc.";
                                        }

                                        leaf last-cleared-time {
                                            type yang:date-and-time;
                                            description "Time when the counters in this table were last cleared.";
                                        }

                                    } // container statistics

                                } // container traffic-manager

                                list queue {
                                    key "queue-id";
                                    description "SAP Egress Queue statistics.";

                                    leaf queue-id {
                                        type types-qos:egress-queue-id;
                                        description "The unique identifier for the queue.";
                                    }

                                    container statistics {
                                        description "SAP Egress Queue statistics.";

                                        choice stat-mode {
                                            case profile {

                                                container profile {

                                                    leaf in-inplus-profile-forwarded-packets {
                                                        type yang:counter64;
                                                        description
                                                            "The number of in-profile/in-plus-profile packets
                                                             (rate below CIR) forwarded.";
                                                    }

                                                    leaf in-inplus-profile-forwarded-octets {
                                                        type yang:counter64;
                                                        description
                                                            "The number of in-profile/in-plus-profile octets
                                                             (rate below CIR) forwarded.";
                                                    }

                                                    leaf out-exceed-profile-forwarded-packets {
                                                        type yang:counter64;
                                                        description
                                                            "The number of out-profile/exceed-profile packets
                                                             (rate above CIR) forwarded.";
                                                    }

                                                    leaf out-exceed-profile-forwarded-octets {
                                                        type yang:counter64;
                                                        description
                                                            "The number of out-profile/exceed-profile octets
                                                             (rate above CIR) forwarded.";
                                                    }

                                                    leaf in-inplus-profile-dropped-packets {
                                                        type yang:counter64;
                                                        description
                                                            "The number of in-profile/in-plus-profile packets
                                                             discarded.";
                                                    }

                                                    leaf in-inplus-profile-dropped-octets {
                                                        type yang:counter64;
                                                        description
                                                            "The number of in-profile/in-plus-profile octets
                                                             discarded.";
                                                    }

                                                    leaf out-exceed-profile-dropped-packets {
                                                        type yang:counter64;
                                                        description
                                                            "The number of out-profile/exceed-profile packets
                                                             discarded.";
                                                    }

                                                    leaf out-exceed-profile-dropped-octets {
                                                        type yang:counter64;
                                                        description
                                                            "The number of out-profile/exceed-profile octets
                                                             discarded.";
                                                    }

                                                } // container profile

                                            }
                                            case v4-v6 {

                                                container v4-v6 {

                                                    leaf ipv4-dropped-packets {
                                                        type yang:counter64;
                                                        description "The number of ipv4 packets discarded.";
                                                    }

                                                    leaf ipv4-dropped-octets {
                                                        type yang:counter64;
                                                        description "The number of ipv4 octets discarded.";
                                                    }

                                                    leaf ipv6-dropped-packets {
                                                        type yang:counter64;
                                                        description "The number of ipv6 packets discarded.";
                                                    }

                                                    leaf ipv6-dropped-octets {
                                                        type yang:counter64;
                                                        description "The number of ipv6 octets discarded.";
                                                    }

                                                    leaf ipv4-forwarded-packets {
                                                        type yang:counter64;
                                                        description "The number of ipv4 packets forwarded.";
                                                    }

                                                    leaf ipv4-forwarded-octets {
                                                        type yang:counter64;
                                                        description "The number of ipv4 octets forwarded.";
                                                    }

                                                    leaf ipv6-forwarded-packets {
                                                        type yang:counter64;
                                                        description "The number of ipv6 packets forwarded.";
                                                    }

                                                    leaf ipv6-forwarded-octets {
                                                        type yang:counter64;
                                                        description "The number of ipv6 octets forwarded.";
                                                    }

                                                } // container v4-v6

                                            }
                                        }
                                    } // container statistics

                                } // list queue

                            } // container sap-egress

                        } // container qos

                    } // container egress

                } // list sap

                container remote-source {
                    description "Enter the remote-source context";

                    list spoke-sdp {
                        key "sdp-bind-id";
                        description "Enter the spoke-sdp list instance";

                        leaf sdp-bind-id {
                            type types-services:sdp-bind-id;
                            description "SDP Binding identifier.";
                        }

                        leaf oper-state {
                            type enumeration {
                                enum "up"                           { value 1; }
                                enum "down"                         { value 5; }
                            }
                            description "Indicates the operating status of this Service-SDP binding.";
                        }

                        leaf oper-flags {
                            type bits {
                                bit sdp-bind-admin-down            { position 0; }
                                bit svc-admin-down                 { position 1; }
                                bit stitching-svc-txdown           { position 2; }
                                bit sdp-oper-down                  { position 3; }
                                bit sdp-path-mtu-too-small         { position 4; }
                                bit no-ingress-vc-label            { position 5; }
                                bit no-egress-vc-label             { position 6; }
                                bit svc-mtu-mismatch               { position 7; }
                                bit vc-type-mismatch               { position 8; }
                                bit relearn-limit-exceeded         { position 9; }
                                bit ies-if-admin-down              { position 10; }
                                bit released-ingress-vc-label      { position 11; }
                                bit labels-exhausted               { position 12; }
                                bit svc-param-mismatch             { position 13; }
                                bit insufficient-bandwidth         { position 14; }
                                bit pw-peer-fault-status-bits      { position 15; }
                                bit mesh-sdp-down                  { position 16; }
                                bit not-managed-by-mcring          { position 17; }
                                bit out-of-resource                { position 18; }
                                bit mh-standby                     { position 19; }
                                bit oam-down-mep-fault             { position 20; }
                                bit oam-up-mep-fault               { position 21; }
                                bit standby-sig-slave-tx-down      { position 22; }
                                bit oper-grp-down                  { position 23; }
                                bit withdrawn-ingress-vc-label     { position 24; }
                                bit vpls-pmsi-down                 { position 25; }
                                bit rec-prot-src-mac               { position 26; }
                                bit peer-fault-status-tx-down      { position 27; }
                                bit evpn-route-conflict            { position 28; }
                                bit admin-locked                   { position 29; }
                                bit evpn-p2mp-conflict             { position 30; }
                                bit label-stack-limit-exceeded     { position 31; }
                            }
                            description
                                "This object indicates all the conditions that affect the
                                 operating status of this SDP Bind.";
                        }

                        container ingress {
                            description "Enter the ingress context";

                            leaf oper-label {
                                type uint32;
                                description "MPLS service label used by the far-end device to send packets to the local PEs sdp-bind.";
                            }

                        } // container ingress

                        container egress {
                            description "Enter the egress context";

                            leaf oper-label {
                                type uint32;
                                description "MPLS service label used to send packets to the far-end device via this sdp-bind.";
                            }

                        } // container egress

                    } // list spoke-sdp

                } // container remote-source

                list spoke-sdp {
                    key "sdp-bind-id";
                    description "Enter the spoke-sdp list instance";

                    leaf sdp-bind-id {
                        type types-services:sdp-bind-id;
                        description "SDP Binding identifier.";
                    }

                    leaf oper-state {
                        type enumeration {
                            enum "up"                           { value 1; }
                            enum "down"                         { value 5; }
                        }
                        description "Indicates the operating status of this Service-SDP binding.";
                    }

                    leaf oper-flags {
                        type bits {
                            bit sdp-bind-admin-down            { position 0; }
                            bit svc-admin-down                 { position 1; }
                            bit stitching-svc-txdown           { position 2; }
                            bit sdp-oper-down                  { position 3; }
                            bit sdp-path-mtu-too-small         { position 4; }
                            bit no-ingress-vc-label            { position 5; }
                            bit no-egress-vc-label             { position 6; }
                            bit svc-mtu-mismatch               { position 7; }
                            bit vc-type-mismatch               { position 8; }
                            bit relearn-limit-exceeded         { position 9; }
                            bit ies-if-admin-down              { position 10; }
                            bit released-ingress-vc-label      { position 11; }
                            bit labels-exhausted               { position 12; }
                            bit svc-param-mismatch             { position 13; }
                            bit insufficient-bandwidth         { position 14; }
                            bit pw-peer-fault-status-bits      { position 15; }
                            bit mesh-sdp-down                  { position 16; }
                            bit not-managed-by-mcring          { position 17; }
                            bit out-of-resource                { position 18; }
                            bit mh-standby                     { position 19; }
                            bit oam-down-mep-fault             { position 20; }
                            bit oam-up-mep-fault               { position 21; }
                            bit standby-sig-slave-tx-down      { position 22; }
                            bit oper-grp-down                  { position 23; }
                            bit withdrawn-ingress-vc-label     { position 24; }
                            bit vpls-pmsi-down                 { position 25; }
                            bit rec-prot-src-mac               { position 26; }
                            bit peer-fault-status-tx-down      { position 27; }
                            bit evpn-route-conflict            { position 28; }
                            bit admin-locked                   { position 29; }
                            bit evpn-p2mp-conflict             { position 30; }
                            bit label-stack-limit-exceeded     { position 31; }
                        }
                        description
                            "This object indicates all the conditions that affect the
                             operating status of this SDP Bind.";
                    }

                    container ingress {
                        description "Enter the ingress context";

                        leaf oper-label {
                            type uint32;
                            description "MPLS service label used by the far-end device to send packets to the local PEs sdp-bind.";
                        }

                    } // container ingress

                    container egress {
                        description "Enter the egress context";

                        leaf oper-label {
                            type uint32;
                            description "MPLS service label used to send packets to the far-end device via this sdp-bind.";
                        }

                    } // container egress

                } // list spoke-sdp

                list pcap {
                    key "session-name";
                    description "Enter the pcap list instance";

                    leaf session-name {
                        type types-sros:named-item;
                        description "Packet Capture (PCAP) session name";
                    }

                    leaf session-state {
                        type enumeration {
                            enum "failed"                       { value 0; }
                            enum "init"                         { value 1; }
                            enum "ready"                        { value 2; }
                            enum "start"                        { value 3; }
                            enum "in-progress"                  { value 4; }
                            enum "stopped"                      { value 5; }
                            enum "file-error"                   { value 6; }
                            enum "buffer-full"                  { value 7; }
                            enum "buffer-high-watermark"        { value 8; }
                        }
                        description "The capture state of the PCAP session.";
                    }

                    leaf buffer-size {
                        type uint32;
                        units "bytes";
                        description "The total buffer size, in bytes, currently in use by the PCAP session.";
                    }

                    leaf file-size {
                        type uint32;
                        units "bytes";
                        description "The total number of bytes that have been written to the file specified by file-url.";
                    }

                    leaf last-file-write-time {
                        type types-sros:date-time;
                        description "The last time the file specified by file-url was written to.";
                    }

                    leaf buffer-write-failures {
                        type uint32;
                        description "The total number of times that the PCAP session has failed to write to its buffer.";
                    }

                    leaf buffer-read-failures {
                        type uint32;
                        description "The total number of times that the PCAP session has failed to read its buffer.";
                    }

                    leaf dropped-packets {
                        type uint32;
                        units "packets";
                        description "The total number of packets that were dropped by this PCAP session.";
                    }

                    leaf processing-time-bailouts {
                        type uint32;
                        description "The total number of processing time bailouts that have occurred for the PCAP session.";
                    }

                } // list pcap

            } // list mirror-dest

            list mirror-source {
                key "service-name";
                description "Enter the mirror-source list instance";

                leaf service-name {
                    type types-services:service-name;
                    description "Service name";
                }

                leaf creation-origin {
                    type enumeration {
                        enum "debug"                        { value 1; }
                        enum "li"                           { value 2; }
                        enum "config"                       { value 3; }
                    }
                    description "The protocol or mechanism that created this mirror-source entry";
                }

                container statistics {
                    description "Statistics per-mirror-source entry";

                    leaf total-sources {
                        type uint32;
                        description "The total number of sources configured under this mirror-source entry";
                    }

                } // container statistics

            } // list mirror-source

        } // container mirror

    } // grouping state-mirror

}
