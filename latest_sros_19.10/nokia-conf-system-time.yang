submodule nokia-conf-system-time {

    yang-version "1.1";

    belongs-to nokia-conf { prefix "conf"; }

    import nokia-sros-yang-extensions     { prefix "sros-ext"; }
    import nokia-types-router             { prefix "types-router"; }
    import nokia-types-sros               { prefix "types-sros"; }
    import nokia-types-system             { prefix "types-system"; }

    include nokia-conf-groups;
    include nokia-conf-router;

    sros-ext:sros-major-release "rel19";

    organization "Nokia";

    contact
        "Nokia SR OS Support
         Web: <http://www.nokia.com>";

    description
        "Nokia YANG Data model to configure system time parameters on SR OS based routers.

         Copyright 2016 Nokia. All rights reserved. Reproduction of this document
         is authorized on the condition that the foregoing copyright notice is included.

         This nokia-conf-system-time YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-04-25";

    grouping conf-system-time {
        container time {
            description "Enter the time context";

            leaf prefer-local-time {
                type boolean;
                default "false";
                description "Use local time over UTC time in the system";
            }

            leaf-list apply-groups {
                type leafref {
                    path "../../../groups/group/name";
                }
                max-elements 8;
                ordered-by user;
                description "Apply a configuration group at this level";
            }

            container zone {
                description "Enter the zone context";

                choice time-zone {
                    default "standard-zone";
                    case standard-zone {

                        container standard {
                            description "Enter the standard context";

                            leaf name {
                                type enumeration {
                                    enum "hst"                          { value 1; }
                                    enum "akst"                         { value 2; }
                                    enum "pst"                          { value 3; }
                                    enum "mst"                          { value 4; }
                                    enum "cst"                          { value 5; }
                                    enum "est"                          { value 6; }
                                    enum "ast"                          { value 7; }
                                    enum "nst"                          { value 8; }
                                    enum "utc"                          { value 9; }
                                    enum "gmt"                          { value 10; }
                                    enum "wet"                          { value 11; }
                                    enum "cet"                          { value 12; }
                                    enum "eet"                          { value 13; }
                                    enum "msk"                          { value 14; }
                                    enum "msd"                          { value 15; }
                                    enum "awst"                         { value 16; }
                                    enum "acst"                         { value 17; }
                                    enum "aest"                         { value 18; }
                                    enum "nzst"                         { value 19; }
                                }
                                default "utc";
                                description "Active standard time zone in this managed system";
                            }

                        } // container standard

                    }
                    case non-standard-zone {

                        container non-standard {
                            description "Enter the non-standard context";

                            leaf name {
                                type string {
                                    length "1..5";
                                    pattern "([0-9]|[a-z])+" {
                                        error-message "The name can only contain lower case letters, and digits.";
                                    }
                                }
                                description "Active non-standard time zone in this managed system";
                            }

                            leaf offset {
                                type types-system:hours-minutes-with-range;
                                description "Number of hours and minutes by which the time zone offsets from UTC";
                            }

                        } // container non-standard

                    }
                }
            } // container zone

            list dst-zone {
                key "summer-time-zone";
                max-elements 1;
                description "Enter the dst-zone list instance";

                leaf summer-time-zone {
                    type string {
                        length "1..5";
                    }
                    description "Name of a summer time zone";
                }

                leaf offset {
                    type uint32 {
                        range "0..60";
                    }
                    units "minutes";
                    default "60";
                    description "Offset for summer time setting";
                }

                leaf-list apply-groups {
                    type leafref {
                        path "../../../../groups/group/name";
                    }
                    max-elements 8;
                    ordered-by user;
                    description "Apply a configuration group at this level";
                }

                container end {
                    description "Enter the end context";

                    leaf week {
                        type types-system:week;
                        default "first";
                        description "Week of the month when the daylight savings time setting ends";
                    }

                    leaf day {
                        type types-system:day-of-week-name-long;
                        default "sunday";
                        description "Day of the week when the daylight savings time setting ends";
                    }

                    leaf month {
                        type types-system:month-name-long;
                        default "january";
                        description "Month of the week when the daylight savings time setting ends";
                    }

                    leaf hours-minutes {
                        type types-system:hours-minutes-twenty-four;
                        default "00:00";
                        description "Hour and number of minutes after which the daylight savings time ends";
                    }

                } // container end

                container start {
                    description "Enter the start context";

                    leaf week {
                        type types-system:week;
                        default "first";
                        description "Week of the month when the daylight savings time setting starts";
                    }

                    leaf day {
                        type types-system:day-of-week-name-long;
                        default "sunday";
                        description "Day of the week when the daylight savings time setting starts";
                    }

                    leaf month {
                        type types-system:month-name-long;
                        default "january";
                        description "Month of the week when the daylight savings time setting starts";
                    }

                    leaf hours-minutes {
                        type types-system:hours-minutes-twenty-four;
                        default "00:00";
                        description "Hour and number of minutes after which the daylight savings time starts";
                    }

                } // container start

            } // list dst-zone

            container ntp {
                presence "Enables/disables the NTP server";
                description "Enter the ntp context";

                leaf authentication-check {
                    type boolean;
                    default "true";
                    description "Reject NTP PDUs that do not match the authentication key-id, type, or key requirements";
                }

                leaf admin-state {
                    type types-sros:admin-state;
                    default "disable";
                    description "Administrative state of NTP execution";
                }

                leaf-list apply-groups {
                    type leafref {
                        path "../../../../groups/group/name";
                    }
                    max-elements 8;
                    ordered-by user;
                    description "Apply a configuration group at this level";
                }

                container ntp-server {
                    presence "Enable NTP server for the node";
                    description "Enter the ntp-server context";

                    leaf authenticate {
                        type boolean;
                        default "false";
                        description "Authentication of NTP PDUs when acting as a server";
                    }

                } // container ntp-server

                list server {
                    key "ip-address router-instance";
                    description "Enter the server list instance";

                    leaf ip-address {
                        type union {
                            type types-sros:ip-address;
                            type enumeration {
                                enum "ptp"                          { value 1; }
                            }
                        }
                        description "Node that provides time to the NTP client of this system";
                    }

                    leaf router-instance {
                        type string;
                        description "Routing context containing the interface";
                    }

                    leaf key-id {
                        type leafref {
                            path "../../authentication-key/key-id";
                        }
                        description "Specifies the key-id of the authentication key and its authentication type used by this node to receive and transmit NTP packets to and from an NTP node.";
                    }

                    leaf version {
                        type uint32 {
                            range "2..4";
                        }
                        default "4";
                        description "Specifies the NTP version number generated or accepted by this node in NTP packets.";
                    }

                    leaf prefer {
                        type boolean;
                        default "false";
                        description "NTP server from which is preferred to receive time";
                    }

                    leaf-list apply-groups {
                        type leafref {
                            path "../../../../../groups/group/name";
                        }
                        max-elements 8;
                        ordered-by user;
                        description "Apply a configuration group at this level";
                    }

                } // list server

                list peer {
                    key "ip-address router-instance";
                    description "Enter the peer list instance";

                    leaf ip-address {
                        type types-sros:ip-address;
                        description "Identifies a node that will provide time to the NTP client of this system.";
                    }

                    leaf router-instance {
                        type string;
                        description "Routing context containing the interface";
                    }

                    leaf key-id {
                        type leafref {
                            path "../../authentication-key/key-id";
                        }
                        description "Specifies the key-id of the authentication key and its authentication type used by this node to receive and transmit NTP packets to and from an NTP node.";
                    }

                    leaf version {
                        type uint32 {
                            range "2..4";
                        }
                        default "4";
                        description "Specifies the NTP version number generated or accepted by this node in NTP packets.";
                    }

                    leaf prefer {
                        type boolean;
                        default "false";
                        description "NTP server from which is preferred to receive time";
                    }

                    leaf-list apply-groups {
                        type leafref {
                            path "../../../../../groups/group/name";
                        }
                        max-elements 8;
                        ordered-by user;
                        description "Apply a configuration group at this level";
                    }

                } // list peer

                list broadcast {
                    key "router-instance interface-name";
                    description "Enter the broadcast list instance";

                    leaf router-instance {
                        type leafref {
                            path "../../../../../router/router-name";
                        }
                        description "Administrative name for this virtual router";
                    }

                    leaf interface-name {
                        type types-sros:interface-name;
                        description "Router interface name";
                    }

                    leaf version {
                        type uint32 {
                            range "2..4";
                        }
                        default "4";
                        description "NTP version number generated or accepted by this node in NTP packets";
                    }

                    leaf ttl {
                        type uint32 {
                            range "1..255";
                        }
                        default "127";
                        description "TTL value of messages transmitted by this broadcast address";
                    }

                    leaf key-id {
                        type leafref {
                            path "../../authentication-key/key-id";
                        }
                        description "Specifies the key-id of the authentication key and its authentication type used by this node to receive and transmit NTP packets to and from an NTP node.";
                    }

                    leaf-list apply-groups {
                        type leafref {
                            path "../../../../../groups/group/name";
                        }
                        max-elements 8;
                        ordered-by user;
                        description "Apply a configuration group at this level";
                    }

                } // list broadcast

                list broadcast-client {
                    key "router-instance interface-name";
                    description "Enter the broadcast-client list instance";

                    leaf router-instance {
                        type string;
                        description "Administrative name for this virtual router";
                    }

                    leaf interface-name {
                        type types-sros:interface-name;
                        description "Router interface name";
                    }

                    leaf authenticate {
                        type boolean;
                        default "false";
                        description "NTP PDUs authentication required when acting as a broadcast client";
                    }

                    leaf-list apply-groups {
                        type leafref {
                            path "../../../../../groups/group/name";
                        }
                        max-elements 8;
                        ordered-by user;
                        description "Apply a configuration group at this level";
                    }

                } // list broadcast-client

                container multicast {
                    presence "Configure NTP multicast server";
                    description "Enter the multicast context";

                    leaf version {
                        type uint32 {
                            range "2..4";
                        }
                        default "4";
                        description "Specifies the NTP version number generated or accepted by this node in NTP packets.";
                    }

                    leaf key-id {
                        type leafref {
                            path "../../authentication-key/key-id";
                        }
                        description "Specifies the key-id of the authentication key and its authentication type used by this node to receive and transmit NTP packets to and from an NTP node.";
                    }

                    leaf-list apply-groups {
                        type leafref {
                            path "../../../../../groups/group/name";
                        }
                        max-elements 8;
                        ordered-by user;
                        description "Apply a configuration group at this level";
                    }

                } // container multicast

                container multicast-client {
                    presence "Configure NTP multicast client";
                    description "Enter the multicast-client context";

                    leaf authenticate {
                        type boolean;
                        default "false";
                        description "Authentication of NTP PDUs required when acting as a client";
                    }

                    leaf-list apply-groups {
                        type leafref {
                            path "../../../../../groups/group/name";
                        }
                        max-elements 8;
                        ordered-by user;
                        description "Apply a configuration group at this level";
                    }

                } // container multicast-client

                list authentication-key {
                    key "key-id";
                    description "Enter the authentication-key list instance";

                    leaf key-id {
                        type uint32 {
                            range "1..255";
                        }
                        description "Index of the NTP authentication key table that uniquely identifies an authentication key and type";
                    }

                    leaf key {
                        type types-sros:encrypted-leaf {
                            length "1..71";
                        }
                        mandatory true;
                        description "Key to authenticate NTP packets";
                    }

                    leaf type {
                        type enumeration {
                            enum "des"                          { value 1; }
                            enum "message-digest"               { value 2; }
                        }
                        mandatory true;
                        description "Type of authentication method to authenticate NTP packet";
                    }

                    leaf-list apply-groups {
                        type leafref {
                            path "../../../../../groups/group/name";
                        }
                        max-elements 8;
                        ordered-by user;
                        description "Apply a configuration group at this level";
                    }

                } // list authentication-key

            } // container ntp

            container sntp {
                description "Enter the sntp context";

                leaf sntp-state {
                    type types-router:unicast-broadcast;
                    default "unicast";
                    description "Mode for Simple Network Time Protocol (SNTP)";
                }

                leaf admin-state {
                    type types-sros:admin-state;
                    default "disable";
                    description "Administrative state of the SNTP protocol execution";
                }

                leaf-list apply-groups {
                    type leafref {
                        path "../../../../groups/group/name";
                    }
                    max-elements 8;
                    ordered-by user;
                    description "Apply a configuration group at this level";
                }

                list server {
                    key "ip-address";
                    description "Enter the server list instance";

                    leaf ip-address {
                        type types-sros:ip-address;
                        description "Node that provides time to the NTP client of this system";
                    }

                    leaf version {
                        type int32 {
                            range "1..3";
                        }
                        default "3";
                        description "SNTP version supported by this server";
                    }

                    leaf prefer {
                        type boolean;
                        default "false";
                        description "Preference value for this SNTP server";
                    }

                    leaf interval {
                        type uint32 {
                            range "64..1024";
                        }
                        units "seconds";
                        default "64";
                        description "Frequency of querying the server";
                    }

                    leaf-list apply-groups {
                        type leafref {
                            path "../../../../../groups/group/name";
                        }
                        max-elements 8;
                        ordered-by user;
                        description "Apply a configuration group at this level";
                    }

                } // list server

            } // container sntp

        } // container time

    } // grouping conf-system-time

}
