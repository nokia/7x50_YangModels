submodule nokia-conf-submgt-service-chaining {

    yang-version "1.1";

    belongs-to nokia-conf { prefix "conf"; }

    import nokia-sros-yang-extensions     { prefix "sros-ext"; }
    import nokia-types-filter             { prefix "types-filter"; }
    import nokia-types-services           { prefix "types-services"; }
    import nokia-types-sros               { prefix "types-sros"; }

    include nokia-conf-groups;

    sros-ext:sros-major-release "rel19";

    organization "Nokia";

    contact
        "Nokia SR OS Support
         Web: <http://www.nokia.com>";

    description
        "Nokia YANG Data model to configure service chaining on SR OS based routers.

         Copyright 2016 Nokia. All rights reserved. Reproduction of this document
         is authorized on the condition that the foregoing copyright notice is included.

         This nokia-conf-submgt-service-chaining YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-10-09";

    grouping conf-submgt-service-chaining-isa-service-chaining {
        container isa-service-chaining {
            description "Enter the isa-service-chaining context";

            leaf mac-prefix {
                type string {
                    length "8";
                    pattern "[0-9a-f][02468ace](:[0-9a-f]{2}){2}";
                }
                description "Unique MAC prefix per ISA and per outside service for all NAT-groups configured for Service Chaining";
            }

            leaf-list apply-groups {
                type leafref {
                    path "../../../groups/group/name";
                }
                max-elements 8;
                ordered-by user;
                description "Apply a configuration group at this level";
            }

            list evpn {
                key "id";
                max-elements 1024;
                description "Enter the evpn list instance";

                leaf id {
                    type types-services:service-name {
                        pattern "[0-9]{1,10}";
                    }
                    description "Service-id of the EVPN";
                }

                leaf admin-state {
                    type types-sros:admin-state;
                    default "disable";
                    description "Administrative state of EVPN";
                }

                leaf description {
                    type types-sros:description;
                    description "Text description";
                }

                leaf import-mode {
                    type enumeration {
                        enum "none"                         { value 0; }
                        enum "bridged"                      { value 1; }
                        enum "routed"                       { value 2; }
                    }
                    sros-ext:immutable;
                    default "none";
                    description "Import mode for the EVPN";
                }

                leaf prefix-route-resolution {
                    type enumeration {
                        enum "recursive"                    { value 0; }
                        enum "non-recursive"                { value 1; }
                    }
                    sros-ext:immutable;
                    default "recursive";
                    description "How prefix routes should be resolved";
                }

                leaf-list apply-groups {
                    type leafref {
                        path "../../../../groups/group/name";
                    }
                    max-elements 8;
                    ordered-by user;
                    description "Apply a configuration group at this level";
                }

                container bgp {
                    description "Enter the bgp context";

                    container route-distinguisher {
                        description "Enter the route-distinguisher context";

                        leaf rd {
                            type types-services:vpn-route-distinguisher-or-auto-rd;
                            sros-ext:auto-restart-to-modify;
                            description "High-order 6 bytes that are used as string to compose VSI-ID for use in NLRI";
                        }

                    } // container route-distinguisher

                    container route-target {
                        presence "Route target parameters";
                        description "Enter the route-target context";

                        leaf import {
                            type types-services:route-target-32;
                            sros-ext:auto-restart-to-modify;
                            mandatory true;
                            description "Extended community name for default import policy for BGP in EVPN service";
                        }

                        leaf export {
                            type types-services:route-target-32;
                            sros-ext:auto-restart-to-modify;
                            mandatory true;
                            description "Extended community name for default export policy for BGP in EVPN service";
                        }

                    } // container route-target

                } // container bgp

                container export {
                    description "Enter the export context";

                    container vxlan {
                        description "Enter the vxlan context";

                        leaf vni {
                            type uint32 {
                                range "1..16777215";
                            }
                            sros-ext:auto-restart-to-modify;
                            description "VNI of the VXLAN created by the EVPN service";
                        }

                    } // container vxlan

                    container gateway-address-range {
                        when "not(../../import-mode = 'bridged') and ../../prefix-route-resolution = 'recursive'";
                        presence "Gateway address range";
                        description "Enter the gateway-address-range context";

                        leaf start {
                            type types-sros:ipv4-unicast-address;
                            mandatory true;
                            description "Start of the gateway address range (V4) for this EVPN service";
                        }

                        leaf end {
                            type types-sros:ipv4-unicast-address;
                            mandatory true;
                            description "End of the gateway address range (V4) for this EVPN service";
                        }

                    } // container gateway-address-range

                    container advertise-pools {
                        when "not(../../import-mode = 'bridged')";
                        description "Enter the advertise-pools context";

                        leaf admin-state {
                            type types-sros:admin-state;
                            default "disable";
                            description "Administrative state of NAT pool route advertisement";
                        }

                        list pool {
                            key "router-instance name";
                            description "Add a list entry for pool";

                            leaf router-instance {
                                type string;
                                description "Router-instance of the NAT pool";
                            }

                            leaf name {
                                type types-sros:named-item;
                                description "Name of the NAT pool";
                            }

                        } // list pool

                    } // container advertise-pools

                } // container export

            } // list evpn

            list vas-filter {
                key "name";
                description "Enter the vas-filter list instance";

                leaf name {
                    type types-sros:named-item;
                    description "VAS filter name";
                }

                leaf description {
                    type types-sros:description;
                    description "Text description";
                }

                leaf-list apply-groups {
                    type leafref {
                        path "../../../../groups/group/name";
                    }
                    max-elements 8;
                    ordered-by user;
                    description "Apply a configuration group at this level";
                }

                list entry {
                    key "id";
                    max-elements 64;
                    description "Enter the entry list instance";

                    leaf id {
                        type types-filter:limited-entry-id;
                        description "VAS filter entry id";
                    }

                    leaf admin-state {
                        type types-sros:admin-state;
                        default "disable";
                        description "Administrative state of the VAS filter";
                    }

                    leaf description {
                        type types-sros:description;
                        description "Text description";
                    }

                    leaf-list apply-groups {
                        type leafref {
                            path "../../../../../groups/group/name";
                        }
                        max-elements 8;
                        ordered-by user;
                        sros-ext:auto-restart-to-modify;
                        description "Apply a configuration group at this level";
                    }

                    container match {
                        sros-ext:auto-restart-to-modify;
                        description "Enter the match context";

                        leaf protocol {
                            type enumeration {
                                enum "tcp-udp"                      { value -2; description "TCP & UDP"; }
                                enum "none"                         { value -1; description "Disable matching by IP protocol"; }
                                enum "icmp"                         { value 1; description "ICMP"; }
                                enum "tcp"                          { value 6; description "TCP"; }
                                enum "udp"                          { value 17; description "UDP"; }
                            }
                            sros-ext:auto-restart-to-modify;
                            default "none";
                            description "IP protocol to match the VAS filter";
                        }

                        leaf foreign-ip {
                            type union {
                                type types-sros:ipv4-unicast-prefix;
                                type types-sros:ipv4-unicast-address;
                            }
                            sros-ext:auto-restart-to-modify;
                            description "Foreign IP address or prefix to match in this VAS filter entry";
                        }

                        leaf foreign-port {
                            type types-sros:tcp-udp-port-non-zero;
                            sros-ext:auto-restart-to-modify;
                            description "Foreign TCP or UDP port to match in this VAS filter entry";
                        }

                    } // container match

                    list action {
                        key "direction";
                        sros-ext:auto-restart-to-modify;
                        description "Enter the action list instance";

                        leaf direction {
                            type enumeration {
                                enum "upstream"                     { value 1; }
                                enum "downstream"                   { value 2; }
                            }
                            description "Direction for the action in a VAS filter entry";
                        }

                        leaf fail-action {
                            type types-filter:filter-default-action;
                            sros-ext:auto-restart-to-modify;
                            default "accept";
                            description "Fail action when sf-ip is not resolved or no forward action specified";
                        }

                        leaf-list apply-groups {
                            type leafref {
                                path "../../../../../../groups/group/name";
                            }
                            max-elements 8;
                            ordered-by user;
                            sros-ext:auto-restart-to-modify;
                            description "Apply a configuration group at this level";
                        }

                        container forward {
                            presence "Packet forwarding";
                            sros-ext:auto-restart-to-modify;
                            description "Enter the forward context";

                            leaf sf-ip {
                                type types-sros:ip-unicast-without-local-address;
                                sros-ext:auto-restart-to-modify;
                                mandatory true;
                                description "Forwarding SF (Service Forward) IP address for the action in VAS filter entry";
                            }

                            leaf svc {
                                type leafref {
                                    path "../../../../../evpn/id";
                                }
                                sros-ext:auto-restart-to-modify;
                                mandatory true;
                                description "EVPN service used for forwarding packets";
                            }

                            leaf esi {
                                type types-services:ethernet-segment-id {
                                    pattern "[0-9a-fA-F]{2}([:\\- ][0-9a-fA-F]{2}){9}";
                                }
                                sros-ext:auto-restart-to-modify;
                                default "00:00:00:00:00:00:00:00:00:00";
                                description "ESI (Ethernet Segment Identifier) for the action in a VAS filter";
                            }

                        } // container forward

                        container insert-nsh {
                            sros-ext:auto-restart-to-modify;
                            description "Enter the insert-nsh context";

                            container svc-path {
                                presence "Service path";
                                sros-ext:auto-restart-to-modify;
                                description "Enter the svc-path context";

                                leaf path-id {
                                    type uint32 {
                                        range "1..16777215";
                                    }
                                    sros-ext:auto-restart-to-modify;
                                    mandatory true;
                                    description "Path ID used to construct a NSH for the action in a VAS filter entry";
                                }

                                leaf svc-index {
                                    type uint32 {
                                        range "1..255";
                                    }
                                    sros-ext:auto-restart-to-modify;
                                    mandatory true;
                                    description "Service index used to construct a NSH for the action in a VAS filter entry";
                                }

                            } // container svc-path

                            container meta-data {
                                sros-ext:auto-restart-to-modify;
                                description "Enter the meta-data context";

                                choice type {
                                    case opaque-data {

                                        leaf opaque-data {
                                            type string {
                                                length "10|18|26|34";
                                            }
                                            sros-ext:auto-restart-to-modify;
                                            description "Opaque meta-data for the NSH";
                                        }

                                    }
                                    case insert-subscriber-id {

                                        leaf insert-subscriber-id {
                                            type empty;
                                            sros-ext:auto-restart-to-modify;
                                            description "Insert the subscriber-id in the NSH";
                                        }

                                    }
                                }
                            } // container meta-data

                        } // container insert-nsh

                    } // list action

                } // list entry

            } // list vas-filter

        } // container isa-service-chaining

    } // grouping conf-submgt-service-chaining-isa-service-chaining

}
