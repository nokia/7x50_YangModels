submodule nokia-conf-router-pim {

    yang-version "1.1";

    belongs-to nokia-conf { prefix "conf"; }

    import nokia-sros-yang-extensions     { prefix "sros-ext"; }
    import nokia-types-mcast-cac          { prefix "types-mcast-cac"; }
    import nokia-types-sros               { prefix "types-sros"; }

    include nokia-conf-groups;
    include nokia-conf-mcast-cac;
    include nokia-conf-policy-options;
    include nokia-conf-service;

    sros-ext:sros-major-release "rel19";

    organization "Nokia";

    contact
        "Nokia SR OS Support
         Web: <http://www.nokia.com>";

    description
        "Nokia YANG Data model to configure Base router PIM protocol on SR OS based routers.

         Copyright 2016 Nokia. All rights reserved. Reproduction of this document
         is authorized on the condition that the foregoing copyright notice is included.

         This nokia-conf-router-pim YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-04-20";

    grouping conf-router-pim {
        container pim {
            presence "Enables PIM functionality.";
            description "Enter the pim context";

            leaf admin-state {
                type types-sros:admin-state;
                default "enable";
                description "Administrative state of PIM";
            }

            leaf apply-to {
                type enumeration {
                    enum "ies"                          { value 1; }
                    enum "non-ies"                      { value 2; }
                    enum "all"                          { value 3; }
                    enum "none"                         { value 4; }
                }
                default "none";
                description "IES and non-IES interfaces to create in PIM";
            }

            leaf mdt-spt {
                type boolean;
                default "false";
                description "Use SPT switchover for default MDT";
            }

            leaf lag-usage-optimization {
                type boolean;
                default "false";
                description "Optimize LAG usage";
            }

            leaf mc-ecmp-balance {
                type boolean;
                default "true";
                description "Enable multicast balancing of traffic over ECMP links";
            }

            leaf mc-ecmp-balance-hold {
                type uint32 {
                    range "2..600";
                }
                units "minutes";
                description "Hold time for multicast balancing over ECMP links";
            }

            leaf non-dr-attract-traffic {
                type boolean;
                default "false";
                description "Attract traffic when the router is not the designated one";
            }

            leaf pim-ssm-scaling {
                type boolean;
                sros-ext:auto-restart-to-modify;
                default "false";
                description "Enable PIM-SSM scaling";
            }

            container ipv4 {
                description "Enter the ipv4 context";

                leaf ssm-assert-compatible-mode {
                    type boolean;
                    default "false";
                    description "Enable SSM assert compatible mode";
                }

                leaf admin-state {
                    type types-sros:admin-state;
                    default "enable";
                    description "Administrative state of PIM operation for IPv4";
                }

                leaf multicast-fast-failover {
                    type boolean;
                    default "false";
                    description "Use Multicast-Only Fast Reroute (MoFRR) functionality";
                }

                leaf rpf-table {
                    type enumeration {
                        enum "rtable-m"                     { value 0; }
                        enum "rtable-u"                     { value 1; }
                        enum "both"                         { value 2; }
                    }
                    default "rtable-u";
                    description "Route table(s) for the Reverse Path Forwarding (RPF) lookup";
                }

                leaf ssm-default-range {
                    type boolean;
                    default "true";
                    description "SSM default range";
                }

                container gtm {
                    description "Enter the gtm context";

                    leaf auto-discovery {
                        type enumeration {
                            enum "bgp"                          { value 1; }
                        }
                        description "Method for multicast VPN membership auto-discovery";
                    }

                } // container gtm

            } // container ipv4

            container ipv6 {
                description "Enter the ipv6 context";

                leaf admin-state {
                    type types-sros:admin-state;
                    default "disable";
                    description "Administrative state of PIM operation for IPv6";
                }

                leaf multicast-fast-failover {
                    type boolean;
                    default "false";
                    description "Use Multicast-Only Fast Reroute (MoFRR) functionality";
                }

                leaf rpf-table {
                    type enumeration {
                        enum "rtable-m"                     { value 0; }
                        enum "rtable-u"                     { value 1; }
                        enum "both"                         { value 2; }
                    }
                    default "rtable-u";
                    description "Route table(s) for the Reverse Path Forwarding (RPF) lookup";
                }

                leaf ssm-default-range {
                    type boolean;
                    default "true";
                    description "SSM default range";
                }

            } // container ipv6

            container mc-ecmp-hashing {
                presence "Hash based multicast balancing of traffic over ECMP links.";
                description "Enter the mc-ecmp-hashing context";

                leaf rebalance {
                    type boolean;
                    default "false";
                    description "Rebalance flows to newly added links immediately instead of waiting until they are pruned";
                }

            } // container mc-ecmp-hashing

            container import {
                description "Enter the import context";

                leaf-list join-policy {
                    type leafref {
                        path "../../../../policy-options/policy-statement/name";
                    }
                    max-elements 5;
                    ordered-by user;
                    description "Character limit for policy name";
                }

                leaf-list register-policy {
                    type leafref {
                        path "../../../../policy-options/policy-statement/name";
                    }
                    max-elements 5;
                    ordered-by user;
                    description "Character limit for policy name";
                }

            } // container import

            list interface {
                key "interface-name";
                description "Enter the interface list instance";

                leaf interface-name {
                    type types-sros:interface-name;
                    description "Router interface name";
                }

                leaf admin-state {
                    type types-sros:admin-state;
                    default "enable";
                    description "Administrative state of this interface";
                }

                leaf assert-period {
                    type int32 {
                        range "1..300";
                    }
                    default "60";
                    description "Time for periodic refreshes of PIM Assert messages on an interface";
                }

                leaf hello-interval {
                    type int32 {
                        range "0..255";
                    }
                    default "30";
                    description "Frequency at which PIM Hello messages are sent over this interface";
                }

                leaf hello-multiplier {
                    type uint32 {
                        range "20..100";
                    }
                    default "35";
                    description "Multiplier of Hello in multiples of 0.1";
                }

                leaf instant-prune-echo {
                    type boolean;
                    default "false";
                    description "Allow PIM to send an instant prune echo when router starts the prune pending timer for PIM interface";
                }

                leaf max-groups {
                    type uint32 {
                        range "0|1..16000";
                    }
                    default "0";
                    description "Max number of groups for which PIM can have local receiver information based on received PIM reports";
                }

                leaf priority {
                    type uint32 {
                        range "1..max";
                    }
                    default "1";
                    description "DR election priority for this interface";
                }

                leaf three-way-hello {
                    type boolean;
                    default "false";
                    description "Allow three-way hello compatibility mode";
                }

                leaf tracking-support {
                    type boolean;
                    default "false";
                    description "Allow upstream routers to explicitly track join membership";
                }

                leaf bsm-check-rtr-alert {
                    type boolean;
                    default "false";
                    description "Check router alert option in bootstrap messages received";
                }

                leaf improved-assert {
                    type boolean;
                    default "true";
                    description "Allow improved assert processing on interface";
                }

                leaf multicast-senders {
                    type enumeration {
                        enum "auto"                         { value 0; }
                        enum "always"                       { value 1; }
                        enum "never"                        { value 2; }
                    }
                    default "auto";
                    description "Subnet matching for the incoming data packets";
                }

                container p2mp-ldp-tree-join {
                    description "Enter the p2mp-ldp-tree-join context";

                    leaf ipv4 {
                        type boolean;
                        default "false";
                        description "Allow dynamic mLDP in-band signaling for IPv4 PIM joins";
                    }

                    leaf ipv6 {
                        type boolean;
                        default "false";
                        description "Allow dynamic mLDP in-band signaling for IPv6 PIM joins";
                    }

                } // container p2mp-ldp-tree-join

                container bfd-liveness {
                    description "Enter the bfd-liveness context";

                    leaf ipv4 {
                        type boolean;
                        default "false";
                        description "Use Bidirectional Forwarding Detection for IPv4 on PIM interface";
                    }

                    leaf ipv6 {
                        type boolean;
                        default "false";
                        description "Use Bidirectional Forwarding Detection for IPv6 on PIM interface";
                    }

                } // container bfd-liveness

                container ipv4 {
                    description "Enter the ipv4 context";

                    leaf multicast {
                        type boolean;
                        default "true";
                        description "Enable PIM interface operation";
                    }

                    container monitor-oper-group {
                        description "Enter the monitor-oper-group context";

                        leaf name {
                            type leafref {
                                path "../../../../../../service/oper-group/name";
                            }
                            description "Operational group to monitor for address family";
                        }

                        leaf operation {
                            type enumeration {
                                enum "add"                          { value 1; }
                                enum "subtract"                     { value 2; }
                                enum "set"                          { value 3; }
                            }
                            description "Perform given operation when oper-group is active.";
                        }

                        leaf priority-delta {
                            type uint32 {
                                range "1..4294967295";
                            }
                            description "Delta priority with operation when operational group is active";
                        }

                    } // container monitor-oper-group

                } // container ipv4

                container ipv6 {
                    description "Enter the ipv6 context";

                    leaf multicast {
                        type boolean;
                        default "true";
                        description "Enable PIM interface operation";
                    }

                    container monitor-oper-group {
                        description "Enter the monitor-oper-group context";

                        leaf name {
                            type leafref {
                                path "../../../../../../service/oper-group/name";
                            }
                            description "Operational group to monitor for address family";
                        }

                        leaf operation {
                            type enumeration {
                                enum "add"                          { value 1; }
                                enum "subtract"                     { value 2; }
                                enum "set"                          { value 3; }
                            }
                            description "Perform given operation when oper-group is active.";
                        }

                        leaf priority-delta {
                            type uint32 {
                                range "1..4294967295";
                            }
                            description "Delta priority with operation when operational group is active";
                        }

                    } // container monitor-oper-group

                } // container ipv6

                container sticky-dr {
                    presence "Whether sticky-DR is enabled and configure DR priority for sticky-DR.";
                    description "Enter the sticky-dr context";

                    leaf priority {
                        type uint32 {
                            range "1..max";
                        }
                        default "1024";
                        description "DR election priority for this interface";
                    }

                } // container sticky-dr

                container mcac {
                    description "Enter the mcac context";

                    leaf interface-policy {
                        type leafref {
                            path "../../../../../mcac/interface-policy/policy-name";
                        }
                        description "Name of multicast CAC interface policy";
                    }

                    leaf policy {
                        type leafref {
                            path "../../../../../mcac/policy/policy-name";
                        }
                        description "Multicast CAC policy name";
                    }

                    container bandwidth {
                        description "Enter the bandwidth context";

                        leaf total {
                            type types-mcast-cac:bandwidth-limit;
                            description "Maximum allowed bandwidth";
                        }

                        leaf mandatory {
                            type types-mcast-cac:bandwidth-limit;
                            description "Pre-reserved bandwidth for all mandatory channels";
                        }

                    } // container bandwidth

                    container mc-constraints {
                        description "Enter the mc-constraints context";

                        leaf use-lag-port-weight {
                            type boolean;
                            default "false";
                            description "Use LAG port weight in calculating MCAC constraints";
                        }

                        leaf admin-state {
                            type types-sros:admin-state;
                            default "enable";
                            description "Administrative state of constraint for multicast CAC policy";
                        }

                        list level {
                            key "level-id";
                            description "Enter the level list instance";

                            leaf level-id {
                                type types-mcast-cac:constraints-level;
                                description "Bandwidth level ID for a multicast CAC constraint";
                            }

                            leaf bandwidth {
                                type types-mcast-cac:bandwidth {
                                    range "0..2147483647";
                                }
                                mandatory true;
                                description "Bandwidth available for this level";
                            }

                        } // list level

                        list number-down {
                            key "number-lag-port-down";
                            description "Enter the number-down list instance";

                            leaf number-lag-port-down {
                                type uint32 {
                                    range "1..64";
                                }
                                description "Number of ports that are down in this LAG link";
                            }

                            leaf level {
                                type types-mcast-cac:constraints-level;
                                mandatory true;
                                description "Level ID to associate with number of down LAG ports";
                            }

                        } // list number-down

                    } // container mc-constraints

                } // container mcac

                container bier-signaling-type {
                    description "Enter the bier-signaling-type context";

                    leaf ipv4 {
                        type boolean;
                        default "false";
                        description "Whether ipv4 bier-signaling-type is enabled.";
                    }

                    leaf ipv6 {
                        type boolean;
                        default "false";
                        description "Whether ipv6 bier-signaling-type is enabled.";
                    }

                } // container bier-signaling-type

            } // list interface

            container rp {
                description "Enter the rp context";

                container bootstrap {
                    description "Enter the bootstrap context";

                    leaf-list import {
                        type leafref {
                            path "../../../../../policy-options/policy-statement/name";
                        }
                        max-elements 5;
                        ordered-by user;
                        description "Character limit for policy name";
                    }

                    leaf-list export {
                        type leafref {
                            path "../../../../../policy-options/policy-statement/name";
                        }
                        max-elements 5;
                        ordered-by user;
                        description "Character limit for policy name";
                    }

                } // container bootstrap

                container ipv4 {
                    description "Enter the ipv4 context";

                    leaf auto-rp-discovery {
                        type boolean;
                        default "false";
                        description "Enable auto RP discovery";
                    }

                    list anycast {
                        key "ipv4-address rp-set-peer";
                        description "Add a list entry for anycast";

                        leaf ipv4-address {
                            type types-sros:ipv4-unicast-address;
                            description "Anycast RP address";
                        }

                        leaf rp-set-peer {
                            type types-sros:ipv4-unicast-address;
                            description "Configure a peer in the anycast rp-set.";
                        }

                    } // list anycast

                    container bsr-candidate {
                        description "Enter the bsr-candidate context";

                        leaf admin-state {
                            type types-sros:admin-state;
                            default "disable";
                            description "Administrative state for participation of router in bootstrap election";
                        }

                        leaf priority {
                            type int32 {
                                range "0..255";
                            }
                            default "0";
                            description "Bootstrap priority of the router";
                        }

                        leaf address {
                            type types-sros:ipv4-unicast-address;
                            description "Candidate BSR IP address for Bootstrap Router election";
                        }

                        leaf hash-mask-len {
                            type int32 {
                                range "0..32";
                            }
                            default "30";
                            description "Length for bootstrap hash mask";
                        }

                    } // container bsr-candidate

                    container rp-candidate {
                        description "Enter the rp-candidate context";

                        leaf admin-state {
                            type types-sros:admin-state;
                            default "disable";
                            description "Administrative state for participation of router in bootstrap election";
                        }

                        leaf holdtime {
                            type int32 {
                                range "5..255";
                            }
                            units "seconds";
                            default "150";
                            description "Time during which the neighboring router considers this router to be up";
                        }

                        leaf priority {
                            type int32 {
                                range "0..255";
                            }
                            default "192";
                            description "Candidate RP priority";
                        }

                        leaf address {
                            type types-sros:ipv4-unicast-address;
                            description "Local RP address";
                        }

                        list group-range {
                            key "ipv4-prefix";
                            description "Add a list entry for group-range";

                            leaf ipv4-prefix {
                                type types-sros:ipv4-multicast-prefix;
                                description "IPv4 address and prefix length";
                            }

                        } // list group-range

                    } // container rp-candidate

                    container static {
                        description "Enter the static context";

                        list address {
                            key "ipv4-address";
                            description "Enter the address list instance";

                            leaf ipv4-address {
                                type types-sros:ipv4-unicast-address;
                                description "Configure the address of the statically configured RP.";
                            }

                            leaf override {
                                type boolean;
                                default "false";
                                description "Change the precedence for static RP over dynamically learnt RP";
                            }

                            list group-prefix {
                                key "ipv4-prefix";
                                description "Add a list entry for group-prefix";

                                leaf ipv4-prefix {
                                    type types-sros:ipv4-multicast-prefix;
                                    description "IPv4 address and prefix length";
                                }

                            } // list group-prefix

                        } // list address

                    } // container static

                } // container ipv4

                container ipv6 {
                    description "Enter the ipv6 context";

                    list anycast {
                        key "ipv6-address rp-set-peer";
                        description "Add a list entry for anycast";

                        leaf ipv6-address {
                            type types-sros:ipv6-unicast-address;
                            description "Anycast RP address";
                        }

                        leaf rp-set-peer {
                            type types-sros:ipv6-unicast-address;
                            description "Configure a peer in the anycast rp-set.";
                        }

                    } // list anycast

                    container bsr-candidate {
                        description "Enter the bsr-candidate context";

                        leaf admin-state {
                            type types-sros:admin-state;
                            default "disable";
                            description "Administrative state for participation of router in bootstrap election";
                        }

                        leaf priority {
                            type int32 {
                                range "0..255";
                            }
                            default "0";
                            description "Bootstrap priority of the router";
                        }

                        leaf address {
                            type types-sros:ipv6-unicast-address;
                            description "Candidate BSR IP address for Bootstrap Router election";
                        }

                        leaf hash-mask-len {
                            type int32 {
                                range "0..128";
                            }
                            default "126";
                            description "Length for bootstrap hash mask";
                        }

                    } // container bsr-candidate

                    container embedded-rp {
                        presence "Enables embedded RP parameters configuration.";
                        description "Enter the embedded-rp context";

                        leaf admin-state {
                            type types-sros:admin-state;
                            default "disable";
                            description "Administrative state of embedded RP";
                        }

                        list group-range {
                            key "ipv6-prefix";
                            description "Add a list entry for group-range";

                            leaf ipv6-prefix {
                                type types-sros:ipv6-multicast-prefix;
                                description "IPv6 address and prefix length";
                            }

                        } // list group-range

                    } // container embedded-rp

                    container rp-candidate {
                        description "Enter the rp-candidate context";

                        leaf admin-state {
                            type types-sros:admin-state;
                            default "disable";
                            description "Administrative state for participation of router in bootstrap election";
                        }

                        leaf holdtime {
                            type int32 {
                                range "5..255";
                            }
                            units "seconds";
                            default "150";
                            description "Time during which the neighboring router considers this router to be up";
                        }

                        leaf priority {
                            type int32 {
                                range "0..255";
                            }
                            default "192";
                            description "Candidate RP priority";
                        }

                        leaf address {
                            type types-sros:ipv6-unicast-address;
                            description "Local RP address";
                        }

                        list group-range {
                            key "ipv6-prefix";
                            description "Add a list entry for group-range";

                            leaf ipv6-prefix {
                                type types-sros:ipv6-multicast-prefix;
                                description "IPv6 address and prefix length";
                            }

                        } // list group-range

                    } // container rp-candidate

                    container static {
                        description "Enter the static context";

                        list address {
                            key "ipv6-address";
                            description "Enter the address list instance";

                            leaf ipv6-address {
                                type types-sros:ipv6-unicast-address;
                                description "Static IP address of the RP";
                            }

                            leaf override {
                                type boolean;
                                default "false";
                                description "Change the precedence for static RP over dynamically learnt RP";
                            }

                            list group-prefix {
                                key "ipv6-prefix";
                                description "Add a list entry for group-prefix";

                                leaf ipv6-prefix {
                                    type types-sros:ipv6-multicast-prefix;
                                    description "IPv6 address and prefix length";
                                }

                            } // list group-prefix

                        } // list address

                    } // container static

                } // container ipv6

            } // container rp

            container rpfv {
                description "Enter the rpfv context";

                leaf mvpn {
                    type boolean;
                    default "false";
                    description "Include proxy RPF vector for Inter-AS Rosen MVPN";
                }

                leaf core {
                    type boolean;
                    default "false";
                    description "Include proxy RPF vector for core";
                }

            } // container rpfv

            list spt-switchover {
                key "ip-prefix";
                description "Enter the spt-switchover list instance";

                leaf ip-prefix {
                    type types-sros:ip-multicast-prefix;
                    description "IP address and mask length";
                }

                leaf threshold {
                    type union {
                        type uint32 {
                            range "1..4294967294";
                        }
                        type enumeration {
                            enum "infinity"                     { value -1; }
                        }
                    }
                    units "kilobps";
                    mandatory true;
                    description "SPT switchover threshold";
                }

            } // list spt-switchover

            container ssm-groups {
                description "Enter the ssm-groups context";

                list group-range {
                    key "ip-prefix";
                    description "Add a list entry for group-range";

                    leaf ip-prefix {
                        type types-sros:ip-multicast-prefix;
                        description "IP address and mask length";
                    }

                } // list group-range

            } // container ssm-groups

        } // container pim

    } // grouping conf-router-pim

}
