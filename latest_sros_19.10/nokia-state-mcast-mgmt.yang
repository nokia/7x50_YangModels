submodule nokia-state-mcast-mgmt {

    yang-version "1.1";

    belongs-to nokia-state { prefix "state"; }

    import ietf-yang-types                { prefix "yang"; }
    import nokia-sros-yang-extensions     { prefix "sros-ext"; }
    import nokia-types-sros               { prefix "types-sros"; }


    sros-ext:sros-major-release "rel19";

    organization "Nokia";

    contact
        "Nokia SR OS Support
         Web: <http://www.nokia.com>";

    description
        "Nokia YANG Data model with operational state for mcast mgmt on SR OS based routers.

         Copyright 2016 Nokia. All rights reserved. Reproduction of this document
         is authorized on the condition that the foregoing copyright notice is included.

         This nokia-state-mcast-mgmt YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-11-18";

    grouping state-mcast-mgmt-multicast-management {
        container multicast-management {
            description "Enter the multicast-management context";

            list multicast-reporting-destination {
                key "name";
                description "Enter the multicast-reporting-destination list instance";

                leaf name {
                    type types-sros:named-item;
                    description "Destination name for multicast reporting";
                }

                container statistics {

                    leaf frames-sent {
                        type yang:counter32;
                        description "The number of frames sent to this multicast reporting destination.";
                    }

                    leaf frames-lost {
                        type yang:counter32;
                        description "The number of frames lost for this multicast reporting destination.";
                    }

                    leaf records-sent {
                        type yang:counter32;
                        description "The number of records sent to this multicast reporting destination.";
                    }

                    leaf records-lost {
                        type yang:counter32;
                        description "The number of records lost to this multicast reporting destination.";
                    }

                } // container statistics

            } // list multicast-reporting-destination

            container chassis-level {
                description "Enter the chassis-level context";

                leaf mmrp-oper-mode {
                    type boolean;
                    description "Enable/Disable managing MMRP traffic by IMPM.";
                }

                leaf mcast-plane-total-capacity {
                    type uint32;
                    description "The total bandwidth of the chassis forwarding plane currently in use";
                }

            } // container chassis-level

        } // container multicast-management

    } // grouping state-mcast-mgmt-multicast-management

}
