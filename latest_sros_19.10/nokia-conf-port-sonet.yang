submodule nokia-conf-port-sonet {

    yang-version "1.1";

    belongs-to nokia-conf { prefix "conf"; }

    import ietf-yang-types                { prefix "yang"; }
    import nokia-sros-yang-extensions     { prefix "sros-ext"; }
    import nokia-types-port               { prefix "types-port"; }
    import nokia-types-qos                { prefix "types-qos"; }
    import nokia-types-sros               { prefix "types-sros"; }
    import nokia-types-subscriber-mgmt    { prefix "types-submgt"; }

    include nokia-conf-groups;
    include nokia-conf-log;
    include nokia-conf-qos;

    sros-ext:sros-major-release "rel19";

    organization "Nokia";

    contact
        "Nokia SR OS Support
         Web: <http://www.nokia.com>";

    description
        "Nokia YANG Data model to configure SONET/SDH ports on SR OS based routers.

         Copyright 2016 Nokia. All rights reserved. Reproduction of this document
         is authorized on the condition that the foregoing copyright notice is included.

         This nokia-conf-port-sonet YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-12-20";

    grouping conf-port-sonet-sonet-sdh {
        container sonet-sdh {
            description "Enter the sonet-sdh context";

            leaf clock-source {
                type enumeration {
                    enum "loop-timed"                   { value 1; }
                    enum "node-timed"                   { value 2; }
                }
                description "Configure the clock for transmitted data.";
            }

            leaf framing {
                type enumeration {
                    enum "sonet"                        { value 2; }
                    enum "sdh"                          { value 3; }
                }
                sros-ext:immutable;
                default "sonet";
                description "SONET or SDH framing";
            }

            leaf loopback {
                type enumeration {
                    enum "line"                         { value 1; }
                    enum "internal"                     { value 2; }
                }
                description "Loopback to activate on SONET port";
            }

            leaf reset-port-on-path-down {
                type boolean;
                default "false";
                description "Reset port when path goes operationally down";
            }

            leaf sd-threshold {
                type uint32 {
                    range "3..9";
                }
                default "6";
                description "Threshold for line signal failure BER";
            }

            leaf sf-threshold {
                type uint32 {
                    range "3..6";
                }
                default "3";
                description "Threshold for line signal failure BER";
            }

            leaf single-fiber {
                type boolean;
                default "false";
                description "Allow packet gathering and redirection of IP packets from a single fiber (RX) port";
            }

            leaf speed {
                type enumeration {
                    enum "oc3"                          { value 1; }
                    enum "oc12"                         { value 2; }
                    enum "oc48"                         { value 3; }
                    enum "oc192"                        { value 4; }
                    enum "oc768"                        { value 5; }
                    enum "oc1"                          { value 6; }
                }
                sros-ext:immutable;
                description "Configure the speed of a SONET/SDH port to be either OC3 or OC12.";
            }

            leaf suppress-low-order-alarms {
                type boolean;
                default "false";
                description "Suppress low order alarms";
            }

            leaf tx-dus {
                type boolean;
                default "false";
                description "Enable/disable the forced transmit 0xF (dus/dnu) in S1 overhead byte.";
            }

            leaf-list apply-groups {
                type leafref {
                    path "../../../groups/group/name";
                }
                max-elements 8;
                ordered-by user;
                description "Apply a configuration group at this level";
            }

            container hold-time {
                description "Enter the hold-time context";

                leaf up {
                    type uint32 {
                        range "0..100";
                    }
                    units "deciseconds";
                    default "5";
                    description "Configure the hold timer for link up event dampening.";
                }

                leaf down {
                    type uint32 {
                        range "0..100";
                    }
                    units "deciseconds";
                    description "Configure the hold timer for link down event dampening.";
                }

            } // container hold-time

            container report-alarm {
                description "Enter the report-alarm context";

                leaf loc {
                    type boolean;
                    default "true";
                    description "Report alarm for a loss of clock that causes the port to shut down";
                }

                leaf lais {
                    type boolean;
                    default "false";
                    description "Report Line Indication Signal Errors alarm";
                }

                leaf lrdi {
                    type boolean;
                    default "true";
                    description "Report Line Remote Defect Indication Errors alarm";
                }

                leaf ss1f {
                    type boolean;
                    default "false";
                    description "Report alarm for section synchronization failure";
                }

                leaf lb2er-sd {
                    type boolean;
                    default "false";
                    description "Report alarm for line signal degradation BER (bit interleaved parity) errors";
                }

                leaf lb2er-sf {
                    type boolean;
                    default "true";
                    description "Report alarm line signal failure BER errors";
                }

                leaf slof {
                    type boolean;
                    default "true";
                    description "Report alarm for section loss of frame errors";
                }

                leaf slos {
                    type boolean;
                    default "true";
                    description "Report alarm for section loss of signal error on the transmit side";
                }

                leaf lrei {
                    type boolean;
                    default "false";
                    description "Report alarm for a line error condition";
                }

            } // container report-alarm

            container section-trace {
                description "Enter the section-trace context";

                choice section-trace {
                    default "byte";
                    case increment-z0 {

                        leaf increment-z0 {
                            type empty;
                            description "Set the j0 byte to 0x01 and increment z0 byte.";
                        }

                    }
                    case byte {

                        leaf byte {
                            type string {
                                length "1..4";
                            }
                            default "1";
                            description "Set j0 byte to the first octet of the j0 string and the z0 byte to 0xcc.";
                        }

                    }
                    case string {

                        leaf string {
                            type string {
                                length "0..16";
                            }
                            description "Set j0 byte to the string and the z0 byte to 0xcc.";
                        }

                    }
                }
            } // container section-trace

        } // container sonet-sdh

    } // grouping conf-port-sonet-sonet-sdh

}
