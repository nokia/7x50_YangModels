submodule nokia-conf-router-ospf {

    yang-version "1.1";

    belongs-to nokia-conf { prefix "conf"; }

    import nokia-sros-yang-extensions     { prefix "sros-ext"; }
    import nokia-types-igp                { prefix "types-igp"; }
    import nokia-types-ospf               { prefix "types-ospf"; }
    import nokia-types-router             { prefix "types-router"; }
    import nokia-types-sros               { prefix "types-sros"; }

    include nokia-conf-groups;
    include nokia-conf-policy-options;
    include nokia-conf-router;
    include nokia-conf-routing-options;
    include nokia-conf-system;
    include nokia-conf-system-security;

    sros-ext:sros-major-release "rel19";

    organization "Nokia";

    contact
        "Nokia SR OS Support
         Web: <http://www.nokia.com>";

    description
        "Nokia YANG Data model to configure router ospf protocol attributes on SR OS based routers.

         Copyright 2016 Nokia. All rights reserved. Reproduction of this document
         is authorized on the condition that the foregoing copyright notice is included.

         This nokia-conf-router-ospf YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-08-31";

    grouping conf-router-ospf {
        list ospf {
            key "ospf-instance";
            max-elements 32;
            description "Enter the ospf list instance";

            leaf ospf-instance {
                type uint32 {
                    range "0..31";
                }
                description "Value for the integrated OSPF instance";
            }

            leaf admin-state {
                type types-sros:admin-state;
                default "disable";
                description "Administrative state of the OSPF instance";
            }

            leaf router-id {
                type types-igp:router-id;
                sros-ext:auto-restart-to-modify;
                description "Unique router ID for the OSPF instance";
            }

            leaf advertise-router-capability {
                type types-ospf:advertise-router-capability-type;
                default "false";
                description "Allow router advertisement capabilities";
            }

            leaf advertise-tunnel-link {
                type boolean;
                default "false";
                description "Allow router advertisement capabilities";
            }

            leaf external-preference {
                type int32 {
                    range "1..255";
                }
                default "150";
                description "Preference for OSPF external routes";
            }

            leaf-list export-policy {
                type leafref {
                    path "../../../policy-options/policy-statement/name";
                }
                max-elements 5;
                ordered-by user;
                description "Configure names of export policies to be used for determining which routes are exported from the routing table to this IGP.";
            }

            leaf-list import-policy {
                type leafref {
                    path "../../../policy-options/policy-statement/name";
                }
                max-elements 5;
                ordered-by user;
                description "Configure names of import policies to be used for determining which routes are imported from this IGP to the routing table.";
            }

            leaf ldp-over-rsvp {
                type boolean;
                default "false";
                description "Allow LSP over RSVP in this OSPF instance";
            }

            leaf ldp-sync {
                type boolean;
                default "true";
                description "Use IGP-LDP synchronization feature on all interfaces participating in routing protocol";
            }

            leaf multicast-import {
                type boolean;
                default "false";
                description "Submit routes into the multicast Route Table Manager";
            }

            leaf overload-include-ext-1 {
                type boolean;
                default "false";
                description "Advertise external type-1 routes with maximum metric value in cases of overload";
            }

            leaf overload-include-ext-2 {
                type boolean;
                default "false";
                description "Advertise external type-2 routes with maximum metric value in cases of overload";
            }

            leaf overload-include-stub {
                type boolean;
                default "false";
                description "Advertise all stub interfaces with maximum metric value in cases of overload";
            }

            leaf overload {
                type boolean;
                default "false";
                description "Change overload state of the local router to appear to be overloaded";
            }

            leaf preference {
                type int32 {
                    range "1..255";
                }
                default "10";
                description "Preference for OSPF internal routes";
            }

            leaf reference-bandwidth {
                type types-sros:reference-bandwidth-ext;
                units "kilobps";
                default "100000000";
                description "Bandwidth to reference the default costing of interfaces";
            }

            leaf traffic-engineering {
                type boolean;
                default "false";
                description "Calculate traffic engineering route";
            }

            leaf unicast-import {
                type boolean;
                default "true";
                description "Submit routes into the unicast Route Table Manager";
            }

            leaf compatible-rfc1583 {
                type boolean;
                default "true";
                description "OSPF summary and external route calculations";
            }

            leaf multi-instance {
                type boolean;
                default "false";
                description "Enable/disable OSPF Multi Instance Extensions";
            }

            leaf-list apply-groups {
                type leafref {
                    path "../../../groups/group/name";
                }
                max-elements 8;
                ordered-by user;
                description "Apply a configuration group at this level";
            }

            container external-db-overflow {
                presence "Limit on number of AS-external-LSAs in LSDB and wait time before processing these if limit is exceeded";
                description "Enter the external-db-overflow context";

                leaf limit {
                    type uint32 {
                        range "0..2147483647";
                    }
                    default "0";
                    description "Number of external LSA at which overload is triggered";
                }

                leaf interval {
                    type uint32 {
                        range "0..2147483647";
                    }
                    units "seconds";
                    default "0";
                    description "Time during which the router operates in overload";
                }

            } // container external-db-overflow

            container export-limit {
                presence "Maximum number of routes (prefixes) that can be exported into OSPF from the route table";
                description "Enter the export-limit context";

                leaf number {
                    type uint32 {
                        range "1..max";
                    }
                    mandatory true;
                    description "Maximum number of routes or prefixes to be exported into IGP instance from route table";
                }

                leaf log-percent {
                    type uint32 {
                        range "1..100";
                    }
                    description "Export limit at which warning a log message and SNMP notification are sent";
                }

            } // container export-limit

            container overload-on-boot {
                presence "Configure the local router so that it appears to be overloaded at boot up.";
                description "Enter the overload-on-boot context";

                leaf timeout {
                    type uint32 {
                        range "1..1800";
                    }
                    units "seconds";
                    description "Time during which the router operates in overload state before reestablishing normal operations";
                }

            } // container overload-on-boot

            container rib-priority {
                description "Enter the rib-priority context";

                container high {
                    description "Enter the high context";

                    leaf prefix-list {
                        type leafref {
                            path "../../../../../policy-options/prefix-list/name";
                        }
                        description "List used to select routes processed at higher priority through OSPF route calculation process";
                    }

                } // container high

            } // container rib-priority

            container rtr-adv-lsa-limit {
                presence "Configure maximum number of LSA's we accept from 1 advertising router";
                description "Enter the rtr-adv-lsa-limit context";

                leaf max-lsa-count {
                    type uint32 {
                        range "1..max";
                    }
                    mandatory true;
                    description "Maximum number of LSAs allowed to be advertised by one router";
                }

                leaf log-only {
                    type boolean;
                    default "false";
                    description "Log the event without triggering overload";
                }

                leaf warning-threshold {
                    type uint32 {
                        range "0..100";
                    }
                    units "percent";
                    default "0";
                    description "Percentage of the maximum LSA count at which a warning is given";
                }

                leaf overload-timeout {
                    type types-igp:overload-timeout;
                    default "forever";
                    description "Maximum timeout for overload when the maximum LSA count is reached";
                }

            } // container rtr-adv-lsa-limit

            container graceful-restart {
                presence "Enable/disable graceful-restart for OSPF";
                description "Enter the graceful-restart context";

                leaf helper-mode {
                    type boolean;
                    default "true";
                    description "Enable graceful restart helper for OSPF";
                }

                leaf strict-lsa-checking {
                    type boolean;
                    default "true";
                    description "Perform strict LSA checking during graceful restart helper";
                }

            } // container graceful-restart

            container timers {
                description "Enter the timers context";

                leaf incremental-spf-wait {
                    type uint32 {
                        range "0..1000";
                    }
                    units "milliseconds";
                    default "1000";
                    description "Delay time before an incremental SPF calculation is started";
                }

                leaf lsa-accumulate {
                    type uint32 {
                        range "0..1000";
                    }
                    units "milliseconds";
                    default "1000";
                    description "Delay time for accumulating multiple LSAs before advertising them to neighbors";
                }

                leaf lsa-arrival {
                    type uint32 {
                        range "0..600000";
                    }
                    units "milliseconds";
                    default "1000";
                    description "Minimum delay between receipt of the same LSAs arriving from neighbors";
                }

                leaf redistribute-delay {
                    type uint32 {
                        range "0..1000";
                    }
                    units "milliseconds";
                    default "1000";
                    description "Hold down timer for external routes that are redistributed in OSPF";
                }

                container lsa-generate {
                    description "Enter the lsa-generate context";

                    leaf max-lsa-wait {
                        type uint32 {
                            range "10..600000";
                        }
                        units "milliseconds";
                        default "5000";
                        description "Maximum time between two consecutive occurrences of an LSA being generated";
                    }

                    leaf lsa-initial-wait {
                        type uint32 {
                            range "10..600000";
                        }
                        units "milliseconds";
                        default "5000";
                        description "First waiting period between link state advertisements LSA originates";
                    }

                    leaf lsa-second-wait {
                        type uint32 {
                            range "10..600000";
                        }
                        units "milliseconds";
                        default "5000";
                        description "Hold time between the first and second LSA generation";
                    }

                } // container lsa-generate

                container spf-wait {
                    description "Enter the spf-wait context";

                    leaf spf-max-wait {
                        type uint32 {
                            range "10..120000";
                        }
                        units "milliseconds";
                        default "10000";
                        description "Maximum interval between two consecutive SPF calculations";
                    }

                    leaf spf-initial-wait {
                        type uint32 {
                            range "10..100000";
                        }
                        units "milliseconds";
                        default "1000";
                        description "Initial SPF calculation delay after a topology change";
                    }

                    leaf spf-second-wait {
                        type uint32 {
                            range "10..100000";
                        }
                        units "milliseconds";
                        default "1000";
                        description "Hold time between the first and second SPF calculation";
                    }

                } // container spf-wait

            } // container timers

            container loopfree-alternate {
                presence "Enable/disable fast re-route capability for OSPF";
                description "Enter the loopfree-alternate context";

                container exclude {
                    description "Enter the exclude context";

                    leaf-list prefix-policy {
                        type leafref {
                            path "../../../../../policy-options/policy-statement/name";
                        }
                        max-elements 5;
                        ordered-by user;
                        description "Loopfree Alternative (LFA) exclude policies from which prefixes are excluded. Prefixes excluded from LFA this way will not be used in the LFA calculation, regardless of their priority.";
                    }

                } // container exclude

                container remote-lfa {
                    presence "Enable/disable Remote LFA";
                    description "Enter the remote-lfa context";

                    leaf max-pq-cost {
                        type uint32;
                        default "65535";
                        description "Maximum cost of a destination node during reverse SPF calculation";
                    }

                    container node-protect {
                        presence "Configure node-protection support in this OSPF instance.";
                        description "Enter the node-protect context";

                        leaf max-pq-nodes {
                            type uint32 {
                                range "1..32";
                            }
                            default "16";
                            description "Specifies the maximum number of PQ nodes.";
                        }

                    } // container node-protect

                } // container remote-lfa

                container ti-lfa {
                    presence "Enable/disable topology Independent LFA";
                    description "Enter the ti-lfa context";

                    leaf max-sr-frr-labels {
                        type uint32 {
                            range "0..3";
                        }
                        default "2";
                        description "Maximum number of labels that TI-LFA backup next hop can use";
                    }

                    container node-protect {
                        presence "Configure node-protection support in this OSPF instance.";
                        description "Enter the node-protect context";

                    } // container node-protect

                } // container ti-lfa

            } // container loopfree-alternate

            container database-export {
                presence "Enable/disable database export";
                description "Enter the database-export context";

                leaf igp-identifier {
                    type uint64;
                    description "Unique identifier for the IGP instance in the BGP-LS NLRI";
                }

                container bgp-ls-identifier {
                    presence "Enable/disable IGP instance-identifier";
                    description "Enter the bgp-ls-identifier context";

                    leaf value {
                        type uint32;
                        default "0";
                        description "BGP-LS identifier that is sent in the BGP-LS NLRI";
                    }

                } // container bgp-ls-identifier

            } // container database-export

            container asbr {
                presence "Configure the router as an ASBR (Autonomous System Boundary Router)";
                description "Enter the asbr context";

                leaf trace-path {
                    type union {
                        type int32 {
                            range "0..31";
                        }
                        type enumeration {
                            enum "none"                         { value -1; }
                        }
                    }
                    default "none";
                    description "Domain identity";
                }

            } // container asbr

            container entropy-label {
                description "Enter the entropy-label context";

                leaf override-tunnel-elc {
                    type boolean;
                    default "false";
                    description "Received entropy label capability advertisement to override";
                }

            } // container entropy-label

            container segment-routing {
                description "Enter the segment-routing context";

                leaf admin-state {
                    type types-sros:admin-state;
                    default "disable";
                    description "Administrative state of segment routing";
                }

                leaf adj-sid-hold {
                    type types-igp:adj-sid-hold-type;
                    units "seconds";
                    default "15";
                    description "Adjacency SID hold time";
                }

                leaf entropy-label {
                    type boolean;
                    default "true";
                    description "Entropy label capability";
                }

                leaf export-tunnel-table {
                    type types-igp:export-tunnel-table-type;
                    description "Export tunnel table";
                }

                leaf srlb {
                    type leafref {
                        path "../../../mpls-labels/reserved-label-block/label-block-name";
                    }
                    description "Segment routing local block";
                }

                leaf tunnel-mtu {
                    type types-router:ip-mtu-ext;
                    description "Tunnel MTU size";
                }

                leaf tunnel-table-pref {
                    type uint32 {
                        range "1..255";
                    }
                    default "10";
                    description "Preference of SR tunnels created by the IGP instance";
                }

                leaf-list apply-groups {
                    type leafref {
                        path "../../../../groups/group/name";
                    }
                    max-elements 8;
                    ordered-by user;
                    description "Apply a configuration group at this level";
                }

                container prefix-sid-range {
                    presence "Configure prefix-sid-range";
                    description "Enter the prefix-sid-range context";

                    choice type {
                        case global {

                            leaf global {
                                type empty;
                                description "Use global SR range";
                            }

                        }
                        case local {

                            leaf start-label {
                                type uint32 {
                                    range "0..524287";
                                }
                                sros-ext:auto-restart-to-modify;
                                default "0";
                                description "Value for the local label starting offset";
                            }

                            leaf max-index {
                                type uint32 {
                                    range "0..524287";
                                }
                                sros-ext:auto-restart-to-modify;
                                default "1";
                                description "Maximum local SID index";
                            }

                        }
                    }
                } // container prefix-sid-range

                container backup-node-sid {
                    presence "Configure backup-node-sid";
                    description "Enter the backup-node-sid context";

                    leaf ip-prefix {
                        type types-sros:ipv4-unicast-prefix;
                        description "IP prefix and prefix length for the backup-node-sid";
                    }

                    choice type {
                        case label {

                            leaf label {
                                type int64 {
                                    range "1..4294967295";
                                }
                                description "Specifies IPvX node SID label for this interface.";
                            }

                        }
                        case index {

                            leaf index {
                                type int64 {
                                    range "0..4294967295";
                                }
                                description "IPvX node SID index for this interface";
                            }

                        }
                    }
                } // container backup-node-sid

                container egress-statistics {
                    description "Enter the egress-statistics context";

                    leaf adj-set {
                        type boolean;
                        default "false";
                        description "Enable statistics on Adjacency Sets";
                    }

                    leaf adj-sid {
                        type boolean;
                        default "false";
                        description "Enable statistics on Adjacency SIDs";
                    }

                    leaf node-sid {
                        type boolean;
                        default "false";
                        description "Enable statistics on Node SIDs";
                    }

                } // container egress-statistics

                container ingress-statistics {
                    description "Enter the ingress-statistics context";

                    leaf adj-set {
                        type boolean;
                        default "false";
                        description "Enable statistics on Adjacency Sets";
                    }

                    leaf adj-sid {
                        type boolean;
                        default "false";
                        description "Enable statistics on Adjacency SIDs";
                    }

                    leaf node-sid {
                        type boolean;
                        default "false";
                        description "Enable statistics on Node SIDs";
                    }

                } // container ingress-statistics

                list adjacency-set {
                    key "id";
                    description "Enter the adjacency-set list instance";

                    leaf id {
                        type uint32 {
                            range "1..max";
                        }
                        description "Non-zero identifier for a given adjacency set";
                    }

                    leaf parallel {
                        type boolean;
                        default "true";
                        description "Require all members of the adjacency set to terminate on the same neighboring node";
                    }

                    leaf advertise {
                        type boolean;
                        default "true";
                        description "Advertise the adjacency set when all links terminate on the same neighboring node";
                    }

                    leaf-list apply-groups {
                        type leafref {
                            path "../../../../../groups/group/name";
                        }
                        max-elements 8;
                        ordered-by user;
                        description "Apply a configuration group at this level";
                    }

                    container sid {
                        presence "Assign a static SID value to this adj-set";
                        description "Enter the sid context";

                        choice type {
                            case label {

                                leaf label {
                                    type int64 {
                                        range "1..1048575";
                                    }
                                    description "Adjacency SID";
                                }

                            }
                        }
                    } // container sid

                } // list adjacency-set

                container mapping-server {
                    description "Enter the mapping-server context";

                    leaf admin-state {
                        type types-sros:admin-state;
                        default "disable";
                        description "Administrative state of the OSPF segment routing mapping server";
                    }

                    list node-sid-map {
                        key "sid-index";
                        description "Enter the node-sid-map list instance";

                        leaf sid-index {
                            type uint32;
                            description "Start SID index for the node SID mapping";
                        }

                        leaf range {
                            type uint32 {
                                range "1..65535";
                            }
                            sros-ext:immutable;
                            default "1";
                            description "Number of prefixes to be mapped by the Extended Range Prefix TLV";
                        }

                        leaf ip-prefix {
                            type types-sros:ipv4-prefix;
                            sros-ext:immutable;
                            mandatory true;
                            description "Starting prefix of the mapping";
                        }

                        leaf-list apply-groups {
                            type leafref {
                                path "../../../../../../groups/group/name";
                            }
                            max-elements 8;
                            ordered-by user;
                            description "Apply a configuration group at this level";
                        }

                        container scope {
                            description "Enter the scope context";

                            choice scope {
                                default "as";
                                case area {

                                    leaf area {
                                        type leafref {
                                            path "../../../../../area/area-id";
                                        }
                                        description "Area ID in which the advertise Extended Range TLV is advertised";
                                    }

                                }
                                case as {

                                    leaf as {
                                        type empty;
                                        description "Advertise Extended Range TLV in whole autonomous system";
                                    }

                                }
                            }
                        } // container scope

                    } // list node-sid-map

                } // container mapping-server

            } // container segment-routing

            container igp-shortcut {
                description "Enter the igp-shortcut context";

                leaf admin-state {
                    type types-sros:admin-state;
                    default "disable";
                    description "Administrative state of the IGP shortcuts";
                }

                leaf-list apply-groups {
                    type leafref {
                        path "../../../../groups/group/name";
                    }
                    max-elements 8;
                    ordered-by user;
                    description "Apply a configuration group at this level";
                }

                container tunnel-next-hop {
                    description "Enter the tunnel-next-hop context";

                    list family {
                        key "family-type";
                        description "Enter the family list instance";

                        leaf family-type {
                            type types-igp:tunn-next-hop-family-type-v4-only;
                            description "Address family type for tunnel next-hop";
                        }

                        leaf resolution {
                            type types-sros:resolution-type;
                            description "Resolution state for IGP shortcut tunnels";
                        }

                        leaf-list apply-groups {
                            type leafref {
                                path "../../../../../../groups/group/name";
                            }
                            max-elements 8;
                            ordered-by user;
                            description "Apply a configuration group at this level";
                        }

                        container resolution-filter {
                            description "Enter the resolution-filter context";

                            leaf rsvp {
                                type boolean;
                                default "false";
                                description "Use RSVP tunneling for next-hop resolution";
                            }

                            leaf sr-te {
                                type boolean;
                                default "false";
                                description "Use SR-TE tunneling for next-hop resolution";
                            }

                        } // container resolution-filter

                    } // list family

                } // container tunnel-next-hop

            } // container igp-shortcut

            list area {
                key "area-id";
                description "Enter the area list instance";

                leaf area-id {
                    type types-sros:ipv4-address;
                    description "Area-ID attribute";
                }

                leaf advertise-router-capability {
                    type boolean;
                    default "true";
                    description "Allow router advertisement capabilities";
                }

                leaf blackhole-aggregate {
                    type boolean;
                    default "true";
                    description "Install a low priority blackhole route to avoid loops";
                }

                leaf-list export-policy {
                    type leafref {
                        path "../../../../policy-options/policy-statement/name";
                    }
                    max-elements 5;
                    ordered-by user;
                    description "Route that is exported as Type 3 Summary-LSAs or OSPFv3 Inter-Area-Prefix-LSA between areas";
                }

                leaf-list import-policy {
                    type leafref {
                        path "../../../../policy-options/policy-statement/name";
                    }
                    max-elements 5;
                    ordered-by user;
                    description "Route that is imported as summary type 3/inter-area-prefix-LSA from another area into this area";
                }

                leaf loopfree-alternate-exclude {
                    type boolean;
                    default "false";
                    description "Exclude specific interface or all interfaces participating in all OSPF areas in SPF LFA computation";
                }

                leaf database-export-exclude {
                    type boolean;
                    default "false";
                    description "Exclude IGP link-state information of OSPF area from being exported into extended TE-DB";
                }

                leaf-list apply-groups {
                    type leafref {
                        path "../../../../groups/group/name";
                    }
                    max-elements 8;
                    ordered-by user;
                    description "Apply a configuration group at this level";
                }

                container stub {
                    presence "Configure this area as an OSPF stub area";
                    description "Enter the stub context";

                    leaf default-metric {
                        type uint32 {
                            range "1..16777214";
                        }
                        default "1";
                        description "Metric used by the ABR for the default route into the stub area";
                    }

                    leaf summaries {
                        type boolean;
                        default "true";
                        description "Send summary (Type 3) LSAs into the stub area on an ABR";
                    }

                } // container stub

                container nssa {
                    presence "Configure this area as an OSPF Not So Stubby Area (NSSA)";
                    description "Enter the nssa context";

                    leaf redistribute-external {
                        type boolean;
                        default "true";
                        description "Redistribute external routes into the NSSA";
                    }

                    leaf summaries {
                        type boolean;
                        default "true";
                        description "Send summary (Type 3) LSAs into the NSSA on an ABR";
                    }

                    list area-range {
                        key "ip-prefix-mask";
                        description "Enter the area-range list instance";

                        leaf ip-prefix-mask {
                            type types-sros:ipv4-unicast-prefix;
                            description "ip-prefix a.b.c.d (host bits must be 0) mask [0..32]";
                        }

                        leaf advertise {
                            type boolean;
                            default "true";
                            description "Advertise summarized range of addresses to other areas";
                        }

                        leaf-list apply-groups {
                            type leafref {
                                path "../../../../../../groups/group/name";
                            }
                            max-elements 8;
                            ordered-by user;
                            description "Apply a configuration group at this level";
                        }

                    } // list area-range

                    container originate-default-route {
                        presence "Enable/disable generation of default route and its LSA type (3 or 7) into the NSSA";
                        description "Enter the originate-default-route context";

                        leaf type-nssa {
                            type boolean;
                            default "false";
                            description "Generate a default route using NSSA-LSA type";
                        }

                        leaf adjacency-check {
                            type boolean;
                            default "true";
                            description "Default route to remove if there is no adjacency";
                        }

                    } // container originate-default-route

                } // container nssa

                list area-range {
                    key "ip-prefix-mask";
                    description "Enter the area-range list instance";

                    leaf ip-prefix-mask {
                        type types-sros:ipv4-unicast-prefix;
                        description "ip-prefix a.b.c.d (host bits must be 0) mask [0..32]";
                    }

                    leaf advertise {
                        type boolean;
                        default "true";
                        description "Advertise summarized range of addresses to other areas";
                    }

                    leaf-list apply-groups {
                        type leafref {
                            path "../../../../../groups/group/name";
                        }
                        max-elements 8;
                        ordered-by user;
                        description "Apply a configuration group at this level";
                    }

                } // list area-range

                list interface {
                    key "interface-name";
                    description "Enter the interface list instance";

                    leaf interface-name {
                        type types-sros:interface-name;
                        description "Router interface name";
                    }

                    leaf advertise-router-capability {
                        type boolean;
                        default "true";
                        description "Allow router advertisement capabilities";
                    }

                    leaf advertise-subnet {
                        type boolean;
                        default "true";
                        description "Advertise point-to-point interfaces as subnet routes";
                    }

                    leaf interface-type {
                        type types-ospf:interface-type;
                        sros-ext:immutable;
                        description "Interface type to broadcast or point-to-point";
                    }

                    leaf lsa-filter-out {
                        type types-ospf:lsa-filter-out;
                        default "none";
                        description "LSA flooding reduction";
                    }

                    leaf metric {
                        type uint32 {
                            range "1..65535";
                        }
                        description "Explicit route cost metric that is applied to the interface";
                    }

                    leaf mtu {
                        type types-router:ip-mtu-ext;
                        description "MTU for the OSPF to use on the interface";
                    }

                    leaf passive {
                        type boolean;
                        description "Allow interface to be advertised as an OSPF interface without running the OSPF protocol";
                    }

                    leaf poll-interval {
                        type uint32;
                        units "seconds";
                        default "120";
                        description "Time between two Hello packets to a non-adjacent OSPF NBMA neighbor";
                    }

                    leaf priority {
                        type uint16 {
                            range "0..255";
                        }
                        default "1";
                        description "Priority of the interface to apply in the designated router election on the subnet";
                    }

                    leaf rib-priority {
                        type types-ospf:rib-priority;
                        description "RIB priority for OSPF";
                    }

                    leaf admin-state {
                        type types-sros:admin-state;
                        default "enable";
                        description "Administrative state of the OSPF";
                    }

                    leaf hello-interval {
                        type uint32 {
                            range "1..65535";
                        }
                        units "seconds";
                        default "10";
                        description "Time between OSPF Hellos of this interface";
                    }

                    leaf dead-interval {
                        type uint32 {
                            range "2..65535";
                        }
                        units "seconds";
                        default "40";
                        description "Time OSPF waits without receiving Hello packets before declaring a neighbor down";
                    }

                    leaf retransmit-interval {
                        type uint32 {
                            range "1..1800";
                        }
                        units "seconds";
                        default "5";
                        description "Time before OSPF retransmits an unacknowledged LSA to a neighbor";
                    }

                    leaf transit-delay {
                        type uint32 {
                            range "1..1800";
                        }
                        units "seconds";
                        default "1";
                        description "Time required to transmit an LSA on the interface, virtual link, or sham link";
                    }

                    leaf authentication-keychain {
                        type leafref {
                            path "../../../../../system/security/keychains/keychain/keychain-name";
                        }
                        description "Configure TCP authentication keychain to use for the session";
                    }

                    leaf authentication-key {
                        type types-sros:encrypted-leaf {
                            length "1..38";
                        }
                        description "Authentication key";
                    }

                    leaf authentication-type {
                        type types-ospf:authentication-type;
                        description "Authentication type used on OSPF interface";
                    }

                    leaf sid-protection {
                        type boolean;
                        default "true";
                        description "Allow adjacency SID protection by LFA and remote LFA";
                    }

                    leaf-list apply-groups {
                        type leafref {
                            path "../../../../../groups/group/name";
                        }
                        max-elements 8;
                        ordered-by user;
                        description "Apply a configuration group at this level";
                    }

                    container bfd-liveness {
                        presence "Enable BFD";
                        description "Enter the bfd-liveness context";

                        leaf remain-down-on-failure {
                            type boolean;
                            default "false";
                            description "Force adjacency down on BFD failure and remain down until BFD session returns";
                        }

                    } // container bfd-liveness

                    container loopfree-alternate {
                        description "Enter the loopfree-alternate context";

                        leaf exclude {
                            type boolean;
                            default "false";
                            description "Enable/disable fast re-route capability for OSPF at interface level (only valid for primary interface)";
                        }

                        container policy-map {
                            presence "Configure a route-next-hop template";
                            description "Enter the policy-map context";

                            leaf route-nh-template {
                                type leafref {
                                    path "../../../../../../../routing-options/route-next-hop-policy/template/template-name";
                                }
                                mandatory true;
                                description "Route next hop policy template that is applied to interface";
                            }

                        } // container policy-map

                    } // container loopfree-alternate

                    container node-sid {
                        presence "Configure node-sid";
                        description "Enter the node-sid context";

                        leaf clear-n-flag {
                            type boolean;
                            default "false";
                            description "Specifies whether the node-sid flag (N-flag) should be cleared.";
                        }

                        choice type {
                            case label {

                                leaf label {
                                    type int64 {
                                        range "1..4294967295";
                                    }
                                    description "Specifies IPvX node SID label for this interface.";
                                }

                            }
                            case index {

                                leaf index {
                                    type int64 {
                                        range "0..4294967295";
                                    }
                                    description "IPvX node SID index for this interface";
                                }

                            }
                        }
                    } // container node-sid

                    container adjacency-sid {
                        presence "Configure static adjacency-sid";
                        description "Enter the adjacency-sid context";

                        choice type {
                            case label {

                                leaf label {
                                    type int64 {
                                        range "1..1048575";
                                    }
                                    description "Adjacency SID";
                                }

                            }
                        }
                    } // container adjacency-sid

                    list message-digest-key {
                        key "key-id";
                        description "Enter the message-digest-key list instance";

                        leaf key-id {
                            type uint16 {
                                range "1..255";
                            }
                            description "Message digest index";
                        }

                        leaf md5 {
                            type types-sros:encrypted-leaf {
                                length "1..51";
                            }
                            mandatory true;
                            description "MD5 hash key";
                        }

                        leaf-list apply-groups {
                            type leafref {
                                path "../../../../../../groups/group/name";
                            }
                            max-elements 8;
                            ordered-by user;
                            description "Apply a configuration group at this level";
                        }

                    } // list message-digest-key

                    list neighbor {
                        key "address";
                        description "Add a list entry for neighbor";

                        leaf address {
                            type types-sros:ipv4-unicast-address;
                            description "Neighbor address";
                        }

                    } // list neighbor

                    list adjacency-set {
                        key "id";
                        max-elements 1024;
                        description "Add a list entry for adjacency-set";

                        leaf id {
                            type leafref {
                                path "../../../../segment-routing/adjacency-set/id";
                            }
                            description "Adjacency set identity";
                        }

                    } // list adjacency-set

                } // list interface

                list virtual-link {
                    key "router-id transit-area";
                    description "Enter the virtual-link list instance";

                    leaf router-id {
                        type types-sros:ipv4-address;
                        description "Router identity of the virtual link neighbor";
                    }

                    leaf transit-area {
                        type leafref {
                            path "../../area-id";
                        }
                        description "Transit area that links backbone area to area without physical connection with the backbone";
                    }

                    leaf admin-state {
                        type types-sros:admin-state;
                        default "enable";
                        description "Administrative state of the OSPF";
                    }

                    leaf hello-interval {
                        type uint32 {
                            range "1..65535";
                        }
                        units "seconds";
                        default "10";
                        description "Time between OSPF Hellos of this interface";
                    }

                    leaf dead-interval {
                        type uint32 {
                            range "2..65535";
                        }
                        units "seconds";
                        default "60";
                        description "Time OSPF waits without receiving Hello packets before declaring a neighbor down";
                    }

                    leaf retransmit-interval {
                        type uint32 {
                            range "1..1800";
                        }
                        units "seconds";
                        default "5";
                        description "Time before OSPF retransmits an unacknowledged LSA to a neighbor";
                    }

                    leaf transit-delay {
                        type uint32 {
                            range "1..1800";
                        }
                        units "seconds";
                        default "1";
                        description "Time required to transmit an LSA on the interface, virtual link, or sham link";
                    }

                    leaf authentication-keychain {
                        type leafref {
                            path "../../../../../system/security/keychains/keychain/keychain-name";
                        }
                        description "Configure TCP authentication keychain to use for the session";
                    }

                    leaf authentication-key {
                        type types-sros:encrypted-leaf {
                            length "1..38";
                        }
                        description "Authentication key";
                    }

                    leaf authentication-type {
                        type types-ospf:authentication-type;
                        description "Authentication type used on OSPF interface";
                    }

                    leaf-list apply-groups {
                        type leafref {
                            path "../../../../../groups/group/name";
                        }
                        max-elements 8;
                        ordered-by user;
                        description "Apply a configuration group at this level";
                    }

                    list message-digest-key {
                        key "key-id";
                        description "Enter the message-digest-key list instance";

                        leaf key-id {
                            type uint16 {
                                range "1..255";
                            }
                            description "Message digest index";
                        }

                        leaf md5 {
                            type types-sros:encrypted-leaf {
                                length "1..51";
                            }
                            mandatory true;
                            description "key - [16 chars max] hash/hash2-key - [44 chars max] (for hash scheme)";
                        }

                        leaf-list apply-groups {
                            type leafref {
                                path "../../../../../../groups/group/name";
                            }
                            max-elements 8;
                            ordered-by user;
                            description "Apply a configuration group at this level";
                        }

                    } // list message-digest-key

                } // list virtual-link

            } // list area

        } // list ospf

    } // grouping conf-router-ospf

}
