submodule nokia-conf-system-security-snmp {

    yang-version "1.1";

    belongs-to nokia-conf { prefix "conf"; }

    import nokia-sros-yang-extensions     { prefix "sros-ext"; }
    import nokia-types-sros               { prefix "types-sros"; }

    include nokia-conf-groups;

    sros-ext:sros-major-release "rel19";

    organization "Nokia";

    contact
        "Nokia SR OS Support
         Web: <http://www.nokia.com>";

    description
        "Nokia YANG Data model to configure system security snmp parameters. on SR OS based routers.

         Copyright 2016 Nokia. All rights reserved. Reproduction of this document
         is authorized on the condition that the foregoing copyright notice is included.

         This nokia-conf-system-security-snmp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2017-10-24";

    grouping conf-system-security-snmp {
        container snmp {
            description "Enter the snmp context";

            leaf-list apply-groups {
                type leafref {
                    path "../../../../groups/group/name";
                }
                max-elements 8;
                ordered-by user;
                description "Apply a configuration group at this level";
            }

            list access {
                key "group context security-model security-level";
                description "Enter the access list instance";

                leaf group {
                    type types-sros:named-item;
                    description "Group name";
                }

                leaf context {
                    type types-sros:named-item;
                    default "_sros_none";
                    description "String against which the context name should match to gain access rights";
                }

                leaf security-model {
                    type enumeration {
                        enum "snmpv1"                       { value 1; }
                        enum "snmpv2c"                      { value 2; }
                        enum "usm"                          { value 3; }
                    }
                    description "Security model";
                }

                leaf security-level {
                    type enumeration {
                        enum "no-auth-no-privacy"           { value 1; }
                        enum "auth-no-privacy"              { value 2; }
                        enum "privacy"                      { value 3; }
                    }
                    description "Minimum level of security required to gain the access rights allowed by this entry";
                }

                leaf prefix-match {
                    type enumeration {
                        enum "exact"                        { value 1; }
                        enum "prefix"                       { value 2; }
                    }
                    description "Type of the context name match";
                }

                leaf read {
                    type types-sros:named-item;
                    description "Specifies the MIB view of the SNMP context to which this conceptual row authorizes read access.";
                }

                leaf write {
                    type types-sros:named-item;
                    description "Specifies the MIB view of the SNMP context to which this conceptual row authorizes write access.";
                }

                leaf notify {
                    type types-sros:named-item;
                    description "MIB view of SNMP context to which access for notifications is authorized by this conceptual row";
                }

            } // list access

            list community {
                key "community-string";
                description "Enter the community list instance";

                leaf community-string {
                    type types-sros:encrypted-leaf {
                        length "1..114";
                    }
                    description "Management information that is accessed when using the community string";
                }

                leaf access-permissions {
                    type enumeration {
                        enum "r"                            { value 1; }
                        enum "rw"                           { value 2; }
                        enum "rwa"                          { value 3; }
                        enum "mgmt"                         { value 4; }
                        enum "vpls-mgmt"                    { value 5; }
                    }
                    mandatory true;
                    description "SNMP community name(s) to be used with the associated VPRN instance";
                }

                leaf version {
                    type enumeration {
                        enum "v1"                           { value 1; }
                        enum "v2c"                          { value 2; }
                        enum "both"                         { value 3; }
                    }
                    default "both";
                    description "SNMP version";
                }

                leaf source-access-list {
                    type leafref {
                        path "../../source-access-list/list-name";
                    }
                    description "Management information to be accessed when using the community string";
                }

                leaf-list apply-groups {
                    type leafref {
                        path "../../../../../groups/group/name";
                    }
                    max-elements 8;
                    ordered-by user;
                    description "Apply a configuration group at this level";
                }

            } // list community

            list usm-community {
                key "community-string";
                description "Enter the usm-community list instance";

                leaf community-string {
                    type types-sros:encrypted-leaf {
                        length "1..114";
                    }
                    description "SNMPv1/SNMPv2 community string to determine the SNMPv3 access permission";
                }

                leaf group {
                    must ". != 'snmp-ro' and . != 'snmp-rw' and . != 'snmp-rwa' and . != 'snmp-mgmt' and . != 'snmp-vpls-mgmt'";
                    type types-sros:named-item;
                    description "Group to manage the access rights of the community string";
                }

                leaf source-access-list {
                    type leafref {
                        path "../../source-access-list/list-name";
                    }
                    description "Management information to be accessed when using the community string";
                }

            } // list usm-community

            container attempts {
                description "Enter the attempts context";

                leaf count {
                    type uint16 {
                        range "1..64";
                    }
                    default "20";
                    description "Maximum unsuccessful SNMP attempts that are allowed for the specified time";
                }

                leaf time {
                    type uint16 {
                        range "0..60";
                    }
                    units "minutes";
                    default "5";
                    description "Time when a number of unsuccessful attempts are made before the host is locked out";
                }

                leaf lockout {
                    type uint16 {
                        range "0..1440";
                    }
                    units "minutes";
                    default "10";
                    description "Lockout period during which the host is not allowed to log in";
                }

                leaf-list apply-groups {
                    type leafref {
                        path "../../../../../groups/group/name";
                    }
                    max-elements 8;
                    ordered-by user;
                    description "Apply a configuration group at this level";
                }

            } // container attempts

            list source-access-list {
                key "list-name";
                max-elements 16;
                description "Enter the source-access-list list instance";

                leaf list-name {
                    type types-sros:string-not-all-spaces {
                        length "1..32";
                        pattern "(^[A-Za-z].*[^ \\\\t]?$)|(^[^_].*[^ \\\\t]?$)" {
                            error-message "List name must begin with a letter";
                        }
                    }
                    description "Value for the name given to source access list";
                }

                leaf-list apply-groups {
                    type leafref {
                        path "../../../../../groups/group/name";
                    }
                    max-elements 8;
                    ordered-by user;
                    description "Apply a configuration group at this level";
                }

                list source-host {
                    key "host-name";
                    max-elements 16;
                    description "Enter the source-host list instance";

                    leaf host-name {
                        type types-sros:named-item;
                        description "Source host entry name";
                    }

                    leaf address {
                        type types-sros:ip-unicast-address;
                        mandatory true;
                        description "Address of the source host entry";
                    }

                    leaf-list apply-groups {
                        type leafref {
                            path "../../../../../../groups/group/name";
                        }
                        max-elements 8;
                        ordered-by user;
                        description "Apply a configuration group at this level";
                    }

                } // list source-host

            } // list source-access-list

            list view {
                key "view-name subtree";
                description "Enter the view list instance";

                leaf view-name {
                    type types-sros:named-item;
                    description "Name of the view to display output";
                }

                leaf subtree {
                    type string {
                        length "1..256";
                    }
                    description "Object Identifier (OID) value";
                }

                leaf mask {
                    type string {
                        length "1..16";
                        pattern "(0X|0x)?(([A-Fa-f0-9]){2})+" {
                            error-message "Hex value must be even number of characters.";
                        }
                    }
                    description "Mask value as binary value, or hex value";
                }

                leaf type {
                    type enumeration {
                        enum "included"                     { value 1; }
                        enum "excluded"                     { value 2; }
                    }
                    description "Type of SNMP security view mask";
                }

                leaf-list apply-groups {
                    type leafref {
                        path "../../../../../groups/group/name";
                    }
                    max-elements 8;
                    ordered-by user;
                    description "Apply a configuration group at this level";
                }

            } // list view

        } // container snmp

    } // grouping conf-system-security-snmp

}
