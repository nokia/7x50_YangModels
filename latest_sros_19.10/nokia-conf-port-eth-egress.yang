submodule nokia-conf-port-eth-egress {

    yang-version "1.1";

    belongs-to nokia-conf { prefix "conf"; }

    import nokia-sros-yang-extensions     { prefix "sros-ext"; }
    import nokia-types-qos                { prefix "types-qos"; }
    import nokia-types-sros               { prefix "types-sros"; }

    include nokia-conf-groups;
    include nokia-conf-qos;

    sros-ext:sros-major-release "rel19";

    organization "Nokia";

    contact
        "Nokia SR OS Support
         Web: <http://www.nokia.com>";

    description
        "Nokia YANG Data model to configure egress capabilities for ethernet ports on SR OS based routers.

         Copyright 2016 Nokia. All rights reserved. Reproduction of this document
         is authorized on the condition that the foregoing copyright notice is included.

         This nokia-conf-port-eth-egress YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-08-20";

    grouping conf-port-eth-egress {
        container egress {
            description "Enter the egress context";

            leaf hs-port-pool-policy {
                type leafref {
                    path "../../../../qos/hs-port-pool-policy/name";
                }
                description "HS port pool policy";
            }

            leaf hsmda-scheduler-policy {
                type leafref {
                    path "../../../../qos/hsmda-scheduler-policy/hsmda-scheduler-policy-name";
                }
                description "HSMDA scheduler policy";
            }

            leaf monitor-port-scheduler {
                type boolean;
                default "false";
                description "Enable/disable monitoring of egress scheduler on the Ethernet port.";
            }

            leaf rate {
                type int32 {
                    range "1..400000000";
                }
                units "kilobps";
                description "Maximum egress bandwidth that this Ethernet port can receive";
            }

            leaf eth-bn-rate-changes {
                type boolean;
                default "false";
                description "Receive rate changes in Ethernet Bandwidth Notification (Eth-BN) messages to update egress rate";
            }

            leaf-list apply-groups {
                type leafref {
                    path "../../../../groups/group/name";
                }
                max-elements 8;
                ordered-by user;
                description "Apply a configuration group at this level";
            }

            container port-qos-policy {
                description "Enter the port-qos-policy context";

                leaf policy-name {
                    type leafref {
                        path "../../../../../qos/port-qos-policy/port-qos-policy-name";
                    }
                    description "Port qos policy name";
                }

            } // container port-qos-policy

            list expanded-secondary-shaper {
                key "secondary-shaper-name";
                description "Enter the expanded-secondary-shaper list instance";

                leaf secondary-shaper-name {
                    type types-sros:named-item;
                    description "Name for the expanded secondary shaper";
                }

                leaf low-burst-max-class {
                    type uint32 {
                        range "1..8";
                    }
                    default "8";
                    description "Class to associate with the Ethernet egress expanded secondary shaper";
                }

                leaf monitor-threshold {
                    type types-qos:secondary-shaper-class-threshold;
                    description "Monitoring threshold for non-conformance burst";
                }

                leaf rate {
                    type types-qos:secondary-shaper-pir-rate;
                    default "max";
                    description "Rate of the expanded secondary shaper";
                }

                leaf-list apply-groups {
                    type leafref {
                        path "../../../../../groups/group/name";
                    }
                    max-elements 8;
                    ordered-by user;
                    description "Apply a configuration group at this level";
                }

                container aggregate-burst {
                    description "Enter the aggregate-burst context";

                    leaf high-burst-increase {
                        type int32 {
                            range "0..65528";
                        }
                        units "bytes";
                        description "High burst increase";
                    }

                    leaf low-burst-limit {
                        type types-qos:class-burst-limit;
                        units "bytes";
                        description "Low burst limit";
                    }

                } // container aggregate-burst

                list class {
                    key "class-number";
                    description "Enter the class list instance";

                    leaf class-number {
                        type uint32 {
                            range "1..8";
                        }
                        description "Unique value of the class";
                    }

                    leaf rate {
                        type types-qos:secondary-shaper-pir-rate;
                        default "max";
                        description "Class rate";
                    }

                    leaf monitor-threshold {
                        type types-qos:secondary-shaper-class-threshold;
                        description "Monitoring threshold for non-conformance burst of the class";
                    }

                    leaf burst-limit {
                        type types-qos:class-burst-limit;
                        units "bytes";
                        description "Class identifier of the low burst maximum class";
                    }

                    leaf-list apply-groups {
                        type leafref {
                            path "../../../../../../groups/group/name";
                        }
                        max-elements 8;
                        ordered-by user;
                        description "Apply a configuration group at this level";
                    }

                } // list class

            } // list expanded-secondary-shaper

            container hs-scheduler-policy {
                description "Enter the hs-scheduler-policy context";

                leaf policy-name {
                    type leafref {
                        path "../../../../../qos/hs-scheduler-policy/name";
                    }
                    description "HS scheduler policy name";
                }

                container overrides {
                    presence "Enable hs-scheduler-overrides.";
                    description "Enter the overrides context";

                    leaf max-rate {
                        type types-qos:hs-pir-rate-override;
                        units "megabps";
                        description "Configure the maximum rate.";
                    }

                    leaf-list apply-groups {
                        type leafref {
                            path "../../../../../../groups/group/name";
                        }
                        max-elements 8;
                        ordered-by user;
                        description "Apply a configuration group at this level";
                    }

                    list group {
                        key "group-id";
                        description "Enter the group list instance";

                        leaf group-id {
                            type uint32 {
                                range "1";
                            }
                            description "Specifies the group identifier.";
                        }

                        leaf rate {
                            type types-qos:hs-pir-rate-override;
                            units "megabps";
                            description "Configure a group rate.";
                        }

                        leaf-list apply-groups {
                            type leafref {
                                path "../../../../../../../groups/group/name";
                            }
                            max-elements 8;
                            ordered-by user;
                            description "Apply a configuration group at this level";
                        }

                    } // list group

                    list scheduling-class {
                        key "class-number";
                        description "Enter the scheduling-class list instance";

                        leaf class-number {
                            type uint32 {
                                range "1..6";
                            }
                            description "The unique value of the class.";
                        }

                        leaf rate {
                            type types-qos:hs-pir-rate-override;
                            units "megabps";
                            description "Configure the rate of the scheduling class.";
                        }

                        leaf weight {
                            type types-qos:hs-wrr-weight-override;
                            description "Configure the weight of the scheduling class.";
                        }

                        leaf-list apply-groups {
                            type leafref {
                                path "../../../../../../../groups/group/name";
                            }
                            max-elements 8;
                            ordered-by user;
                            description "Apply a configuration group at this level";
                        }

                    } // list scheduling-class

                } // container overrides

            } // container hs-scheduler-policy

            container port-scheduler-policy {
                description "Enter the port-scheduler-policy context";

                leaf policy-name {
                    type leafref {
                        path "../../../../../qos/port-scheduler-policy/name";
                    }
                    description "Configure an egress scheduler policy.";
                }

                container overrides {
                    presence "Enable port-scheduler-overrides.";
                    description "Enter the overrides context";

                    leaf-list apply-groups {
                        type leafref {
                            path "../../../../../../groups/group/name";
                        }
                        max-elements 8;
                        ordered-by user;
                        description "Apply a configuration group at this level";
                    }

                    container max-rate {
                        description "Enter the max-rate context";

                        choice rate-or-percent-rate {
                            case rate {

                                leaf rate {
                                    type types-qos:sched-pir-rate;
                                    units "kilobps";
                                    default "max";
                                    description "Configure the PIR rate as a rate.";
                                }

                            }
                            case percent-rate {

                                leaf percent-rate {
                                    type decimal64 {
                                        range "0.01..100";
                                        fraction-digits 2;
                                    }
                                    units "percent";
                                    default "100";
                                    description "Configure the PIR rate as a percent.";
                                }

                            }
                        }
                    } // container max-rate

                    list level {
                        key "priority-level";
                        description "Enter the level list instance";

                        leaf priority-level {
                            type uint32 {
                                range "1..8";
                            }
                            description "Specifies the priority level of the port scheduler override.";
                        }

                        leaf-list apply-groups {
                            type leafref {
                                path "../../../../../../../groups/group/name";
                            }
                            max-elements 8;
                            ordered-by user;
                            description "Apply a configuration group at this level";
                        }

                        choice rate-or-percent-rate {
                            case rate {

                                container rate {
                                    description "Enter the rate context";

                                    leaf pir {
                                        type types-qos:sched-pir-rate-ovr;
                                        units "kilobps";
                                        description "Configure the PIR rate in kbps.";
                                    }

                                    leaf cir {
                                        type types-qos:sched-cir-rate-ovr;
                                        units "kilobps";
                                        description "Configure the CIR rate in kbps.";
                                    }

                                } // container rate

                            }
                            case percent-rate {

                                container percent-rate {
                                    description "Enter the percent-rate context";

                                    leaf pir {
                                        type types-qos:pir-percent-override;
                                        units "percent";
                                        description "Configure the PIR rate as a percent.";
                                    }

                                    leaf cir {
                                        type types-qos:cir-percent-override;
                                        units "percent";
                                        description "Configure Che CIR rate as a percent.";
                                    }

                                } // container percent-rate

                            }
                        }
                    } // list level

                } // container overrides

            } // container port-scheduler-policy

            list hs-secondary-shaper {
                key "secondary-shaper-name";
                description "Enter the hs-secondary-shaper list instance";

                leaf secondary-shaper-name {
                    type types-sros:named-item;
                    description "Specifies the expanded secondary shaper name on the egress side.";
                }

                leaf description {
                    type types-sros:description;
                    description "Text description";
                }

                leaf-list apply-groups {
                    type leafref {
                        path "../../../../../groups/group/name";
                    }
                    max-elements 8;
                    ordered-by user;
                    description "Apply a configuration group at this level";
                }

                container aggregate {
                    description "Enter the aggregate context";

                    leaf low-burst-max-class {
                        type uint32 {
                            range "1..6";
                        }
                        default "6";
                        description "Specify the low burst max class.";
                    }

                    leaf rate {
                        type union {
                            type int32 {
                                range "1..100000000";
                            }
                            type enumeration {
                                enum "max"                          { value -1; }
                            }
                        }
                        units "kilobps";
                        default "max";
                        description "Specify the aggregate rate.";
                    }

                } // container aggregate

                list class {
                    key "class-number";
                    description "Enter the class list instance";

                    leaf class-number {
                        type uint32 {
                            range "1..6";
                        }
                        description "The unique value of the class.";
                    }

                    leaf rate {
                        type union {
                            type int32 {
                                range "1..100000000";
                            }
                            type enumeration {
                                enum "max"                          { value -1; }
                            }
                        }
                        units "kilobps";
                        default "max";
                        description "Specify the aggregate rate";
                    }

                    leaf-list apply-groups {
                        type leafref {
                            path "../../../../../../groups/group/name";
                        }
                        max-elements 8;
                        ordered-by user;
                        description "Apply a configuration group at this level";
                    }

                } // list class

            } // list hs-secondary-shaper

        } // container egress

    } // grouping conf-port-eth-egress

}
