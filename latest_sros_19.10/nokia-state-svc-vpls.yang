submodule nokia-state-svc-vpls {

    yang-version "1.1";

    belongs-to nokia-state { prefix "state"; }

    import ietf-yang-types                { prefix "yang"; }
    import nokia-sros-yang-extensions     { prefix "sros-ext"; }
    import nokia-types-eth-cfm            { prefix "types-eth-cfm"; }
    import nokia-types-igmp               { prefix "types-igmp"; }
    import nokia-types-pim                { prefix "types-pim"; }
    import nokia-types-qos                { prefix "types-qos"; }
    import nokia-types-services           { prefix "types-services"; }
    import nokia-types-sros               { prefix "types-sros"; }

    include nokia-state-eth-cfm;
    include nokia-state-subscriber-mgmt;

    sros-ext:sros-major-release "rel19";

    organization "Nokia";

    contact
        "Nokia SR OS Support
         Web: <http://www.nokia.com>";

    description
        "Nokia YANG Data model with operational state for vpls services on SR OS based routers.

         Copyright 2016 Nokia. All rights reserved. Reproduction of this document
         is authorized on the condition that the foregoing copyright notice is included.

         This nokia-state-svc-vpls YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-02-14";

    grouping state-svc-vpls {
        list vpls {
            key "service-name";
            description "Enter the vpls list instance";

            leaf service-name {
                type types-services:service-name;
                description "Service name";
            }

            leaf oper-service-id {
                type types-services:service-id;
                description "Service identifier";
            }

            leaf oper-state {
                type types-sros:oper-state;
                description "Operational state.";
            }

            leaf sap-count {
                type int32;
                description "Number of SAPs";
            }

            leaf sdp-bind-count {
                type int32;
                description "Number of SDP binds";
            }

            leaf template-used {
                type string;
                description "Template used to create this service";
            }

            leaf creation-origin {
                type types-sros:creation-origin;
                description "Creation origin of the service";
            }

            leaf l2pt-term-enabled {
                type boolean;
                description
                    "If 'l2pt-termination' and/or 'bpdu-translation'
                     is in use in this service by at least one SAP or
                     spoke SDP Bind. If the value is 'true', it means that
                     at least one of 'l2pt-termination' or 'bpdu-translation'
                     is enabled.";
            }

            container fdb {
                description "Enter the fdb context";

                leaf mac-relearn-only {
                    type boolean;
                    description
                        "When set to 'true' either the FDB table of this VPLS
                         service is full, or that the maximum system wide number of
                         MACs supported by the node has been reached, and thus
                         MAC learning is temporary disabled, and only MAC relearns
                         can take place.";
                }

                container statistics {
                    description "FDB usage information";

                    leaf total {
                        type int32;
                        description "Number of entries allocated in the FDB ";
                    }

                    leaf in-use {
                        type int32;
                        description "Number of entries currently in use in the FDB";
                    }

                    leaf static {
                        type int32;
                        description "Number of static entries in the FDB";
                    }

                    leaf learned {
                        type int32;
                        description "Number of learned entries in the FDB";
                    }

                    leaf oam {
                        type int32;
                        description "Number of OAM entries in the FDB";
                    }

                    leaf conditional-static {
                        type int32;
                        description "Number of conditional static entries in the FDB";
                    }

                    leaf dhcp {
                        type int32;
                        description "Number of dhcp-learned entries in the FDB";
                    }

                    leaf host {
                        type int32;
                        description "Number of host-learned entries in the FDB";
                    }

                    leaf interface {
                        type int32;
                        description "Number of interface entries in the FDB";
                    }

                    leaf bgp-evpn {
                        type int32;
                        description "Number of bgp-evpn entries in the FDB";
                    }

                    leaf evpn-static {
                        type int32;
                        description "Number of evpn static entries in the FDB";
                    }

                } // container statistics

            } // container fdb

            container mfib {
                description "Enter the mfib context";

                container table {
                    description "Enter the table context";

                    list mac-based-stream {
                        key "mac-address";
                        description "States for macBased multicast.";

                        leaf mac-address {
                            type yang:mac-address;
                        }

                        leaf matched-packets {
                            type yang:zero-based-counter64;
                            description "The number of multicast packets that matched this entry.";
                        }

                        leaf matched-octets {
                            type yang:zero-based-counter64;
                            description "The number of forwarded octets that matched this entry.";
                        }

                        list sap {
                            key "sap-id";

                            leaf sap-id {
                                type types-sros:sap;
                                description "SAP identifier";
                            }

                            leaf forwarding-state {
                                type types-igmp:forwarding-state;
                                description "The traffic forwarding state on this port.";
                            }

                            leaf port-service-name {
                                type types-services:service-name;
                                description "The service to which this port belongs";
                            }

                        } // list sap

                        list sdp {
                            key "sdp-bind-id";

                            leaf sdp-bind-id {
                                type types-services:sdp-bind-id;
                                description "SDP Binding identifier as <sdp-id>:<vc-id>. sdp-id - [1..32767] vc-id - [1..4294967295].";
                            }

                            leaf forwarding-state {
                                type types-igmp:forwarding-state;
                                description "The traffic forwarding state on this port.";
                            }

                            leaf port-service-name {
                                type types-services:service-name;
                                description "The service to which this port belongs";
                            }

                        } // list sdp

                        list vxlan {
                            key "vtep vni";

                            leaf vtep {
                                type types-sros:ip-unicast-address;
                            }

                            leaf vni {
                                type types-services:vxlan-vni;
                            }

                            leaf forwarding-state {
                                type types-igmp:forwarding-state;
                                description "The traffic forwarding state on this port.";
                            }

                            leaf port-service-name {
                                type types-services:service-name;
                                description "The service to which this port belongs";
                            }

                        } // list vxlan

                        list evpn-mpls {
                            key "tep label";

                            leaf tep {
                                type types-sros:ip-unicast-address;
                            }

                            leaf label {
                                type uint32;
                            }

                            leaf forwarding-state {
                                type types-igmp:forwarding-state;
                                description "The traffic forwarding state on this port.";
                            }

                            leaf port-service-name {
                                type types-services:service-name;
                                description "The service to which this port belongs";
                            }

                        } // list evpn-mpls

                    } // list mac-based-stream

                    list ipv4-based-stream {
                        key "group-address source-address";
                        description "States for ipv4 sgBased ipmulticast.";

                        leaf group-address {
                            type types-sros:ipv4-address;
                            description "Group address of multicast channel.";
                        }

                        leaf source-address {
                            type types-sros:ipv4-address;
                            description "Source address of multicast channel.";
                        }

                        leaf matched-packets {
                            type yang:zero-based-counter64;
                            description "The number of multicast packets that matched this entry.";
                        }

                        leaf matched-octets {
                            type yang:zero-based-counter64;
                            description "The number of forwarded octets that matched this entry.";
                        }

                        list sap {
                            key "sap-id";

                            leaf sap-id {
                                type types-sros:sap;
                                description "SAP identifier";
                            }

                            leaf forwarding-state {
                                type types-igmp:forwarding-state;
                                description "The traffic forwarding state on this port.";
                            }

                            leaf port-service-name {
                                type types-services:service-name;
                                description "The service to which this port belongs";
                            }

                        } // list sap

                        list sdp {
                            key "sdp-bind-id";

                            leaf sdp-bind-id {
                                type types-services:sdp-bind-id;
                                description "SDP Binding identifier as <sdp-id>:<vc-id>. sdp-id - [1..32767] vc-id - [1..4294967295].";
                            }

                            leaf forwarding-state {
                                type types-igmp:forwarding-state;
                                description "The traffic forwarding state on this port.";
                            }

                            leaf port-service-name {
                                type types-services:service-name;
                                description "The service to which this port belongs";
                            }

                        } // list sdp

                        list vxlan {
                            key "vtep vni";

                            leaf vtep {
                                type types-sros:ip-unicast-address;
                            }

                            leaf vni {
                                type types-services:vxlan-vni;
                            }

                            leaf forwarding-state {
                                type types-igmp:forwarding-state;
                                description "The traffic forwarding state on this port.";
                            }

                            leaf port-service-name {
                                type types-services:service-name;
                                description "The service to which this port belongs";
                            }

                        } // list vxlan

                        list evpn-mpls {
                            key "tep label";

                            leaf tep {
                                type types-sros:ip-unicast-address;
                            }

                            leaf label {
                                type uint32;
                            }

                            leaf forwarding-state {
                                type types-igmp:forwarding-state;
                                description "The traffic forwarding state on this port.";
                            }

                            leaf port-service-name {
                                type types-services:service-name;
                                description "The service to which this port belongs";
                            }

                        } // list evpn-mpls

                        list multicast-management-operational-data {
                            key "chassis-number slot-number fp-number";
                            description "Operational states";

                            leaf chassis-number {
                                type uint32;
                                description "The unique index identifying this physical chassis.";
                            }

                            leaf slot-number {
                                type uint32;
                                description
                                    "The unique value which identifies the IOM slot within a
                                     chassis in the system.";
                            }

                            leaf fp-number {
                                type uint32;
                                description "Forwarding plane within a specific IOM card";
                            }

                            leaf bandwith {
                                type yang:gauge32;
                                units "kilobps";
                                description "Current bandwidth";
                            }

                            leaf current-path {
                                type enumeration {
                                    enum "none"                         { value 0; }
                                    enum "primary"                      { value 1; }
                                    enum "secondary"                    { value 2; }
                                    enum "ancillary"                    { value 3; }
                                    enum "blackhole"                    { value 4; }
                                }
                                description "Explicit sf path.";
                            }

                            leaf explicit-path {
                                type boolean;
                                description "???";
                            }

                            leaf admin-bw {
                                type yang:gauge32;
                                description "Admin bandwidth.";
                            }

                            leaf preference {
                                type yang:gauge32;
                                description "Preference level.";
                            }

                            leaf blackholed {
                                type boolean;
                                description "In black-hole state";
                            }

                            leaf blackhole-rate {
                                type yang:gauge32;
                                description "The current rate at which this channel will be placed in black-hole state";
                            }

                            leaf highest-bw {
                                type yang:gauge32;
                                description "The highest multicast bandwidth that has been accounted.";
                            }

                            leaf second-highest-bw {
                                type yang:gauge32;
                                description "The second highest multicast bandwidth that has been accounted.";
                            }

                            leaf expiry-time {
                                type uint32;
                                units "seconds";
                                description "Remaining time before the bandwidth update timer on the FP expires";
                            }

                            leaf plane {
                                type uint32;
                                description "Forwarding plane";
                            }

                        } // list multicast-management-operational-data

                    } // list ipv4-based-stream

                    list ipv6-based-stream {
                        key "group-address source-address";
                        description "States for ipv6 sgBased ipmulticast.";

                        leaf group-address {
                            type types-sros:ipv6-address;
                            description "Group address of multicast channel.";
                        }

                        leaf source-address {
                            type types-sros:ipv6-address;
                            description "Source address of multicast channel.";
                        }

                        leaf matched-packets {
                            type yang:zero-based-counter64;
                            description "The number of multicast packets that matched this entry.";
                        }

                        leaf matched-octets {
                            type yang:zero-based-counter64;
                            description "The number of forwarded octets that matched this entry.";
                        }

                        list sap {
                            key "sap-id";

                            leaf sap-id {
                                type types-sros:sap;
                                description "SAP identifier";
                            }

                            leaf forwarding-state {
                                type types-igmp:forwarding-state;
                                description "The traffic forwarding state on this port.";
                            }

                            leaf port-service-name {
                                type types-services:service-name;
                                description "The service to which this port belongs";
                            }

                        } // list sap

                        list sdp {
                            key "sdp-bind-id";

                            leaf sdp-bind-id {
                                type types-services:sdp-bind-id;
                                description "SDP Binding identifier as <sdp-id>:<vc-id>. sdp-id - [1..32767] vc-id - [1..4294967295].";
                            }

                            leaf forwarding-state {
                                type types-igmp:forwarding-state;
                                description "The traffic forwarding state on this port.";
                            }

                            leaf port-service-name {
                                type types-services:service-name;
                                description "The service to which this port belongs";
                            }

                        } // list sdp

                        list vxlan {
                            key "vtep vni";

                            leaf vtep {
                                type types-sros:ip-unicast-address;
                            }

                            leaf vni {
                                type types-services:vxlan-vni;
                            }

                            leaf forwarding-state {
                                type types-igmp:forwarding-state;
                                description "The traffic forwarding state on this port.";
                            }

                            leaf port-service-name {
                                type types-services:service-name;
                                description "The service to which this port belongs";
                            }

                        } // list vxlan

                        list evpn-mpls {
                            key "tep label";

                            leaf tep {
                                type types-sros:ip-unicast-address;
                            }

                            leaf label {
                                type uint32;
                            }

                            leaf forwarding-state {
                                type types-igmp:forwarding-state;
                                description "The traffic forwarding state on this port.";
                            }

                            leaf port-service-name {
                                type types-services:service-name;
                                description "The service to which this port belongs";
                            }

                        } // list evpn-mpls

                        list multicast-management-operational-data {
                            key "chassis-number slot-number fp-number";
                            description "Operational states";

                            leaf chassis-number {
                                type uint32;
                                description "The unique index identifying this physical chassis.";
                            }

                            leaf slot-number {
                                type uint32;
                                description
                                    "The unique value which identifies the IOM slot within a
                                     chassis in the system.";
                            }

                            leaf fp-number {
                                type uint32;
                                description "Forwarding plane within a specific IOM card";
                            }

                            leaf bandwith {
                                type yang:gauge32;
                                units "kilobps";
                                description "Current bandwidth";
                            }

                            leaf current-path {
                                type enumeration {
                                    enum "none"                         { value 0; }
                                    enum "primary"                      { value 1; }
                                    enum "secondary"                    { value 2; }
                                    enum "ancillary"                    { value 3; }
                                    enum "blackhole"                    { value 4; }
                                }
                                description "Explicit sf path.";
                            }

                            leaf explicit-path {
                                type boolean;
                                description "???";
                            }

                            leaf admin-bw {
                                type yang:gauge32;
                                description "Admin bandwidth.";
                            }

                            leaf preference {
                                type yang:gauge32;
                                description "Preference level.";
                            }

                            leaf blackholed {
                                type boolean;
                                description "In black-hole state";
                            }

                            leaf blackhole-rate {
                                type yang:gauge32;
                                description "The current rate at which this channel will be placed in black-hole state";
                            }

                            leaf highest-bw {
                                type yang:gauge32;
                                description "The highest multicast bandwidth that has been accounted.";
                            }

                            leaf second-highest-bw {
                                type yang:gauge32;
                                description "The second highest multicast bandwidth that has been accounted.";
                            }

                            leaf expiry-time {
                                type uint32;
                                units "seconds";
                                description "Remaining time before the bandwidth update timer on the FP expires";
                            }

                            leaf plane {
                                type uint32;
                                description "Forwarding plane";
                            }

                        } // list multicast-management-operational-data

                    } // list ipv6-based-stream

                } // container table

            } // container mfib

            container pbb {
                description "Enter the pbb context";

                leaf oper-source-bmac {
                    type yang:mac-address;
                    description "Backbone Source MAC Address for PBB packets.";
                }

                list backbone-vpls {
                    key "backbone-vpls-service-name";
                    description "Enter the backbone-vpls list instance";

                    leaf backbone-vpls-service-name {
                        type leafref {
                            path "../../../service-name";
                        }
                        description "Backbone VPLS service";
                    }

                    leaf oper-isid {
                        type types-services:isid;
                        description
                            "VPLS service ISID used as part of the PBB frames. It is used at
                             the destination PE as a demultiplexor field.";
                    }

                } // list backbone-vpls

            } // container pbb

            container temp-flood {
                description "Temporary flooding information";

                leaf active {
                    type boolean;
                    description "Whether temporary flooding is currently active";
                }

                leaf change-count {
                    type int32;
                    description
                        "Number of times temporary flooding status
                         changed from inactive to active.

                         The value of this object resets to zero when temporary
                         flooding is disabled.";
                }

            } // container temp-flood

            container stp {
                description "Enter the stp context";

                list mst-instance {
                    key "mst-inst-number";
                    description "Enter the mst-instance list instance";

                    leaf mst-inst-number {
                        type uint32 {
                            range "1..4094";
                        }
                        description "Multiple Spanning Tree Instance number";
                    }

                    leaf regional-root {
                        type binary {
                            length "8";
                        }
                        description
                            "The bridge identifier of the regional root
                             of the MSTI spanning tree";
                    }

                    leaf root-cost {
                        type int32;
                        description
                            "The cost of the path to the regional root bridge
                             as seen from this bridge.";
                    }

                    leaf hop-count {
                        type int32;
                        description "The remaining number of hops.";
                    }

                    leaf root-port {
                        type int32;
                        description
                            "The port number of the port which offers the lowest cost
                             path from this bridge to the regional root bridge.";
                    }

                } // list mst-instance

            } // container stp

            list bgp {
                key "bgp-instance";
                description "Enter the bgp list instance";

                leaf bgp-instance {
                    type int32 {
                        range "1..2";
                    }
                    description "BGP instance";
                }

                leaf oper-route-distinguisher-type {
                    type types-services:route-distinguisher-type;
                    description "Type of operational route-distinguisher.";
                }

                leaf oper-route-distinguisher {
                    type string;
                    description "Operational route-distinguisher used when advertising NLRIs.";
                }

                container route-target {
                    description "Enter the route-target context";

                    leaf export-origin {
                        type types-services:route-target-origin;
                        description "Origin of route-target export policy";
                    }

                    leaf oper-export {
                        type string;
                        description "Operational route-target used when advertising NLRIs.";
                    }

                    leaf import-origin {
                        type types-services:route-target-origin;
                        description "Origin of route-target import policy";
                    }

                    leaf oper-import {
                        type string;
                        description "Operational route-target used when importing NLRIs.";
                    }

                } // container route-target

            } // list bgp

            container igmp-snooping {
                description "Enter the igmp-snooping context";

                leaf transmitted-bgp-smet-routes {
                    type yang:counter32;
                    description "Transmitted BGP SMET routes";
                }

                container querier {
                    description "The active IGMP querier selected in this service.";

                    leaf address {
                        type types-sros:ipv4-address;
                        description
                            "The source IP address used by queries sent out by
                             this multicast router.";
                    }

                    leaf version {
                        type types-igmp:igmp-version;
                        description
                            "The version of the protocol that is sent by this
                             multicast router.";
                    }

                    leaf up-time {
                        type uint32;
                        units "seconds";
                        description
                            "The time since this multicast router has been known
                             in this service.";
                    }

                    leaf expiry-time {
                        type uint32;
                        units "seconds";
                        description "The time remaining before this multicast router is aged out.";
                    }

                    container igmp-v3-states {

                        leaf general-query-interval {
                            type uint32;
                            units "seconds";
                            description "The General Query Interval used by this multicast router.";
                        }

                        leaf general-response-interval {
                            type uint32;
                            units "seconds";
                            description
                                "The General Query Response interval used by this
                                 multicast router.";
                        }

                        leaf robust-count {
                            type uint32;
                            description "The Robust Count value used by this multicast router.";
                        }

                    } // container igmp-v3-states

                    container port {

                        leaf port-type {
                            type enumeration {
                                enum "sap"                          { value 0; }
                                enum "sdp"                          { value 1; }
                                enum "rvpls"                        { value 2; }
                                enum "vxlan"                        { value 3; }
                                enum "evpn-mpls"                    { value 4; }
                            }
                        }

                        leaf sap-id {
                            type types-sros:sap;
                            description "SAP identifier.";
                        }

                        leaf sdp-bind-id {
                            type types-services:sdp-bind-id;
                            description "SDP Binding identifier.";
                        }

                        leaf rvpls-service-name {
                            type types-services:service-name;
                            description "RVPLS service identifier.";
                        }

                        leaf rvpls-interface-name {
                            type types-sros:interface-name;
                            description "RVPLS interface identifier.";
                        }

                        leaf vxlan-vtep {
                            type types-sros:ip-unicast-address;
                            description "VXLAN VTEP identifier.";
                        }

                        leaf vxlan-vni {
                            type types-services:vxlan-vni;
                            description "VXLAN VNI identifier.";
                        }

                    } // container port

                } // container querier

                list multicast-router {
                    key "address";
                    description "The IGMP multicast routers fond on this service.";

                    leaf address {
                        type types-sros:ipv4-address;
                        description
                            "The source IP address used by queries sent out by
                             this multicast router.";
                    }

                    leaf version {
                        type types-igmp:igmp-version;
                        description
                            "The version of the protocol that is sent by this
                             multicast router.";
                    }

                    leaf up-time {
                        type uint32;
                        units "seconds";
                        description
                            "The time since this multicast router has been known
                             in this service.";
                    }

                    leaf expiry-time {
                        type uint32;
                        units "seconds";
                        description "The time remaining before this multicast router is aged out.";
                    }

                    container igmp-v3-states {

                        leaf general-query-interval {
                            type uint32;
                            units "seconds";
                            description "The General Query Interval used by this multicast router.";
                        }

                        leaf general-response-interval {
                            type uint32;
                            units "seconds";
                            description
                                "The General Query Response interval used by this
                                 multicast router.";
                        }

                        leaf robust-count {
                            type uint32;
                            description "The Robust Count value used by this multicast router.";
                        }

                    } // container igmp-v3-states

                    container port {

                        leaf port-type {
                            type enumeration {
                                enum "sap"                          { value 0; }
                                enum "sdp"                          { value 1; }
                                enum "rvpls"                        { value 2; }
                                enum "vxlan"                        { value 3; }
                                enum "evpn-mpls"                    { value 4; }
                            }
                        }

                        leaf sap-id {
                            type types-sros:sap;
                            description "SAP identifier.";
                        }

                        leaf sdp-bind-id {
                            type types-services:sdp-bind-id;
                            description "SDP Binding identifier.";
                        }

                        leaf rvpls-service-name {
                            type types-services:service-name;
                            description "RVPLS service identifier.";
                        }

                        leaf rvpls-interface-name {
                            type types-sros:interface-name;
                            description "RVPLS interface identifier.";
                        }

                        leaf vxlan-vtep {
                            type types-sros:ip-unicast-address;
                            description "VXLAN VTEP identifier.";
                        }

                        leaf vxlan-vni {
                            type types-services:vxlan-vni;
                            description "VXLAN VNI identifier.";
                        }

                    } // container port

                } // list multicast-router

                list group {
                    key "group-address";
                    description
                        "Multicast group membership information for this service.
                         The content of this table is used by the system to
                         'proxy-report' towards the Querier.";

                    leaf group-address {
                        type types-sros:ipv4-multicast-address;
                        description "Group address of static IGMP multicast channel";
                    }

                    leaf filter-mode {
                        type types-igmp:filter-mode;
                    }

                    leaf up-time {
                        type uint32;
                        units "seconds";
                        description "The time elapsed since this entry was created.";
                    }

                    list source {
                        key "source-address";
                        description "List of multicast source information for the group.";

                        leaf source-address {
                            type types-sros:ipv4-address;
                            description "Source address of multicast channel.";
                        }

                        leaf up-time {
                            type uint32;
                            units "seconds";
                            description "The time elapsed since this entry was created.";
                        }

                    } // list source

                } // list group

            } // container igmp-snooping

            container mld-snooping {
                description "Enter the mld-snooping context";

                leaf transmitted-bgp-smet-routes {
                    type yang:counter32;
                    description "Transmitted BGP SMET routes";
                }

                container querier {
                    description "The active MLD querier selected in this service.";

                    leaf address {
                        type types-sros:ipv6-address;
                        description
                            "The source IP address used by queries sent out by
                             this multicast router.";
                    }

                    leaf version {
                        type types-igmp:igmp-version;
                        description
                            "The version of the protocol that is sent by this
                             multicast router.";
                    }

                    leaf up-time {
                        type uint32;
                        units "seconds";
                        description
                            "The time since this multicast router has been known
                             in this service.";
                    }

                    leaf expiry-time {
                        type uint32;
                        units "seconds";
                        description "The time remaining before this multicast router is aged out.";
                    }

                    container mld-v2-states {

                        leaf general-query-interval {
                            type uint32;
                            units "seconds";
                            description "The General Query Interval used by this multicast router.";
                        }

                        leaf general-response-interval {
                            type uint32;
                            units "seconds";
                            description
                                "The General Query Response interval used by this
                                 multicast router.";
                        }

                        leaf robust-count {
                            type uint32;
                            description "The Robust Count value used by this multicast router.";
                        }

                    } // container mld-v2-states

                    container port {

                        leaf port-type {
                            type enumeration {
                                enum "sap"                          { value 0; }
                                enum "sdp"                          { value 1; }
                                enum "rvpls"                        { value 2; }
                                enum "vxlan"                        { value 3; }
                                enum "evpn-mpls"                    { value 4; }
                            }
                        }

                        leaf sap-id {
                            type types-sros:sap;
                            description "SAP identifier.";
                        }

                        leaf sdp-bind-id {
                            type types-services:sdp-bind-id;
                            description "SDP Binding identifier.";
                        }

                        leaf rvpls-service-name {
                            type types-services:service-name;
                            description "RVPLS service identifier.";
                        }

                        leaf rvpls-interface-name {
                            type types-sros:interface-name;
                            description "RVPLS interface identifier.";
                        }

                        leaf vxlan-vtep {
                            type types-sros:ip-unicast-address;
                            description "VXLAN VTEP identifier.";
                        }

                        leaf vxlan-vni {
                            type types-services:vxlan-vni;
                            description "VXLAN VNI identifier.";
                        }

                    } // container port

                } // container querier

                list multicast-router {
                    key "address";
                    description "The MLD multicast routers fond on this service.";

                    leaf address {
                        type types-sros:ipv6-address;
                        description
                            "The source IP address used by queries sent out by
                             this multicast router.";
                    }

                    leaf version {
                        type types-igmp:igmp-version;
                        description
                            "The version of the protocol that is sent by this
                             multicast router.";
                    }

                    leaf up-time {
                        type uint32;
                        units "seconds";
                        description
                            "The time since this multicast router has been known
                             in this service.";
                    }

                    leaf expiry-time {
                        type uint32;
                        units "seconds";
                        description "The time remaining before this multicast router is aged out.";
                    }

                    container mld-v2-states {

                        leaf general-query-interval {
                            type uint32;
                            units "seconds";
                            description "The General Query Interval used by this multicast router.";
                        }

                        leaf general-response-interval {
                            type uint32;
                            units "seconds";
                            description
                                "The General Query Response interval used by this
                                 multicast router.";
                        }

                        leaf robust-count {
                            type uint32;
                            description "The Robust Count value used by this multicast router.";
                        }

                    } // container mld-v2-states

                    container port {

                        leaf port-type {
                            type enumeration {
                                enum "sap"                          { value 0; }
                                enum "sdp"                          { value 1; }
                                enum "rvpls"                        { value 2; }
                                enum "vxlan"                        { value 3; }
                                enum "evpn-mpls"                    { value 4; }
                            }
                        }

                        leaf sap-id {
                            type types-sros:sap;
                            description "SAP identifier.";
                        }

                        leaf sdp-bind-id {
                            type types-services:sdp-bind-id;
                            description "SDP Binding identifier.";
                        }

                        leaf rvpls-service-name {
                            type types-services:service-name;
                            description "RVPLS service identifier.";
                        }

                        leaf rvpls-interface-name {
                            type types-sros:interface-name;
                            description "RVPLS interface identifier.";
                        }

                        leaf vxlan-vtep {
                            type types-sros:ip-unicast-address;
                            description "VXLAN VTEP identifier.";
                        }

                        leaf vxlan-vni {
                            type types-services:vxlan-vni;
                            description "VXLAN VNI identifier.";
                        }

                    } // container port

                } // list multicast-router

                list group {
                    key "group-address";
                    description
                        "Multicast group membership information for this service.
                         The content of this table is used by the system to
                         'proxy-report' towards the Querier.";

                    leaf group-address {
                        type types-sros:ipv6-multicast-address;
                        description "Group address of multicast channel";
                    }

                    leaf filter-mode {
                        type types-igmp:filter-mode;
                    }

                    leaf up-time {
                        type uint32;
                        units "seconds";
                        description "The time elapsed since this entry was created.";
                    }

                    list source {
                        key "source-address";
                        description "List of multicast source information for the group.";

                        leaf source-address {
                            type types-sros:ipv6-address;
                            description "Source address of multicast channel.";
                        }

                        leaf up-time {
                            type uint32;
                            units "seconds";
                            description "The time elapsed since this entry was created.";
                        }

                    } // list source

                } // list group

            } // container mld-snooping

            container pim-snooping {
                description "Enter the pim-snooping context";

                container ipv4 {
                    description "Enter the ipv4 context";

                    leaf oper-state {
                        type types-sros:oper-state;
                        description
                            "The value of the this object indicates the operational
                             state of PIM.";
                    }

                    leaf operational-mode {
                        type types-pim:pim-vpls-operational-mode;
                        description
                            "The value of the this object indicates the operational
                             mode of PIM.";
                    }

                    leaf designated-router {
                        type types-sros:ip-address;
                        description "The address of the designated router.";
                    }

                    leaf tracking-support {
                        type boolean;
                        description "The service's capability to disable Join message suppression.";
                    }

                    leaf up-time {
                        type uint32;
                        units "seconds";
                        description "The time elapsed since PIM snooping was enabled.";
                    }

                    list sg {
                        key "group-address source-address";
                        description
                            "Each entry represents a source address from which receivers are
                             interested or not interested in receiving multicast traffic.";

                        leaf group-address {
                            type types-sros:ipv4-multicast-address;
                            description
                                "The IP multicast group address for which this entry contains information.
                                 If the source-type is 'starStarRP', the value of this object will
                                 be zero and source-address will contain the address of the RP.";
                        }

                        leaf source-address {
                            type types-sros:ipv4-address;
                            description
                                "The source address for which this entry contains information.
                                 If source-type is 'starG', the value of this object will be zero.
                                 If source-type is 'starstarRP', the value of this object will be address of the RP.";
                        }

                        leaf rpf-neighbor-address {
                            type types-sros:ip-address;
                            description "The address of the RPF neighbor.";
                        }

                        leaf rpt-rpf-neighbor-address {
                            type types-sros:ip-address;
                            description "The address of the RPF neighbor on the RPT.";
                        }

                        leaf upstream-join-prune-state {
                            type enumeration {
                                enum "not-joined"                   { value 0; }
                                enum "joined"                       { value 1; }
                            }
                            description "The Upstream Join Prune state.";
                        }

                        leaf upstream-join-prune-timer {
                            type uint32;
                            units "seconds";
                            description
                                "The time remaining before the service sends another
                                 Join message to it's upstream neighbor.";
                        }

                        leaf upstream-join-prune-rpt-state {
                            type enumeration {
                                enum "not-joined-star-g"            { value 0; }
                                enum "not-pruned"                   { value 1; }
                                enum "pruned"                       { value 2; }
                            }
                            description "The Upstream Join Prune Rpt state.";
                        }

                        leaf upstream-join-prune-rpt-timer {
                            type uint32;
                            units "seconds";
                            description
                                "the delay to triggered Join(S,G,rpt) messages to prevent
                                 implosions of triggered messages.";
                        }

                        leaf join-or-prune-port-count {
                            type yang:gauge32;
                            description
                                "The number of ports on which the service received a Join or Prune message for
                                 this source group combination.";
                        }

                        leaf immediate-out-port-count {
                            type yang:gauge32;
                            description
                                "The number of ports in the immediate outgoing interface list. An outgoing
                                 list can be 'immediate' if it is built directly from the state of
                                 the relevant type as indicated by source-type.";
                        }

                        leaf inherited-out-port-count {
                            type yang:gauge32;
                            description
                                "The number of ports in the inherited outgoing interface list. An 'inherited'
                                 list inherits state from other types.";
                        }

                        leaf inherited-rpt-out-port-count {
                            type yang:gauge32;
                            description "The number of ports in the inherited outgoing interface list for (S,G,Rpt).";
                        }

                        leaf port-count {
                            type yang:gauge32;
                            description
                                "The number of ports on which the service received messages for this source group
                                 combination.";
                        }

                        leaf up-time {
                            type uint32;
                            units "seconds";
                            description "The time since this source group entry got created.";
                        }

                        container rpf-port {
                            description "The service port on which the RPF neighbor exists.";

                            leaf port-type {
                                type enumeration {
                                    enum "sap"                          { value 0; }
                                    enum "sdp"                          { value 1; }
                                    enum "rvpls"                        { value 2; }
                                    enum "vxlan"                        { value 3; }
                                    enum "evpn-mpls"                    { value 4; }
                                }
                            }

                            leaf sap-id {
                                type types-sros:sap;
                                description "SAP identifier.";
                            }

                            leaf sdp-bind-id {
                                type types-services:sdp-bind-id;
                                description "SDP Binding identifier.";
                            }

                            leaf rvpls-service-name {
                                type types-services:service-name;
                                description "RVPLS service identifier.";
                            }

                            leaf rvpls-interface-name {
                                type types-sros:interface-name;
                                description "RVPLS interface identifier.";
                            }

                            leaf vxlan-vtep {
                                type types-sros:ip-unicast-address;
                                description "VXLAN VTEP identifier.";
                            }

                            leaf vxlan-vni {
                                type types-services:vxlan-vni;
                                description "VXLAN VNI identifier.";
                            }

                        } // container rpf-port

                        list sap {
                            key "sap-id";
                            description "List of saps for an entry in sg list.";

                            leaf sap-id {
                                type types-sros:sap;
                                description "SAP identifier";
                            }

                            leaf port-flags {
                                type types-pim:vpls-sg-flags;
                                description "Set of lists to which this port belongs";
                            }

                        } // list sap

                        list spoke-sdp {
                            key "sdp-bind-id";
                            description "List of spoke-sdps for an entry in sg list.";

                            leaf sdp-bind-id {
                                type types-services:sdp-bind-id;
                                description "SDP Binding identifier as <sdp-id>:<vc-id>. sdp-id - [1..32767] vc-id - [1..4294967295].";
                            }

                            leaf port-flags {
                                type types-pim:vpls-sg-flags;
                                description "Set of lists to which this port belongs";
                            }

                        } // list spoke-sdp

                        container evpn-mpls {
                            description "Evpn-mpls tunnel for an entry in sg list.";

                            leaf port-flags {
                                type types-pim:vpls-sg-flags;
                                description "Set of lists to which this port belongs";
                            }

                        } // container evpn-mpls

                        list vxlan {
                            key "vtep vni";
                            description "List of vxlan tunnels for an entry in sg list.";

                            leaf vtep {
                                type types-sros:ip-unicast-address;
                            }

                            leaf vni {
                                type types-services:vxlan-vni;
                            }

                            leaf port-flags {
                                type types-pim:vpls-sg-flags;
                                description "Set of lists to which this port belongs";
                            }

                        } // list vxlan

                        list rvpls {
                            key "routed-service-name routed-interface-name";
                            description "List of rvpls interfaces for an entry in sg list.";

                            leaf routed-service-name {
                                type types-services:service-name;
                                description "Service name.";
                            }

                            leaf routed-interface-name {
                                type types-sros:interface-name;
                                description "Router interface name.";
                            }

                            leaf port-flags {
                                type types-pim:vpls-sg-flags;
                                description "Set of lists to which this port belongs";
                            }

                        } // list rvpls

                    } // list sg

                    container statistics {
                        description "PIM statistics for this service.";

                        leaf sg-count {
                            type yang:gauge32;
                            description "The number of sg entries for which the source address is not null.";
                        }

                        leaf star-g-count {
                            type yang:gauge32;
                            description "The number of sg entries for which the source address is null.";
                        }

                    } // container statistics

                } // container ipv4

                container ipv6 {
                    description "Enter the ipv6 context";

                    leaf oper-state {
                        type types-sros:oper-state;
                        description
                            "The value of the this object indicates the operational
                             state of PIM.";
                    }

                    leaf operational-mode {
                        type types-pim:pim-vpls-operational-mode;
                        description
                            "The value of the this object indicates the operational
                             mode of PIM.";
                    }

                    leaf designated-router {
                        type types-sros:ip-address;
                        description "The address of the designated router.";
                    }

                    leaf tracking-support {
                        type boolean;
                        description "The service's capability to disable Join message suppression.";
                    }

                    leaf up-time {
                        type uint32;
                        units "seconds";
                        description "The time elapsed since PIM snooping was enabled.";
                    }

                    list sg {
                        key "group-address source-address";
                        description
                            "Each entry represents a source address from which receivers are
                             interested or not interested in receiving multicast traffic.";

                        leaf group-address {
                            type types-sros:ipv6-multicast-address;
                            description
                                "The IP multicast group address for which this entry contains information.
                                 If the source-type is 'starStarRP', the value of this object will
                                 be zero and source-address will contain the address of the RP.";
                        }

                        leaf source-address {
                            type types-sros:ipv6-address;
                            description
                                "The source address for which this entry contains information.
                                 If source-type is 'starG', the value of this object will be zero.
                                 If source-type is 'starstarRP', the value of this object will be address of the RP.";
                        }

                        leaf rpf-neighbor-address {
                            type types-sros:ip-address;
                            description "The address of the RPF neighbor.";
                        }

                        leaf rpt-rpf-neighbor-address {
                            type types-sros:ip-address;
                            description "The address of the RPF neighbor on the RPT.";
                        }

                        leaf upstream-join-prune-state {
                            type enumeration {
                                enum "not-joined"                   { value 0; }
                                enum "joined"                       { value 1; }
                            }
                            description "The Upstream Join Prune state.";
                        }

                        leaf upstream-join-prune-timer {
                            type uint32;
                            units "seconds";
                            description
                                "The time remaining before the service sends another
                                 Join message to it's upstream neighbor.";
                        }

                        leaf upstream-join-prune-rpt-state {
                            type enumeration {
                                enum "not-joined-star-g"            { value 0; }
                                enum "not-pruned"                   { value 1; }
                                enum "pruned"                       { value 2; }
                            }
                            description "The Upstream Join Prune Rpt state.";
                        }

                        leaf upstream-join-prune-rpt-timer {
                            type uint32;
                            units "seconds";
                            description
                                "the delay to triggered Join(S,G,rpt) messages to prevent
                                 implosions of triggered messages.";
                        }

                        leaf join-or-prune-port-count {
                            type yang:gauge32;
                            description
                                "The number of ports on which the service received a Join or Prune message for
                                 this source group combination.";
                        }

                        leaf immediate-out-port-count {
                            type yang:gauge32;
                            description
                                "The number of ports in the immediate outgoing interface list. An outgoing
                                 list can be 'immediate' if it is built directly from the state of
                                 the relevant type as indicated by source-type.";
                        }

                        leaf inherited-out-port-count {
                            type yang:gauge32;
                            description
                                "The number of ports in the inherited outgoing interface list. An 'inherited'
                                 list inherits state from other types.";
                        }

                        leaf inherited-rpt-out-port-count {
                            type yang:gauge32;
                            description "The number of ports in the inherited outgoing interface list for (S,G,Rpt).";
                        }

                        leaf port-count {
                            type yang:gauge32;
                            description
                                "The number of ports on which the service received messages for this source group
                                 combination.";
                        }

                        leaf up-time {
                            type uint32;
                            units "seconds";
                            description "The time since this source group entry got created.";
                        }

                        container rpf-port {
                            description "The service port on which the RPF neighbor exists.";

                            leaf port-type {
                                type enumeration {
                                    enum "sap"                          { value 0; }
                                    enum "sdp"                          { value 1; }
                                    enum "rvpls"                        { value 2; }
                                    enum "vxlan"                        { value 3; }
                                    enum "evpn-mpls"                    { value 4; }
                                }
                            }

                            leaf sap-id {
                                type types-sros:sap;
                                description "SAP identifier.";
                            }

                            leaf sdp-bind-id {
                                type types-services:sdp-bind-id;
                                description "SDP Binding identifier.";
                            }

                            leaf rvpls-service-name {
                                type types-services:service-name;
                                description "RVPLS service identifier.";
                            }

                            leaf rvpls-interface-name {
                                type types-sros:interface-name;
                                description "RVPLS interface identifier.";
                            }

                            leaf vxlan-vtep {
                                type types-sros:ip-unicast-address;
                                description "VXLAN VTEP identifier.";
                            }

                            leaf vxlan-vni {
                                type types-services:vxlan-vni;
                                description "VXLAN VNI identifier.";
                            }

                        } // container rpf-port

                        list sap {
                            key "sap-id";
                            description "List of saps for an entry in sg list.";

                            leaf sap-id {
                                type types-sros:sap;
                                description "SAP identifier";
                            }

                            leaf port-flags {
                                type types-pim:vpls-sg-flags;
                                description "Set of lists to which this port belongs";
                            }

                        } // list sap

                        list spoke-sdp {
                            key "sdp-bind-id";
                            description "List of spoke-sdps for an entry in sg list.";

                            leaf sdp-bind-id {
                                type types-services:sdp-bind-id;
                                description "SDP Binding identifier as <sdp-id>:<vc-id>. sdp-id - [1..32767] vc-id - [1..4294967295].";
                            }

                            leaf port-flags {
                                type types-pim:vpls-sg-flags;
                                description "Set of lists to which this port belongs";
                            }

                        } // list spoke-sdp

                        container evpn-mpls {
                            description "Evpn-mpls tunnel for an entry in sg list.";

                            leaf port-flags {
                                type types-pim:vpls-sg-flags;
                                description "Set of lists to which this port belongs";
                            }

                        } // container evpn-mpls

                        list vxlan {
                            key "vtep vni";
                            description "List of vxlan tunnels for an entry in sg list.";

                            leaf vtep {
                                type types-sros:ip-unicast-address;
                            }

                            leaf vni {
                                type types-services:vxlan-vni;
                            }

                            leaf port-flags {
                                type types-pim:vpls-sg-flags;
                                description "Set of lists to which this port belongs";
                            }

                        } // list vxlan

                        list rvpls {
                            key "routed-service-name routed-interface-name";
                            description "List of rvpls interfaces for an entry in sg list.";

                            leaf routed-service-name {
                                type types-services:service-name;
                                description "Service name.";
                            }

                            leaf routed-interface-name {
                                type types-sros:interface-name;
                                description "Router interface name.";
                            }

                            leaf port-flags {
                                type types-pim:vpls-sg-flags;
                                description "Set of lists to which this port belongs";
                            }

                        } // list rvpls

                    } // list sg

                    container statistics {
                        description "PIM statistics for this service.";

                        leaf sg-count {
                            type yang:gauge32;
                            description "The number of sg entries for which the source address is not null.";
                        }

                        leaf star-g-count {
                            type yang:gauge32;
                            description "The number of sg entries for which the source address is null.";
                        }

                    } // container statistics

                } // container ipv6

                container evpn-mpls {
                    description "evpn-mpls related information";

                    container ipv4 {

                        leaf oper-state {
                            type types-sros:oper-state;
                            description
                                "The value of the this object indicates the operational
                                 state of PIM for this interface.";
                        }

                        leaf up-time {
                            type uint32;
                            units "seconds";
                            description "The time since this interface became operational.";
                        }

                        leaf group-count {
                            type uint32;
                            description
                                "The number of multicast groups which currently have this
                                 interface as an outgoing interface.";
                        }

                        leaf maximum-groups-until-now {
                            type uint32;
                            description "The highest value that 'group-count' had till now.";
                        }

                        leaf pseudo-wire-forwarder {
                            type boolean;
                            description
                                "Whether this interface is the forwarding interface
                                 of a pair of redundant pseudo-wire ports.";
                        }

                        container statistics {
                            description "The PIM statistics for Ipv4.";

                            leaf rx-packets {
                                type yang:counter32;
                                description "The number of multicast data packets received on this interface.";
                            }

                            leaf rx-hellos {
                                type yang:counter32;
                                description "The number of PIM hello messages received on this interface.";
                            }

                            leaf rx-join-prunes {
                                type yang:counter32;
                                description
                                    "The number of PIM
                                     Join Prune messages received on this interface.";
                            }

                            leaf tx-packets {
                                type yang:counter32;
                                description "The number of multicast data packets transmitted on this interface.";
                            }

                            leaf tx-join-prunes {
                                type yang:counter32;
                                description
                                    "The number of PIM
                                     Join Prune messages transmitted on this interface.";
                            }

                            leaf rx-hellos-dropped {
                                type yang:counter32;
                                description
                                    "The number of PIM Hello messages which were received on this interface but were
                                     dropped.";
                            }

                            leaf rx-neighbor-unknown {
                                type yang:counter32;
                                description
                                    "The number of PIM messages (other than Hello messages) which were received on this
                                     interface and were rejected because the adjacency with the neighbor
                                     router was not already established.";
                            }

                            leaf rx-bad-checksum-discard {
                                type yang:counter32;
                                description
                                    "The number of PIM messages received on this interface which were discarded because
                                     of bad checksum.";
                            }

                            leaf rx-bad-version-discard {
                                type yang:counter32;
                                description "The number of PIM messages with bad versions received on this interface.";
                            }

                            leaf rx-bad-encodings {
                                type yang:counter32;
                                description "The number of PIM messages with bad encodings received on this interface.";
                            }

                            leaf join-policy-drops {
                                type yang:counter32;
                                description
                                    "The number of times the join policy match resulted in dropping PIM Join-Prune
                                     Message or one of the source group contained in the message.";
                            }

                            leaf rx-join-prune-errors {
                                type yang:counter32;
                                description
                                    "The number of errors while processing Join-Prune messages received on this
                                     interface.";
                            }

                        } // container statistics

                        list neighbor {
                            key "neighbor-address";
                            description "List of the router's PIM neighbors.";

                            leaf neighbor-address {
                                type types-sros:ipv4-address;
                                description "This value indicates the IPv4 address of the PIM neighbor.";
                            }

                            leaf dr-priority {
                                type uint32;
                                description
                                    "This value indicates neighbor's DR priority which is received
                                     in the hello message. If the Hello Message did not contain
                                     the DR priority field, the value of priority will be '1'.";
                            }

                            leaf dr-priority-present {
                                type boolean;
                                description
                                    "This value of indicates whether the DR priority field was present
                                     in the Hello message received from the PIM neighbor.";
                            }

                            leaf tracking-support {
                                type boolean;
                                description
                                    "This value indicates whether the T bit in the LAN Prune Delay
                                     option was present in the Hello message. This indicates the
                                     neighbor's capability to disable Join message suppression.";
                            }

                            leaf lan-delay {
                                type uint32;
                                units "milliseconds";
                                description
                                    "This value indicates the value of lan delay field present in
                                     the Hello message received from the neighbor. ";
                            }

                            leaf lan-delay-present {
                                type boolean;
                                description
                                    "This value indicates whether the Hello message received from
                                     the neighbor contained the Lan Delay field.";
                            }

                            leaf generated-id {
                                type uint32;
                                description
                                    "This value indicates a randomly generated 32-bit value that is
                                     regenerated each time PIM forwarding is started or restarted on
                                     the interface, including when the router itself restarts.";
                            }

                            leaf override-interval {
                                type uint32;
                                units "milliseconds";
                                description
                                    "This value indicates the value of the override interval present
                                     in the Hello message.";
                            }

                            leaf up-time {
                                type uint32;
                                units "seconds";
                                description
                                    "This value indicates the time since this PIM neighbor (last)
                                     became a neighbor of the local router.";
                            }

                            leaf expiry-time {
                                type uint32;
                                units "seconds";
                                description
                                    "This value indicates the minimum time remaining before this
                                     PIM neighbor will be aged out.";
                            }

                            leaf hold-time {
                                type uint32;
                                units "seconds";
                                description
                                    "This value indicates the value of the hold time present in the
                                     Hello message.";
                            }

                            leaf join-attribute-support {
                                type boolean;
                                description
                                    "This value indicates whether the Hello Message received from
                                     the neighbor contained the Join Attribute field.";
                            }

                            list secondary-neighbor {
                                key "secondary-neighbor-address";
                                description "Each entry represents the secondary addresses advertised by PIM neighbor.";

                                leaf secondary-neighbor-address {
                                    type types-sros:ipv4-address;
                                    description
                                        "This value indicates the IPv4 address of the secondary PIM
                                         neighbor.";
                                }

                            } // list secondary-neighbor

                        } // list neighbor

                        list sg {
                            key "group-address source-address";
                            description "List of (*,G) and (S,G) entries for which this particular interface has state.";

                            leaf group-address {
                                type types-sros:ipv4-address;
                                description "The multicast group address of the entry.";
                            }

                            leaf source-address {
                                type types-sros:ipv4-address;
                                description "The source address of the multicast sender.";
                            }

                            leaf up-time {
                                type uint32;
                                units "seconds";
                                description "The time since this source group entry got created.";
                            }

                            leaf join-prune-state {
                                type types-pim:join-prune-state;
                                description
                                    "The Join Prune state for this entry on the interface.

                                     PIM Join or Prune messages are sent by the downstream routers
                                     towards the RPF' neighbor.";
                            }

                            leaf join-prune-timer {
                                type uint32;
                                units "seconds";
                                description
                                    "The time remaining before the router transitions the value of
                                     join-prune-state to 'no-info'.

                                     The timer is started or restarted when a valid Join message is
                                     received. If the value of this object is zero and
                                     join-prune-state is 'join' state, it means that the
                                     downstream router sent a holdtime of '0xffff'. In this case,
                                     join-prune-state will not transition until an appropriate
                                     cancelling of Join or Prune message is received.";
                            }

                            leaf prune-pending-timer {
                                type uint32;
                                units "seconds";
                                description
                                    "The time remaining before the router transitions the value of
                                     join-prune-state to 'no-info'.

                                     The timer is set when the PIM Prune message is received.";
                            }

                            leaf join-prune-rpt-state {
                                type types-pim:join-prune-state;
                                description
                                    "The Join Prune Rpt state for this entry on the interface.

                                     PIM Join or Prune messages are sent by the downstream routers towards the
                                     RPF' neighbor. (S,G,rpt) state is a result of receiving (S,G, rpt) JP message
                                     from the downstream router on the RP tree.";
                            }

                            leaf join-prune-rpt-timer {
                                type uint32;
                                units "seconds";
                                description
                                    "The time remaining before the router transitions the value of
                                     join-prune-rpt-state to 'no-info'.

                                     The timer is started or restarted when a valid Join message is
                                     received. If the value of this object is zero and
                                     join-prune-rpt-state is in 'join' state, it means that the
                                     downstream router sent a holdtime of '0xffff'. In this case,
                                     join-prune-rpt-state will not transition until an appropriate
                                     cancelling of Join or Prune message is received from the
                                     downstream router.";
                            }

                            leaf join-prune-rpt-pending-timer {
                                type uint32;
                                units "seconds";
                                description
                                    "The time remaining before the router transitions the value of
                                     join-prune-rpt-state to 'no-info'.

                                     The timer is set when the (S,G,rpt) PIM Prune message is received.";
                            }

                        } // list sg

                    } // container ipv4

                    container ipv6 {

                        leaf oper-state {
                            type types-sros:oper-state;
                            description
                                "The value of the this object indicates the operational
                                 state of PIM for this interface.";
                        }

                        leaf up-time {
                            type uint32;
                            units "seconds";
                            description "The time since this interface became operational.";
                        }

                        leaf group-count {
                            type uint32;
                            description
                                "The number of multicast groups which currently have this
                                 interface as an outgoing interface.";
                        }

                        leaf maximum-groups-until-now {
                            type uint32;
                            description "The highest value that 'group-count' had till now.";
                        }

                        leaf pseudo-wire-forwarder {
                            type boolean;
                            description
                                "Whether this interface is the forwarding interface
                                 of a pair of redundant pseudo-wire ports.";
                        }

                        container statistics {
                            description "The PIM statistics for Ipv6.";

                            leaf rx-packets {
                                type yang:counter32;
                                description "The number of multicast data packets received on this interface.";
                            }

                            leaf rx-hellos {
                                type yang:counter32;
                                description "The number of PIM hello messages received on this interface.";
                            }

                            leaf rx-join-prunes {
                                type yang:counter32;
                                description
                                    "The number of PIM
                                     Join Prune messages received on this interface.";
                            }

                            leaf tx-packets {
                                type yang:counter32;
                                description "The number of multicast data packets transmitted on this interface.";
                            }

                            leaf tx-join-prunes {
                                type yang:counter32;
                                description
                                    "The number of PIM
                                     Join Prune messages transmitted on this interface.";
                            }

                            leaf rx-hellos-dropped {
                                type yang:counter32;
                                description
                                    "The number of PIM Hello messages which were received on this interface but were
                                     dropped.";
                            }

                            leaf rx-neighbor-unknown {
                                type yang:counter32;
                                description
                                    "The number of PIM messages (other than Hello messages) which were received on this
                                     interface and were rejected because the adjacency with the neighbor
                                     router was not already established.";
                            }

                            leaf rx-bad-checksum-discard {
                                type yang:counter32;
                                description
                                    "The number of PIM messages received on this interface which were discarded because
                                     of bad checksum.";
                            }

                            leaf rx-bad-version-discard {
                                type yang:counter32;
                                description "The number of PIM messages with bad versions received on this interface.";
                            }

                            leaf rx-bad-encodings {
                                type yang:counter32;
                                description "The number of PIM messages with bad encodings received on this interface.";
                            }

                            leaf join-policy-drops {
                                type yang:counter32;
                                description
                                    "The number of times the join policy match resulted in dropping PIM Join-Prune
                                     Message or one of the source group contained in the message.";
                            }

                            leaf rx-join-prune-errors {
                                type yang:counter32;
                                description
                                    "The number of errors while processing Join-Prune messages received on this
                                     interface.";
                            }

                        } // container statistics

                        list neighbor {
                            key "neighbor-address";
                            description "List of the router's PIM neighbors.";

                            leaf neighbor-address {
                                type types-sros:ipv6-address;
                                description "This value indicates the IPv6 address of the PIM neighbor.";
                            }

                            leaf dr-priority {
                                type uint32;
                                description
                                    "This value indicates neighbor's DR priority which is received
                                     in the hello message. If the Hello Message did not contain
                                     the DR priority field, the value of priority will be '1'.";
                            }

                            leaf dr-priority-present {
                                type boolean;
                                description
                                    "This value of indicates whether the DR priority field was present
                                     in the Hello message received from the PIM neighbor.";
                            }

                            leaf tracking-support {
                                type boolean;
                                description
                                    "This value indicates whether the T bit in the LAN Prune Delay
                                     option was present in the Hello message. This indicates the
                                     neighbor's capability to disable Join message suppression.";
                            }

                            leaf lan-delay {
                                type uint32;
                                units "milliseconds";
                                description
                                    "This value indicates the value of lan delay field present in
                                     the Hello message received from the neighbor. ";
                            }

                            leaf lan-delay-present {
                                type boolean;
                                description
                                    "This value indicates whether the Hello message received from
                                     the neighbor contained the Lan Delay field.";
                            }

                            leaf generated-id {
                                type uint32;
                                description
                                    "This value indicates a randomly generated 32-bit value that is
                                     regenerated each time PIM forwarding is started or restarted on
                                     the interface, including when the router itself restarts.";
                            }

                            leaf override-interval {
                                type uint32;
                                units "milliseconds";
                                description
                                    "This value indicates the value of the override interval present
                                     in the Hello message.";
                            }

                            leaf up-time {
                                type uint32;
                                units "seconds";
                                description
                                    "This value indicates the time since this PIM neighbor (last)
                                     became a neighbor of the local router.";
                            }

                            leaf expiry-time {
                                type uint32;
                                units "seconds";
                                description
                                    "This value indicates the minimum time remaining before this
                                     PIM neighbor will be aged out.";
                            }

                            leaf hold-time {
                                type uint32;
                                units "seconds";
                                description
                                    "This value indicates the value of the hold time present in the
                                     Hello message.";
                            }

                            leaf join-attribute-support {
                                type boolean;
                                description
                                    "This value indicates whether the Hello Message received from
                                     the neighbor contained the Join Attribute field.";
                            }

                            list secondary-neighbor {
                                key "secondary-neighbor-address";
                                description "Each entry represents the secondary addresses advertised by PIM neighbor.";

                                leaf secondary-neighbor-address {
                                    type types-sros:ipv6-address;
                                    description
                                        "This value indicates the IPv6 address of the secondary PIM
                                         neighbor.";
                                }

                            } // list secondary-neighbor

                        } // list neighbor

                        list sg {
                            key "group-address source-address";
                            description "List of (*,G) and (S,G) entries for which this particular interface has state.";

                            leaf group-address {
                                type types-sros:ipv6-address;
                                description "The multicast group address of the entry.";
                            }

                            leaf source-address {
                                type types-sros:ipv6-address;
                                description "The source address of the multicast sender.";
                            }

                            leaf up-time {
                                type uint32;
                                units "seconds";
                                description "The time since this source group entry got created.";
                            }

                            leaf join-prune-state {
                                type types-pim:join-prune-state;
                                description
                                    "The Join Prune state for this entry on the interface.

                                     PIM Join or Prune messages are sent by the downstream routers
                                     towards the RPF' neighbor.";
                            }

                            leaf join-prune-timer {
                                type uint32;
                                units "seconds";
                                description
                                    "The time remaining before the router transitions the value of
                                     join-prune-state to 'no-info'.

                                     The timer is started or restarted when a valid Join message is
                                     received. If the value of this object is zero and
                                     join-prune-state is 'join' state, it means that the
                                     downstream router sent a holdtime of '0xffff'. In this case,
                                     join-prune-state will not transition until an appropriate
                                     cancelling of Join or Prune message is received.";
                            }

                            leaf prune-pending-timer {
                                type uint32;
                                units "seconds";
                                description
                                    "The time remaining before the router transitions the value of
                                     join-prune-state to 'no-info'.

                                     The timer is set when the PIM Prune message is received.";
                            }

                            leaf join-prune-rpt-state {
                                type types-pim:join-prune-state;
                                description
                                    "The Join Prune Rpt state for this entry on the interface.

                                     PIM Join or Prune messages are sent by the downstream routers towards the
                                     RPF' neighbor. (S,G,rpt) state is a result of receiving (S,G, rpt) JP message
                                     from the downstream router on the RP tree.";
                            }

                            leaf join-prune-rpt-timer {
                                type uint32;
                                units "seconds";
                                description
                                    "The time remaining before the router transitions the value of
                                     join-prune-rpt-state to 'no-info'.

                                     The timer is started or restarted when a valid Join message is
                                     received. If the value of this object is zero and
                                     join-prune-rpt-state is in 'join' state, it means that the
                                     downstream router sent a holdtime of '0xffff'. In this case,
                                     join-prune-rpt-state will not transition until an appropriate
                                     cancelling of Join or Prune message is received from the
                                     downstream router.";
                            }

                            leaf join-prune-rpt-pending-timer {
                                type uint32;
                                units "seconds";
                                description
                                    "The time remaining before the router transitions the value of
                                     join-prune-rpt-state to 'no-info'.

                                     The timer is set when the (S,G,rpt) PIM Prune message is received.";
                            }

                        } // list sg

                    } // container ipv6

                } // container evpn-mpls

            } // container pim-snooping

            container bgp-evpn {
                description "Enter the bgp-evpn context";

                leaf creation-origin {
                    type types-sros:creation-origin;
                    description "Creation origin of BGP-EVPN in the service";
                }

                container mac-duplication {
                    description "Enter the mac-duplication context";

                    leaf num-duplicate-macs {
                        type uint32;
                        description "Number of duplicate MAC addresses";
                    }

                } // container mac-duplication

                list mpls {
                    key "bgp-instance";
                    description "Enter the mpls list instance";

                    leaf bgp-instance {
                        type int32 {
                            range "1..2";
                        }
                        description "BGP instance";
                    }

                    container ingress {
                        description "Bgp Evpn Mpls ingress information";

                        leaf unicast-label {
                            type int32;
                            description "Label advertised for ingress unicast traffic";
                        }

                        leaf bum-label {
                            type int32;
                            description "Label advertised for ingress BUM traffic";
                        }

                    } // container ingress

                } // list mpls

            } // container bgp-evpn

            list endpoint {
                key "name";
                description "Enter the endpoint list instance";

                leaf name {
                    type types-sros:named-item;
                    description "Service endpoint name";
                }

                leaf revert-time-count-down {
                    type types-services:revert-time;
                    units "seconds";
                    description
                        "The count down timer that is used before reverting back to the primary spoke-sdp
                         defined on this service endpoint, after having failed over to
                         a backup spoke-sdp.

                         This count down timer begins after primary Spoke SDP becomes
                         operational.";
                }

                leaf creation-origin {
                    type enumeration {
                        enum "manual"                       { value 0; }
                        enum "bgp-vpws"                     { value 1; }
                    }
                    description "The origin mechanism used to create this endpoint.";
                }

                container tx-active {
                    description "Current transmit active object information";

                    leaf type {
                        type enumeration {
                            enum "none"                         { value 0; }
                            enum "sap"                          { value 1; }
                            enum "sdp-bind"                     { value 2; }
                            enum "sdp-fec"                      { value 3; }
                            enum "evpn-mpls"                    { value 4; }
                        }
                        description "The type of endpoint object that is current transmit active. ";
                    }

                    leaf object {
                        type string;
                        description "The object that is transmit active";
                    }

                    leaf change-count {
                        type uint32;
                        description "The number of times active transmit change has taken place.";
                    }

                    leaf up-time {
                        type uint32;
                        units "centiseconds";
                        description
                            "The active 'up' time of the endpoint object
                             that is current transmit active.";
                    }

                } // container tx-active

            } // list endpoint

            container eth-cfm {
                description "Enter the eth-cfm context";

                list mep {
                    key "md-admin-name ma-admin-name mep-id";
                    description "Enter the mep list instance";

                    leaf md-admin-name {
                        type leafref {
                            path "../../../../../eth-cfm/domain/md-admin-name";
                        }
                        description "Admin-assigned maintenance domain index value";
                    }

                    leaf ma-admin-name {
                        type leafref {
                            path "../../../../../eth-cfm/domain[md-admin-name=current()/../md-admin-name]/association/ma-admin-name";
                        }
                        description "Admin-assigned maintenance association index value";
                    }

                    leaf mep-id {
                        type types-eth-cfm:mep-id-type;
                        description "MEP identifier";
                    }

                } // list mep

            } // container eth-cfm

            list spoke-sdp {
                key "sdp-bind-id";
                description "Enter the spoke-sdp list instance";

                leaf sdp-bind-id {
                    type types-services:sdp-bind-id;
                    description "SDP Binding identifier as <sdp-id>:<vc-id>. sdp-id - [1..32767] vc-id - [1..4294967295].";
                }

                leaf oper-state {
                    type enumeration {
                        enum "up"                           { value 1; }
                        enum "down"                         { value 5; }
                    }
                    description "Indicates the operating status of this Service-SDP binding.";
                }

                leaf oper-flags {
                    type bits {
                        bit sdp-bind-admin-down            { position 0; }
                        bit svc-admin-down                 { position 1; }
                        bit stitching-svc-txdown           { position 2; }
                        bit sdp-oper-down                  { position 3; }
                        bit sdp-path-mtu-too-small         { position 4; }
                        bit no-ingress-vc-label            { position 5; }
                        bit no-egress-vc-label             { position 6; }
                        bit svc-mtu-mismatch               { position 7; }
                        bit vc-type-mismatch               { position 8; }
                        bit relearn-limit-exceeded         { position 9; }
                        bit ies-if-admin-down              { position 10; }
                        bit released-ingress-vc-label      { position 11; }
                        bit labels-exhausted               { position 12; }
                        bit svc-param-mismatch             { position 13; }
                        bit insufficient-bandwidth         { position 14; }
                        bit pw-peer-fault-status-bits      { position 15; }
                        bit mesh-sdp-down                  { position 16; }
                        bit not-managed-by-mcring          { position 17; }
                        bit out-of-resource                { position 18; }
                        bit mh-standby                     { position 19; }
                        bit oam-down-mep-fault             { position 20; }
                        bit oam-up-mep-fault               { position 21; }
                        bit standby-sig-slave-tx-down      { position 22; }
                        bit oper-grp-down                  { position 23; }
                        bit withdrawn-ingress-vc-label     { position 24; }
                        bit vpls-pmsi-down                 { position 25; }
                        bit rec-prot-src-mac               { position 26; }
                        bit peer-fault-status-tx-down      { position 27; }
                        bit evpn-route-conflict            { position 28; }
                        bit admin-locked                   { position 29; }
                        bit evpn-p2mp-conflict             { position 30; }
                        bit label-stack-limit-exceeded     { position 31; }
                    }
                    description
                        "This object indicates all the conditions that affect the
                         operating status of this SDP Bind.";
                }

                leaf pw-peer-status-bits {
                    type bits {
                        bit pw-not-forwarding              { position 0; }
                        bit lac-ingress-fault              { position 1; }
                        bit lac-egress-fault               { position 2; }
                        bit psn-ingress-fault              { position 3; }
                        bit psn-egress-fault               { position 4; }
                        bit pw-fwding-standby              { position 5; }
                    }
                    description
                        "Indicates bits set by the LDP peer when there is a fault on its
                         side of the pseudowire";
                }

                leaf pw-local-status-bits {
                    type bits {
                        bit pw-not-forwarding              { position 0; }
                        bit lac-ingress-fault              { position 1; }
                        bit lac-egress-fault               { position 2; }
                        bit psn-ingress-fault              { position 3; }
                        bit psn-egress-fault               { position 4; }
                        bit pw-fwding-standby              { position 5; }
                    }
                    description "Indicates locally set bits when there is a fault.";
                }

                leaf peer-vccv-cv-bits {
                    type bits {
                        bit icmp-ping                      { position 0; }
                        bit lsp-ping                       { position 1; }
                        bit bfd-fault-detection            { position 2; }
                        bit bfd-fault-detection-and-signalling { position 3; }
                    }
                    description "Indicates CV type bits set by the LDP peer if it supports VCCV.";
                }

                leaf peer-vccv-cc-bits {
                    type bits {
                        bit pwe3-control-word              { position 0; }
                        bit mpls-router-alert-label        { position 1; }
                        bit mpls-pw-demultiplex-or-label   { position 2; }
                    }
                    description "Indicates CC type bits set by the LDP peer if it supports VCCV.";
                }

                leaf oper-control-word {
                    type boolean;
                    description "Status of control word.";
                }

                leaf pw-fault-ip-address {
                    type types-sros:ip-address;
                    description "Faulty IP address sent by peer.";
                }

                leaf class-forwarding-oper-state {
                    type types-sros:oper-state;
                    description "Operational state of forwarding-class based forwarding on this SDP bind.";
                }

                leaf creation-origin {
                    type types-sros:creation-origin;
                    description "Creation origin of the service.";
                }

                leaf oper-hash-label {
                    type boolean;
                    description "Indicates the negotiated value of hash lavel that is used on this SDP binding.";
                }

                leaf min-required-sdp-oper-mtu {
                    type int32;
                    description "Minimum required SDP MTU size used with this SDP binding.";
                }

                leaf bpdus-translated-frames-encap {
                    type enumeration {
                        enum "undefined"                    { value 1; }
                        enum "disabled"                     { value 2; }
                        enum "pvst"                         { value 3; }
                        enum "stp"                          { value 4; }
                        enum "pvst-rw"                      { value 5; }
                    }
                    description
                        "Operational BPDU encapsulation used for BPDU
                         translated frames.";
                }

                container ingress {
                    description "Enter the ingress context";

                    leaf oper-label {
                        type uint32;
                        description "MPLS service label used by the far-end device to send packets to the local PEs sdp-bind.";
                    }

                    container statistics {
                        description "Ingress side statistics";

                        leaf forwarded-packets {
                            type yang:counter64;
                            description "Forwarded packets";
                        }

                        leaf forwarded-octets {
                            type yang:counter64;
                            description "Forwarded octets";
                        }

                        leaf dropped-packets {
                            type yang:counter64;
                            description "Dropped packets";
                        }

                        leaf dropped-octets {
                            type yang:counter64;
                            description "Dropped octets";
                        }

                    } // container statistics

                } // container ingress

                container egress {
                    description "Enter the egress context";

                    leaf oper-label {
                        type uint32;
                        description "MPLS service label used to send packets to the far-end device via this sdp-bind.";
                    }

                    container statistics {
                        description "Egress side statistics";

                        leaf forwarded-packets {
                            type yang:counter64;
                            description "Forwarded packets";
                        }

                        leaf forwarded-octets {
                            type yang:counter64;
                            description "Forwarded octets";
                        }

                    } // container statistics

                } // container egress

                container mvpls {
                    description "MVPLS state information";

                    leaf prune-state {
                        type types-services:mvpls-prune-state;
                        description
                            "MVPLS prune state of the spoke SDP. The leaf
                             will be set to not-applicable if the spoke SDP is
                             not managed by a MVPLS. If the SDP is managed the state
                             reflects whether or not it is pruned by the STP instance
                             running in the MVPLS instance.";
                    }

                    leaf managing-service {
                        type types-sros:named-item-or-empty;
                        description
                            "Service where the STP instance is running that is managing this
                             spoke SDP. This leaf is only valid if mvpls-prune-state is
                             different from not-applicable.";
                    }

                    leaf managing-sdp-bind {
                        type types-services:state-sdp-bind-id-or-zero;
                        description
                            "SDP bind id in the mVPLS instance specified in mgmt-service that
                             is controlling this SDP. This leaf is only valid if
                             mvpls-prune-state is different from not-applicable.";
                    }

                } // container mvpls

                container topology-change-bit {
                    description "Topology change bit state information";

                    leaf in-bpdus {
                        type uint32;
                        description
                            "Number BPDUs received on this SDP Bind
                             with the Topology Change bit set.";
                    }

                    leaf out-bpdus {
                        type uint32;
                        description
                            "Number BPDUs sent out this SDP Bind
                             with the Topology Change bit set.";
                    }

                } // container topology-change-bit

                container fdb {
                    description "Enter the fdb context";

                    container statistics {
                        description "FDB usage information";

                        leaf total {
                            type int32;
                            description "Number of entries allocated in the FDB ";
                        }

                        leaf static {
                            type int32;
                            description "Number of static entries in the FDB";
                        }

                        leaf learned {
                            type int32;
                            description "Number of learned entries in the FDB";
                        }

                        leaf oam {
                            type int32;
                            description "Number of OAM entries in the FDB";
                        }

                        leaf conditional-static {
                            type int32;
                            description "Number of conditional static entries in the FDB";
                        }

                        leaf dhcp {
                            type int32;
                            description "Number of dhcp-learned entries in the FDB";
                        }

                        leaf host {
                            type int32;
                            description "Number of host-learned entries in the FDB";
                        }

                        leaf interface {
                            type int32;
                            description "Number of interface entries in the FDB";
                        }

                        leaf bgp-evpn {
                            type int32;
                            description "Number of bgp-evpn entries in the FDB";
                        }

                        leaf evpn-static {
                            type int32;
                            description "Number of evpn static entries in the FDB";
                        }

                    } // container statistics

                    container protected-src-mac-violation {
                        description "Protected source MAC violation state information";

                        leaf oper-state {
                            type boolean;
                            description "Operational state of the protected-source MAC feature.";
                        }

                        leaf oper-action {
                            type enumeration {
                                enum "oper-down"                    { value 1; }
                                enum "alarm-only"                   { value 2; }
                                enum "discard-frame"                { value 3; }
                            }
                            description "Operational state of the protected-source MAC violation action.";
                        }

                    } // container protected-src-mac-violation

                    container mac-move {
                        description "Mac-move information";

                        leaf remaining-down-time {
                            type union {
                                type uint32 {
                                    range "1..65534";
                                }
                                type enumeration {
                                    enum "never"                        { value 0; }
                                    enum "indefinite"                   { value 65535; }
                                }
                            }
                            units "seconds";
                            description
                                "The time remaining until the relearn-limit-exceeded oper-flag is cleared.
                                 When the value is 'indefinite', this flag will not be cleared automatically.
                                 Relearn-limit-exceeded oper-flag is set when sdp-bind is brought down 
                                 when mac-move max-rate is exceeded.";
                        }

                        leaf remaining-retry-reset-time {
                            type union {
                                type uint32 {
                                    range "1..4294967295";
                                }
                                type enumeration {
                                    enum "never"                        { value 0; }
                                }
                            }
                            units "seconds";
                            description
                                "The time remaining to reset the mac-move retries-left
                                 when the oper-state of sdp-bind is up.";
                        }

                        leaf rate-exceed-times-left {
                            type union {
                                type uint32 {
                                    range "1..4294967294";
                                }
                                type enumeration {
                                    enum "unlimited"                    { value -1; }
                                    enum "none"                         { value 0; }
                                }
                            }
                            description
                                "Counts down the number of times this SDP bind can exceed the
                                 VPLS mac-move max-rate and still be automatically
                                 brought up.";
                        }

                    } // container mac-move

                } // container fdb

                container dhcp {
                    description "Enter the dhcp context";

                    container statistics {
                        description "Packet statistics";

                        container client-packets {
                            description "Client packet statistics";

                            leaf snooped {
                                type yang:counter32;
                                description "The number of DHCP client packets that have been snooped on this SAP.";
                            }

                            leaf forwarded {
                                type yang:counter32;
                                description "The number  of  DHCP  client  packets  that have been forwarded on this SAP.";
                            }

                            leaf dropped {
                                type yang:counter32;
                                description "The number  of  DHCP  client  packets  that have been dropped on this SAP.";
                            }

                            container proxied {
                                description "Proxied packet statistics";

                                leaf radius {
                                    type yang:counter32;
                                    description
                                        "The number of DHCP client packets that have been proxied on this SAP
                                         based on data received from a RADIUS server.";
                                }

                                leaf lease-split {
                                    type yang:counter32;
                                    description
                                        "The number of DHCP client packets that have been proxied on this SAP
                                         based on lease state.";
                                }

                            } // container proxied

                        } // container client-packets

                        container server-packets {
                            description "Server packet statistics";

                            leaf snooped {
                                type yang:counter32;
                                description "The number of DHCP server packets that have been snooped on this SAP.";
                            }

                            leaf forwarded {
                                type yang:counter32;
                                description "The number  of  DHCP  server  packets  that have been forwarded on this SAP.";
                            }

                            leaf dropped {
                                type yang:counter32;
                                description "The number  of  DHCP  server  packets  that have been dropped on this SAP.";
                            }

                        } // container server-packets

                        container spoofed {
                            description "Spoofed packet statistics";

                            leaf force-renews {
                                type yang:counter32;
                                description "The number of DHCP FORCERENEW messages spoofed on this SAP to the DHCP clients.";
                            }

                            leaf releases {
                                type yang:counter32;
                                description "The number of DHCP RELEASE messages spoofed on this SAP to the DHCP server.";
                            }

                        } // container spoofed

                    } // container statistics

                } // container dhcp

                container igmp-snooping {
                    description "Enter the igmp-snooping context";

                    container mcac {
                        description "Enter the mcac context";

                        leaf in-use-mandatory-bandwidth {
                            type uint32;
                            units "kilobps";
                            description
                                "The in-use bandwidth for the mandatory channels for this
                                 protocol interface instance.";
                        }

                        leaf in-use-optional-bandwidth {
                            type uint32;
                            units "kilobps";
                            description
                                "The in-use bandwidth for the optional channels for this
                                 protocol interface instance.";
                        }

                        leaf available-mandatory-bandwidth {
                            type uint32;
                            units "kilobps";
                            description
                                "The pre-reserved bandwidth for the mandatory channels for
                                 this interface instance.";
                        }

                        leaf available-optional-bandwidth {
                            type uint32;
                            units "kilobps";
                            description "The available bandwidth for this interface instance.";
                        }

                        leaf values-in-transit {
                            type boolean;
                            description
                                "The operational (available and in-use mandatory/optional) value for the
                                 following objects is in transition due to configuration change:
                                 - available-mandatory-bandwidth
                                 - available-bandwidth
                                 - in-use-mandatory-bandwidth
                                 - in-use-optional-bandwidth.";
                        }

                    } // container mcac

                    container statistics {
                        description "The IGMP statistics.";

                        container received {
                            description "Received message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                        } // container received

                        container transmitted {
                            description "Transmit message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                            leaf errors {
                                type yang:counter32;
                                description "Transmission Errors.";
                            }

                        } // container transmitted

                        container forwarded {
                            description "Forwarded message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                            leaf unknown-types {
                                type yang:counter32;
                                description "Unknown types.";
                            }

                            leaf errors {
                                type yang:counter32;
                                description "Forwarding Errors.";
                            }

                        } // container forwarded

                        container error {
                            description "Error message statistics.";

                            leaf bad-length {
                                type yang:counter32;
                                description "Bad length.";
                            }

                            leaf bad-ip-checksum {
                                type yang:counter32;
                                description "Bad Ip checksum.";
                            }

                            leaf unknown-type {
                                type yang:counter32;
                                description "Unknown type.";
                            }

                            leaf wrong-version {
                                type yang:counter32;
                                description "Wrong version.";
                            }

                            leaf import-policy-drops {
                                type yang:counter32;
                                description
                                    "Number of times we matched the host IP address or group or
                                     source addresses specified in the import policy.";
                            }

                            leaf missing-router-alert {
                                type yang:counter32;
                                description "Router alert flag is not set.";
                            }

                            leaf bad-encoding {
                                type yang:counter32;
                                description "Badly encoded.";
                            }

                            leaf local-scope {
                                type yang:counter32;
                                description "Link-local scope multicast group address.";
                            }

                            leaf mcac-policy-drops {
                                type yang:counter32;
                                description
                                    "Number of times a join is dropped because of applying a
                                     multicast CAC policy.";
                            }

                            leaf reached-maximum-number-groups {
                                type yang:counter32;
                                description
                                    "Number of times a join is dropped because we reached the maximum
                                     number of groups.";
                            }

                            leaf reached-maximum-number-group-sources {
                                type yang:counter32;
                                description
                                    "Number of times a join is dropped because we reached the maximum
                                     number group-source combinations.";
                            }

                            leaf reached-maximum-number-sources {
                                type yang:counter32;
                                description
                                    "Number of times a join is dropped because we reached the maximum
                                     number of sources per group.";
                            }

                            leaf out-of-memory-drops {
                                type yang:counter32;
                                description "Number of times a join is dropped because we ran out of memory.";
                            }

                            leaf bad-igmp-checksum {
                                type yang:counter32;
                                description
                                    "Number of times a packet is dropped because of a bad IGMP
                                     header checksum.";
                            }

                            leaf zero-source-ip-addr {
                                type yang:counter32;
                                description "Number of times a packet is dropped because it has a zero source ip address.";
                            }

                            leaf send-query-cfg-drops {
                                type yang:counter32;
                                description "Number of times a query is dropped because send-queries is configured.";
                            }

                        } // container error

                    } // container statistics

                    list group {
                        key "group-address";
                        description "Multicast group membership information that joined on this port.";

                        leaf group-address {
                            type types-sros:ipv4-multicast-address;
                            description "Group address of static IGMP multicast channel";
                        }

                        leaf group-type {
                            type types-igmp:learn-type;
                        }

                        leaf filter-mode {
                            type types-igmp:filter-mode;
                        }

                        leaf expiry-time {
                            type uint32;
                            units "seconds";
                            description "The time left before multicast group timeout.";
                        }

                        leaf up-time {
                            type uint32;
                            units "seconds";
                            description "The time elapsed since this entry was created.";
                        }

                        leaf v1-host-timer {
                            type uint32;
                            units "seconds";
                            description
                                "The time remaining until the local router will assume that
                                 there are no longer any version 1 members.";
                        }

                        leaf v2-host-timer {
                            type uint32;
                            units "seconds";
                            description
                                "The time remaining until the local router will assume that
                                 there are no longer any version 2 members.";
                        }

                        leaf igmp-compatibility-mode {
                            type types-igmp:igmp-version;
                            description "Compatibility with older version routers.";
                        }

                        list source {
                            key "source-address";
                            description "List of multicast source information of the multicast group.";

                            leaf source-address {
                                type types-sros:ipv4-address;
                                description "Source address of multicast channel.";
                            }

                            leaf source-type {
                                type types-igmp:learn-type;
                            }

                            leaf forwarding-state {
                                type types-igmp:forwarding-state;
                                description "Traffic forwardeding state on this port.";
                            }

                            leaf expiry-time {
                                type uint32;
                                units "seconds";
                                description "The time left before multicast group timeout.";
                            }

                            leaf up-time {
                                type uint32;
                                units "seconds";
                                description "The time elapsed since this entry was created.";
                            }

                        } // list source

                    } // list group

                } // container igmp-snooping

                container mld-snooping {
                    description "Enter the mld-snooping context";

                    container statistics {
                        description "The MLD statistics.";

                        container received {
                            description "Received message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf leaves {
                                type yang:counter32;
                                description "Leaves.";
                            }

                            leaf drops {
                                type yang:counter32;
                                description "Total number of dropped packets.";
                            }

                        } // container received

                        container transmitted {
                            description "Transmit message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf leaves {
                                type yang:counter32;
                                description "Leaves.";
                            }

                            leaf drops {
                                type yang:counter32;
                                description "Total number of dropped packets.";
                            }

                            leaf errors {
                                type yang:counter32;
                                description "Transmission Errors.";
                            }

                        } // container transmitted

                        container forwarded {
                            description "Forwarded message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf leaves {
                                type yang:counter32;
                                description "Leaves.";
                            }

                            leaf drops {
                                type yang:counter32;
                                description "Total number of dropped packets.";
                            }

                            leaf unknown-types {
                                type yang:counter32;
                                description "Unknown types.";
                            }

                            leaf errors {
                                type yang:counter32;
                                description "Forwarding Errors.";
                            }

                        } // container forwarded

                        container error {
                            description "Error message statistics.";

                            leaf bad-length {
                                type yang:counter32;
                                description "Bad length.";
                            }

                            leaf unknown-type {
                                type yang:counter32;
                                description "Unknown type.";
                            }

                            leaf wrong-version {
                                type yang:counter32;
                                description "Wrong version.";
                            }

                            leaf import-policy-drops {
                                type yang:counter32;
                                description
                                    "Number of times we matched the host IP address or group or
                                     source addresses specified in the import policy.";
                            }

                            leaf missing-router-alert {
                                type yang:counter32;
                                description "Router alert flag is not set.";
                            }

                            leaf bad-encoding {
                                type yang:counter32;
                                description "Badly encoded.";
                            }

                            leaf local-scope {
                                type yang:counter32;
                                description "Link-local scope multicast group address.";
                            }

                            leaf reserved-scope {
                                type yang:counter32;
                                description "Reserved scope multicast group address.";
                            }

                            leaf reached-maximum-number-groups {
                                type yang:counter32;
                                description
                                    "Number of times a join is dropped because we reached the maximum
                                     number of groups.";
                            }

                            leaf reached-maximum-number-group-sources {
                                type yang:counter32;
                                description
                                    "Number of times a join is dropped because we reached the maximum
                                     number group-source combinations.";
                            }

                            leaf reached-maximum-number-sources {
                                type yang:counter32;
                                description
                                    "Number of times a join is dropped because we reached the maximum
                                     number of sources per group.";
                            }

                            leaf out-of-memory-drops {
                                type yang:counter32;
                                description "Number of times a join is dropped because we ran out of memory.";
                            }

                            leaf bad-mld-checksum {
                                type yang:counter32;
                                description
                                    "Number of times a packet is dropped because of a bad MLD
                                     header checksum.";
                            }

                            leaf zero-source-ip-addr {
                                type yang:counter32;
                                description "Number of times a packet is dropped because it has a zero source ip address.";
                            }

                            leaf send-query-cfg-drops {
                                type yang:counter32;
                                description "Number of times a query is dropped because send-queries is configured.";
                            }

                        } // container error

                    } // container statistics

                    list group {
                        key "group-address";
                        description "Multicast group membership information that joined on this port.";

                        leaf group-address {
                            type types-sros:ipv6-multicast-address;
                            description "Group address of multicast channel";
                        }

                        leaf group-type {
                            type types-igmp:learn-type;
                        }

                        leaf filter-mode {
                            type types-igmp:filter-mode;
                        }

                        leaf expiry-time {
                            type uint32;
                            units "seconds";
                            description "The time left before multicast group timeout.";
                        }

                        leaf up-time {
                            type uint32;
                            units "seconds";
                            description "The time elapsed since this entry was created.";
                        }

                        leaf v1-host-timer {
                            type uint32;
                            units "seconds";
                            description
                                "The time remaining until the local router will assume that
                                 there are no longer any version 1 members.";
                        }

                        leaf mld-compatibility-mode {
                            type types-igmp:mld-version;
                            description "Compatibility with older version routers.";
                        }

                        list source {
                            key "source-address";
                            description "List of multicast source information of the multicast group.";

                            leaf source-address {
                                type types-sros:ipv6-address;
                                description "Source address of multicast channel.";
                            }

                            leaf source-type {
                                type types-igmp:learn-type;
                            }

                            leaf forwarding-state {
                                type types-igmp:forwarding-state;
                                description "Traffic forwardeding state on this port.";
                            }

                            leaf expiry-time {
                                type uint32;
                                units "seconds";
                                description "The time left before multicast group timeout.";
                            }

                            leaf up-time {
                                type uint32;
                                units "seconds";
                                description "The time elapsed since this entry was created.";
                            }

                        } // list source

                    } // list group

                } // container mld-snooping

                container pim-snooping {
                    description "Enter the pim-snooping context";

                    container ipv4 {
                        description "PIM parameters for ipv4 on this service.";

                        leaf oper-state {
                            type types-sros:oper-state;
                            description
                                "The value of the this object indicates the operational
                                 state of PIM for this interface.";
                        }

                        leaf up-time {
                            type uint32;
                            units "seconds";
                            description "The time since this interface became operational.";
                        }

                        leaf group-count {
                            type uint32;
                            description
                                "The number of multicast groups which currently have this
                                 interface as an outgoing interface.";
                        }

                        leaf maximum-groups-until-now {
                            type uint32;
                            description "The highest value that 'group-count' had till now.";
                        }

                        leaf pseudo-wire-forwarder {
                            type boolean;
                            description
                                "Whether this interface is the forwarding interface
                                 of a pair of redundant pseudo-wire ports.";
                        }

                        container statistics {
                            description "The PIM statistics for Ipv4.";

                            leaf rx-packets {
                                type yang:counter32;
                                description "The number of multicast data packets received on this interface.";
                            }

                            leaf rx-hellos {
                                type yang:counter32;
                                description "The number of PIM hello messages received on this interface.";
                            }

                            leaf rx-join-prunes {
                                type yang:counter32;
                                description
                                    "The number of PIM
                                     Join Prune messages received on this interface.";
                            }

                            leaf tx-packets {
                                type yang:counter32;
                                description "The number of multicast data packets transmitted on this interface.";
                            }

                            leaf tx-join-prunes {
                                type yang:counter32;
                                description
                                    "The number of PIM
                                     Join Prune messages transmitted on this interface.";
                            }

                            leaf rx-hellos-dropped {
                                type yang:counter32;
                                description
                                    "The number of PIM Hello messages which were received on this interface but were
                                     dropped.";
                            }

                            leaf rx-neighbor-unknown {
                                type yang:counter32;
                                description
                                    "The number of PIM messages (other than Hello messages) which were received on this
                                     interface and were rejected because the adjacency with the neighbor
                                     router was not already established.";
                            }

                            leaf rx-bad-checksum-discard {
                                type yang:counter32;
                                description
                                    "The number of PIM messages received on this interface which were discarded because
                                     of bad checksum.";
                            }

                            leaf rx-bad-version-discard {
                                type yang:counter32;
                                description "The number of PIM messages with bad versions received on this interface.";
                            }

                            leaf rx-bad-encodings {
                                type yang:counter32;
                                description "The number of PIM messages with bad encodings received on this interface.";
                            }

                            leaf join-policy-drops {
                                type yang:counter32;
                                description
                                    "The number of times the join policy match resulted in dropping PIM Join-Prune
                                     Message or one of the source group contained in the message.";
                            }

                            leaf rx-join-prune-errors {
                                type yang:counter32;
                                description
                                    "The number of errors while processing Join-Prune messages received on this
                                     interface.";
                            }

                        } // container statistics

                        list neighbor {
                            key "neighbor-address";
                            description "List of the router's PIM neighbors.";

                            leaf neighbor-address {
                                type types-sros:ipv4-address;
                                description "This value indicates the IPv4 address of the PIM neighbor.";
                            }

                            leaf dr-priority {
                                type uint32;
                                description
                                    "This value indicates neighbor's DR priority which is received
                                     in the hello message. If the Hello Message did not contain
                                     the DR priority field, the value of priority will be '1'.";
                            }

                            leaf dr-priority-present {
                                type boolean;
                                description
                                    "This value of indicates whether the DR priority field was present
                                     in the Hello message received from the PIM neighbor.";
                            }

                            leaf tracking-support {
                                type boolean;
                                description
                                    "This value indicates whether the T bit in the LAN Prune Delay
                                     option was present in the Hello message. This indicates the
                                     neighbor's capability to disable Join message suppression.";
                            }

                            leaf lan-delay {
                                type uint32;
                                units "milliseconds";
                                description
                                    "This value indicates the value of lan delay field present in
                                     the Hello message received from the neighbor. ";
                            }

                            leaf lan-delay-present {
                                type boolean;
                                description
                                    "This value indicates whether the Hello message received from
                                     the neighbor contained the Lan Delay field.";
                            }

                            leaf generated-id {
                                type uint32;
                                description
                                    "This value indicates a randomly generated 32-bit value that is
                                     regenerated each time PIM forwarding is started or restarted on
                                     the interface, including when the router itself restarts.";
                            }

                            leaf override-interval {
                                type uint32;
                                units "milliseconds";
                                description
                                    "This value indicates the value of the override interval present
                                     in the Hello message.";
                            }

                            leaf up-time {
                                type uint32;
                                units "seconds";
                                description
                                    "This value indicates the time since this PIM neighbor (last)
                                     became a neighbor of the local router.";
                            }

                            leaf expiry-time {
                                type uint32;
                                units "seconds";
                                description
                                    "This value indicates the minimum time remaining before this
                                     PIM neighbor will be aged out.";
                            }

                            leaf hold-time {
                                type uint32;
                                units "seconds";
                                description
                                    "This value indicates the value of the hold time present in the
                                     Hello message.";
                            }

                            leaf join-attribute-support {
                                type boolean;
                                description
                                    "This value indicates whether the Hello Message received from
                                     the neighbor contained the Join Attribute field.";
                            }

                            list secondary-neighbor {
                                key "secondary-neighbor-address";
                                description "Each entry represents the secondary addresses advertised by PIM neighbor.";

                                leaf secondary-neighbor-address {
                                    type types-sros:ipv4-address;
                                    description
                                        "This value indicates the IPv4 address of the secondary PIM
                                         neighbor.";
                                }

                            } // list secondary-neighbor

                        } // list neighbor

                        list sg {
                            key "group-address source-address";
                            description "List of (*,G) and (S,G) entries for which this particular interface has state.";

                            leaf group-address {
                                type types-sros:ipv4-address;
                                description "The multicast group address of the entry.";
                            }

                            leaf source-address {
                                type types-sros:ipv4-address;
                                description "The source address of the multicast sender.";
                            }

                            leaf up-time {
                                type uint32;
                                units "seconds";
                                description "The time since this source group entry got created.";
                            }

                            leaf join-prune-state {
                                type types-pim:join-prune-state;
                                description
                                    "The Join Prune state for this entry on the interface.

                                     PIM Join or Prune messages are sent by the downstream routers
                                     towards the RPF' neighbor.";
                            }

                            leaf join-prune-timer {
                                type uint32;
                                units "seconds";
                                description
                                    "The time remaining before the router transitions the value of
                                     join-prune-state to 'no-info'.

                                     The timer is started or restarted when a valid Join message is
                                     received. If the value of this object is zero and
                                     join-prune-state is 'join' state, it means that the
                                     downstream router sent a holdtime of '0xffff'. In this case,
                                     join-prune-state will not transition until an appropriate
                                     cancelling of Join or Prune message is received.";
                            }

                            leaf prune-pending-timer {
                                type uint32;
                                units "seconds";
                                description
                                    "The time remaining before the router transitions the value of
                                     join-prune-state to 'no-info'.

                                     The timer is set when the PIM Prune message is received.";
                            }

                            leaf join-prune-rpt-state {
                                type types-pim:join-prune-state;
                                description
                                    "The Join Prune Rpt state for this entry on the interface.

                                     PIM Join or Prune messages are sent by the downstream routers towards the
                                     RPF' neighbor. (S,G,rpt) state is a result of receiving (S,G, rpt) JP message
                                     from the downstream router on the RP tree.";
                            }

                            leaf join-prune-rpt-timer {
                                type uint32;
                                units "seconds";
                                description
                                    "The time remaining before the router transitions the value of
                                     join-prune-rpt-state to 'no-info'.

                                     The timer is started or restarted when a valid Join message is
                                     received. If the value of this object is zero and
                                     join-prune-rpt-state is in 'join' state, it means that the
                                     downstream router sent a holdtime of '0xffff'. In this case,
                                     join-prune-rpt-state will not transition until an appropriate
                                     cancelling of Join or Prune message is received from the
                                     downstream router.";
                            }

                            leaf join-prune-rpt-pending-timer {
                                type uint32;
                                units "seconds";
                                description
                                    "The time remaining before the router transitions the value of
                                     join-prune-rpt-state to 'no-info'.

                                     The timer is set when the (S,G,rpt) PIM Prune message is received.";
                            }

                        } // list sg

                    } // container ipv4

                    container ipv6 {
                        description "PIM parameters for ipv6 on this service.";

                        leaf oper-state {
                            type types-sros:oper-state;
                            description
                                "The value of the this object indicates the operational
                                 state of PIM for this interface.";
                        }

                        leaf up-time {
                            type uint32;
                            units "seconds";
                            description "The time since this interface became operational.";
                        }

                        leaf group-count {
                            type uint32;
                            description
                                "The number of multicast groups which currently have this
                                 interface as an outgoing interface.";
                        }

                        leaf maximum-groups-until-now {
                            type uint32;
                            description "The highest value that 'group-count' had till now.";
                        }

                        leaf pseudo-wire-forwarder {
                            type boolean;
                            description
                                "Whether this interface is the forwarding interface
                                 of a pair of redundant pseudo-wire ports.";
                        }

                        container statistics {
                            description "The PIM statistics for Ipv6.";

                            leaf rx-packets {
                                type yang:counter32;
                                description "The number of multicast data packets received on this interface.";
                            }

                            leaf rx-hellos {
                                type yang:counter32;
                                description "The number of PIM hello messages received on this interface.";
                            }

                            leaf rx-join-prunes {
                                type yang:counter32;
                                description
                                    "The number of PIM
                                     Join Prune messages received on this interface.";
                            }

                            leaf tx-packets {
                                type yang:counter32;
                                description "The number of multicast data packets transmitted on this interface.";
                            }

                            leaf tx-join-prunes {
                                type yang:counter32;
                                description
                                    "The number of PIM
                                     Join Prune messages transmitted on this interface.";
                            }

                            leaf rx-hellos-dropped {
                                type yang:counter32;
                                description
                                    "The number of PIM Hello messages which were received on this interface but were
                                     dropped.";
                            }

                            leaf rx-neighbor-unknown {
                                type yang:counter32;
                                description
                                    "The number of PIM messages (other than Hello messages) which were received on this
                                     interface and were rejected because the adjacency with the neighbor
                                     router was not already established.";
                            }

                            leaf rx-bad-checksum-discard {
                                type yang:counter32;
                                description
                                    "The number of PIM messages received on this interface which were discarded because
                                     of bad checksum.";
                            }

                            leaf rx-bad-version-discard {
                                type yang:counter32;
                                description "The number of PIM messages with bad versions received on this interface.";
                            }

                            leaf rx-bad-encodings {
                                type yang:counter32;
                                description "The number of PIM messages with bad encodings received on this interface.";
                            }

                            leaf join-policy-drops {
                                type yang:counter32;
                                description
                                    "The number of times the join policy match resulted in dropping PIM Join-Prune
                                     Message or one of the source group contained in the message.";
                            }

                            leaf rx-join-prune-errors {
                                type yang:counter32;
                                description
                                    "The number of errors while processing Join-Prune messages received on this
                                     interface.";
                            }

                        } // container statistics

                        list neighbor {
                            key "neighbor-address";
                            description "List of the router's PIM neighbors.";

                            leaf neighbor-address {
                                type types-sros:ipv6-address;
                                description "This value indicates the IPv6 address of the PIM neighbor.";
                            }

                            leaf dr-priority {
                                type uint32;
                                description
                                    "This value indicates neighbor's DR priority which is received
                                     in the hello message. If the Hello Message did not contain
                                     the DR priority field, the value of priority will be '1'.";
                            }

                            leaf dr-priority-present {
                                type boolean;
                                description
                                    "This value of indicates whether the DR priority field was present
                                     in the Hello message received from the PIM neighbor.";
                            }

                            leaf tracking-support {
                                type boolean;
                                description
                                    "This value indicates whether the T bit in the LAN Prune Delay
                                     option was present in the Hello message. This indicates the
                                     neighbor's capability to disable Join message suppression.";
                            }

                            leaf lan-delay {
                                type uint32;
                                units "milliseconds";
                                description
                                    "This value indicates the value of lan delay field present in
                                     the Hello message received from the neighbor. ";
                            }

                            leaf lan-delay-present {
                                type boolean;
                                description
                                    "This value indicates whether the Hello message received from
                                     the neighbor contained the Lan Delay field.";
                            }

                            leaf generated-id {
                                type uint32;
                                description
                                    "This value indicates a randomly generated 32-bit value that is
                                     regenerated each time PIM forwarding is started or restarted on
                                     the interface, including when the router itself restarts.";
                            }

                            leaf override-interval {
                                type uint32;
                                units "milliseconds";
                                description
                                    "This value indicates the value of the override interval present
                                     in the Hello message.";
                            }

                            leaf up-time {
                                type uint32;
                                units "seconds";
                                description
                                    "This value indicates the time since this PIM neighbor (last)
                                     became a neighbor of the local router.";
                            }

                            leaf expiry-time {
                                type uint32;
                                units "seconds";
                                description
                                    "This value indicates the minimum time remaining before this
                                     PIM neighbor will be aged out.";
                            }

                            leaf hold-time {
                                type uint32;
                                units "seconds";
                                description
                                    "This value indicates the value of the hold time present in the
                                     Hello message.";
                            }

                            leaf join-attribute-support {
                                type boolean;
                                description
                                    "This value indicates whether the Hello Message received from
                                     the neighbor contained the Join Attribute field.";
                            }

                            list secondary-neighbor {
                                key "secondary-neighbor-address";
                                description "Each entry represents the secondary addresses advertised by PIM neighbor.";

                                leaf secondary-neighbor-address {
                                    type types-sros:ipv6-address;
                                    description
                                        "This value indicates the IPv6 address of the secondary PIM
                                         neighbor.";
                                }

                            } // list secondary-neighbor

                        } // list neighbor

                        list sg {
                            key "group-address source-address";
                            description "List of (*,G) and (S,G) entries for which this particular interface has state.";

                            leaf group-address {
                                type types-sros:ipv6-address;
                                description "The multicast group address of the entry.";
                            }

                            leaf source-address {
                                type types-sros:ipv6-address;
                                description "The source address of the multicast sender.";
                            }

                            leaf up-time {
                                type uint32;
                                units "seconds";
                                description "The time since this source group entry got created.";
                            }

                            leaf join-prune-state {
                                type types-pim:join-prune-state;
                                description
                                    "The Join Prune state for this entry on the interface.

                                     PIM Join or Prune messages are sent by the downstream routers
                                     towards the RPF' neighbor.";
                            }

                            leaf join-prune-timer {
                                type uint32;
                                units "seconds";
                                description
                                    "The time remaining before the router transitions the value of
                                     join-prune-state to 'no-info'.

                                     The timer is started or restarted when a valid Join message is
                                     received. If the value of this object is zero and
                                     join-prune-state is 'join' state, it means that the
                                     downstream router sent a holdtime of '0xffff'. In this case,
                                     join-prune-state will not transition until an appropriate
                                     cancelling of Join or Prune message is received.";
                            }

                            leaf prune-pending-timer {
                                type uint32;
                                units "seconds";
                                description
                                    "The time remaining before the router transitions the value of
                                     join-prune-state to 'no-info'.

                                     The timer is set when the PIM Prune message is received.";
                            }

                            leaf join-prune-rpt-state {
                                type types-pim:join-prune-state;
                                description
                                    "The Join Prune Rpt state for this entry on the interface.

                                     PIM Join or Prune messages are sent by the downstream routers towards the
                                     RPF' neighbor. (S,G,rpt) state is a result of receiving (S,G, rpt) JP message
                                     from the downstream router on the RP tree.";
                            }

                            leaf join-prune-rpt-timer {
                                type uint32;
                                units "seconds";
                                description
                                    "The time remaining before the router transitions the value of
                                     join-prune-rpt-state to 'no-info'.

                                     The timer is started or restarted when a valid Join message is
                                     received. If the value of this object is zero and
                                     join-prune-rpt-state is in 'join' state, it means that the
                                     downstream router sent a holdtime of '0xffff'. In this case,
                                     join-prune-rpt-state will not transition until an appropriate
                                     cancelling of Join or Prune message is received from the
                                     downstream router.";
                            }

                            leaf join-prune-rpt-pending-timer {
                                type uint32;
                                units "seconds";
                                description
                                    "The time remaining before the router transitions the value of
                                     join-prune-rpt-state to 'no-info'.

                                     The timer is set when the (S,G,rpt) PIM Prune message is received.";
                            }

                        } // list sg

                    } // container ipv6

                } // container pim-snooping

                container eth-cfm {
                    description "Enter the eth-cfm context";

                    list mep {
                        key "md-admin-name ma-admin-name mep-id";
                        description "Enter the mep list instance";

                        leaf md-admin-name {
                            type leafref {
                                path "../../../../../../eth-cfm/domain/md-admin-name";
                            }
                            description "Admin-assigned maintenance domain index value";
                        }

                        leaf ma-admin-name {
                            type leafref {
                                path "../../../../../../eth-cfm/domain[md-admin-name=current()/../md-admin-name]/association/ma-admin-name";
                            }
                            description "Admin-assigned maintenance association index value";
                        }

                        leaf mep-id {
                            type types-eth-cfm:mep-id-type;
                            description "MEP identifier";
                        }

                    } // list mep

                } // container eth-cfm

            } // list spoke-sdp

            list mesh-sdp {
                key "sdp-bind-id";
                description "Enter the mesh-sdp list instance";

                leaf sdp-bind-id {
                    type types-services:sdp-bind-id;
                    description "SDP Binding identifier as <sdp-id>:<vc-id>. sdp-id - [1..32767] vc-id - [1..4294967295].";
                }

                leaf oper-state {
                    type enumeration {
                        enum "up"                           { value 1; }
                        enum "down"                         { value 5; }
                    }
                    description "Indicates the operating status of this Service-SDP binding.";
                }

                leaf oper-flags {
                    type bits {
                        bit sdp-bind-admin-down            { position 0; }
                        bit svc-admin-down                 { position 1; }
                        bit stitching-svc-txdown           { position 2; }
                        bit sdp-oper-down                  { position 3; }
                        bit sdp-path-mtu-too-small         { position 4; }
                        bit no-ingress-vc-label            { position 5; }
                        bit no-egress-vc-label             { position 6; }
                        bit svc-mtu-mismatch               { position 7; }
                        bit vc-type-mismatch               { position 8; }
                        bit relearn-limit-exceeded         { position 9; }
                        bit ies-if-admin-down              { position 10; }
                        bit released-ingress-vc-label      { position 11; }
                        bit labels-exhausted               { position 12; }
                        bit svc-param-mismatch             { position 13; }
                        bit insufficient-bandwidth         { position 14; }
                        bit pw-peer-fault-status-bits      { position 15; }
                        bit mesh-sdp-down                  { position 16; }
                        bit not-managed-by-mcring          { position 17; }
                        bit out-of-resource                { position 18; }
                        bit mh-standby                     { position 19; }
                        bit oam-down-mep-fault             { position 20; }
                        bit oam-up-mep-fault               { position 21; }
                        bit standby-sig-slave-tx-down      { position 22; }
                        bit oper-grp-down                  { position 23; }
                        bit withdrawn-ingress-vc-label     { position 24; }
                        bit vpls-pmsi-down                 { position 25; }
                        bit rec-prot-src-mac               { position 26; }
                        bit peer-fault-status-tx-down      { position 27; }
                        bit evpn-route-conflict            { position 28; }
                        bit admin-locked                   { position 29; }
                        bit evpn-p2mp-conflict             { position 30; }
                        bit label-stack-limit-exceeded     { position 31; }
                    }
                    description
                        "This object indicates all the conditions that affect the
                         operating status of this SDP Bind.";
                }

                leaf pw-peer-status-bits {
                    type bits {
                        bit pw-not-forwarding              { position 0; }
                        bit lac-ingress-fault              { position 1; }
                        bit lac-egress-fault               { position 2; }
                        bit psn-ingress-fault              { position 3; }
                        bit psn-egress-fault               { position 4; }
                        bit pw-fwding-standby              { position 5; }
                    }
                    description
                        "Indicates bits set by the LDP peer when there is a fault on its
                         side of the pseudowire";
                }

                leaf pw-local-status-bits {
                    type bits {
                        bit pw-not-forwarding              { position 0; }
                        bit lac-ingress-fault              { position 1; }
                        bit lac-egress-fault               { position 2; }
                        bit psn-ingress-fault              { position 3; }
                        bit psn-egress-fault               { position 4; }
                        bit pw-fwding-standby              { position 5; }
                    }
                    description "Indicates locally set bits when there is a fault.";
                }

                leaf peer-vccv-cv-bits {
                    type bits {
                        bit icmp-ping                      { position 0; }
                        bit lsp-ping                       { position 1; }
                        bit bfd-fault-detection            { position 2; }
                        bit bfd-fault-detection-and-signalling { position 3; }
                    }
                    description "Indicates CV type bits set by the LDP peer if it supports VCCV.";
                }

                leaf peer-vccv-cc-bits {
                    type bits {
                        bit pwe3-control-word              { position 0; }
                        bit mpls-router-alert-label        { position 1; }
                        bit mpls-pw-demultiplex-or-label   { position 2; }
                    }
                    description "Indicates CC type bits set by the LDP peer if it supports VCCV.";
                }

                leaf oper-control-word {
                    type boolean;
                    description "Status of control word.";
                }

                leaf pw-fault-ip-address {
                    type types-sros:ip-address;
                    description "Faulty IP address sent by peer.";
                }

                leaf class-forwarding-oper-state {
                    type types-sros:oper-state;
                    description "Operational state of forwarding-class based forwarding on this SDP bind.";
                }

                leaf creation-origin {
                    type types-sros:creation-origin;
                    description "Creation origin of the service.";
                }

                leaf oper-hash-label {
                    type boolean;
                    description "Indicates the negotiated value of hash lavel that is used on this SDP binding.";
                }

                leaf min-required-sdp-oper-mtu {
                    type int32;
                    description "Minimum required SDP MTU size used with this SDP binding.";
                }

                container ingress {
                    description "Enter the ingress context";

                    leaf oper-label {
                        type uint32;
                        description "MPLS service label used by the far-end device to send packets to the local PEs sdp-bind.";
                    }

                    container statistics {
                        description "Ingress side statistics";

                        leaf forwarded-packets {
                            type yang:counter64;
                            description "Forwarded packets";
                        }

                        leaf forwarded-octets {
                            type yang:counter64;
                            description "Forwarded octets";
                        }

                        leaf dropped-packets {
                            type yang:counter64;
                            description "Dropped packets";
                        }

                        leaf dropped-octets {
                            type yang:counter64;
                            description "Dropped octets";
                        }

                    } // container statistics

                } // container ingress

                container egress {
                    description "Enter the egress context";

                    leaf oper-label {
                        type uint32;
                        description "MPLS service label used to send packets to the far-end device via this sdp-bind.";
                    }

                    container statistics {
                        description "Egress side statistics";

                        leaf forwarded-packets {
                            type yang:counter64;
                            description "Forwarded packets";
                        }

                        leaf forwarded-octets {
                            type yang:counter64;
                            description "Forwarded octets";
                        }

                    } // container statistics

                } // container egress

                container fdb {
                    description "Enter the fdb context";

                    container statistics {
                        description "FDB usage information";

                        leaf static {
                            type int32;
                            description "Number of static entries in the FDB";
                        }

                        leaf learned {
                            type int32;
                            description "Number of learned entries in the FDB";
                        }

                        leaf oam {
                            type int32;
                            description "Number of OAM entries in the FDB";
                        }

                        leaf conditional-static {
                            type int32;
                            description "Number of conditional static entries in the FDB";
                        }

                    } // container statistics

                    container protected-src-mac-violation {
                        description "Protected source MAC violation state information";

                        leaf oper-state {
                            type boolean;
                            description "Operational state of the protected-source MAC feature.";
                        }

                        leaf oper-action {
                            type enumeration {
                                enum "oper-down"                    { value 1; }
                                enum "alarm-only"                   { value 2; }
                                enum "discard-frame"                { value 3; }
                            }
                            description "Operational state of the protected-source MAC violation action.";
                        }

                    } // container protected-src-mac-violation

                } // container fdb

                container dhcp {
                    description "Enter the dhcp context";

                    container statistics {
                        description "Packet statistics";

                        container client-packets {
                            description "Client packet statistics";

                            leaf snooped {
                                type yang:counter32;
                                description "The number of DHCP client packets that have been snooped on this SAP.";
                            }

                            leaf forwarded {
                                type yang:counter32;
                                description "The number  of  DHCP  client  packets  that have been forwarded on this SAP.";
                            }

                            leaf dropped {
                                type yang:counter32;
                                description "The number  of  DHCP  client  packets  that have been dropped on this SAP.";
                            }

                            container proxied {
                                description "Proxied packet statistics";

                                leaf radius {
                                    type yang:counter32;
                                    description
                                        "The number of DHCP client packets that have been proxied on this SAP
                                         based on data received from a RADIUS server.";
                                }

                                leaf lease-split {
                                    type yang:counter32;
                                    description
                                        "The number of DHCP client packets that have been proxied on this SAP
                                         based on lease state.";
                                }

                            } // container proxied

                        } // container client-packets

                        container server-packets {
                            description "Server packet statistics";

                            leaf snooped {
                                type yang:counter32;
                                description "The number of DHCP server packets that have been snooped on this SAP.";
                            }

                            leaf forwarded {
                                type yang:counter32;
                                description "The number  of  DHCP  server  packets  that have been forwarded on this SAP.";
                            }

                            leaf dropped {
                                type yang:counter32;
                                description "The number  of  DHCP  server  packets  that have been dropped on this SAP.";
                            }

                        } // container server-packets

                        container spoofed {
                            description "Spoofed packet statistics";

                            leaf force-renews {
                                type yang:counter32;
                                description "The number of DHCP FORCERENEW messages spoofed on this SAP to the DHCP clients.";
                            }

                            leaf releases {
                                type yang:counter32;
                                description "The number of DHCP RELEASE messages spoofed on this SAP to the DHCP server.";
                            }

                        } // container spoofed

                    } // container statistics

                } // container dhcp

                container igmp-snooping {
                    description "Enter the igmp-snooping context";

                    container mcac {
                        description "Enter the mcac context";

                        leaf in-use-mandatory-bandwidth {
                            type uint32;
                            units "kilobps";
                            description
                                "The in-use bandwidth for the mandatory channels for this
                                 protocol interface instance.";
                        }

                        leaf in-use-optional-bandwidth {
                            type uint32;
                            units "kilobps";
                            description
                                "The in-use bandwidth for the optional channels for this
                                 protocol interface instance.";
                        }

                        leaf available-mandatory-bandwidth {
                            type uint32;
                            units "kilobps";
                            description
                                "The pre-reserved bandwidth for the mandatory channels for
                                 this interface instance.";
                        }

                        leaf available-optional-bandwidth {
                            type uint32;
                            units "kilobps";
                            description "The available bandwidth for this interface instance.";
                        }

                        leaf values-in-transit {
                            type boolean;
                            description
                                "The operational (available and in-use mandatory/optional) value for the
                                 following objects is in transition due to configuration change:
                                 - available-mandatory-bandwidth
                                 - available-bandwidth
                                 - in-use-mandatory-bandwidth
                                 - in-use-optional-bandwidth.";
                        }

                    } // container mcac

                    container statistics {
                        description "The IGMP statistics.";

                        container received {
                            description "Received message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                        } // container received

                        container transmitted {
                            description "Transmit message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                            leaf errors {
                                type yang:counter32;
                                description "Transmission Errors.";
                            }

                        } // container transmitted

                        container forwarded {
                            description "Forwarded message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                            leaf unknown-types {
                                type yang:counter32;
                                description "Unknown types.";
                            }

                            leaf errors {
                                type yang:counter32;
                                description "Forwarding Errors.";
                            }

                        } // container forwarded

                        container error {
                            description "Error message statistics.";

                            leaf bad-length {
                                type yang:counter32;
                                description "Bad length.";
                            }

                            leaf bad-ip-checksum {
                                type yang:counter32;
                                description "Bad Ip checksum.";
                            }

                            leaf unknown-type {
                                type yang:counter32;
                                description "Unknown type.";
                            }

                            leaf wrong-version {
                                type yang:counter32;
                                description "Wrong version.";
                            }

                            leaf import-policy-drops {
                                type yang:counter32;
                                description
                                    "Number of times we matched the host IP address or group or
                                     source addresses specified in the import policy.";
                            }

                            leaf missing-router-alert {
                                type yang:counter32;
                                description "Router alert flag is not set.";
                            }

                            leaf bad-encoding {
                                type yang:counter32;
                                description "Badly encoded.";
                            }

                            leaf local-scope {
                                type yang:counter32;
                                description "Link-local scope multicast group address.";
                            }

                            leaf mcac-policy-drops {
                                type yang:counter32;
                                description
                                    "Number of times a join is dropped because of applying a
                                     multicast CAC policy.";
                            }

                            leaf reached-maximum-number-groups {
                                type yang:counter32;
                                description
                                    "Number of times a join is dropped because we reached the maximum
                                     number of groups.";
                            }

                            leaf reached-maximum-number-group-sources {
                                type yang:counter32;
                                description
                                    "Number of times a join is dropped because we reached the maximum
                                     number group-source combinations.";
                            }

                            leaf reached-maximum-number-sources {
                                type yang:counter32;
                                description
                                    "Number of times a join is dropped because we reached the maximum
                                     number of sources per group.";
                            }

                            leaf out-of-memory-drops {
                                type yang:counter32;
                                description "Number of times a join is dropped because we ran out of memory.";
                            }

                            leaf bad-igmp-checksum {
                                type yang:counter32;
                                description
                                    "Number of times a packet is dropped because of a bad IGMP
                                     header checksum.";
                            }

                            leaf zero-source-ip-addr {
                                type yang:counter32;
                                description "Number of times a packet is dropped because it has a zero source ip address.";
                            }

                            leaf send-query-cfg-drops {
                                type yang:counter32;
                                description "Number of times a query is dropped because send-queries is configured.";
                            }

                        } // container error

                    } // container statistics

                    list group {
                        key "group-address";
                        description "Multicast group membership information that joined on this port.";

                        leaf group-address {
                            type types-sros:ipv4-multicast-address;
                            description "Group address of static IGMP multicast channel";
                        }

                        leaf group-type {
                            type types-igmp:learn-type;
                        }

                        leaf filter-mode {
                            type types-igmp:filter-mode;
                        }

                        leaf expiry-time {
                            type uint32;
                            units "seconds";
                            description "The time left before multicast group timeout.";
                        }

                        leaf up-time {
                            type uint32;
                            units "seconds";
                            description "The time elapsed since this entry was created.";
                        }

                        leaf v1-host-timer {
                            type uint32;
                            units "seconds";
                            description
                                "The time remaining until the local router will assume that
                                 there are no longer any version 1 members.";
                        }

                        leaf v2-host-timer {
                            type uint32;
                            units "seconds";
                            description
                                "The time remaining until the local router will assume that
                                 there are no longer any version 2 members.";
                        }

                        leaf igmp-compatibility-mode {
                            type types-igmp:igmp-version;
                            description "Compatibility with older version routers.";
                        }

                        list source {
                            key "source-address";
                            description "List of multicast source information of the multicast group.";

                            leaf source-address {
                                type types-sros:ipv4-address;
                                description "Source address of multicast channel.";
                            }

                            leaf source-type {
                                type types-igmp:learn-type;
                            }

                            leaf forwarding-state {
                                type types-igmp:forwarding-state;
                                description "Traffic forwardeding state on this port.";
                            }

                            leaf expiry-time {
                                type uint32;
                                units "seconds";
                                description "The time left before multicast group timeout.";
                            }

                            leaf up-time {
                                type uint32;
                                units "seconds";
                                description "The time elapsed since this entry was created.";
                            }

                        } // list source

                    } // list group

                } // container igmp-snooping

                container mld-snooping {
                    description "Enter the mld-snooping context";

                    container statistics {
                        description "The MLD statistics.";

                        container received {
                            description "Received message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf leaves {
                                type yang:counter32;
                                description "Leaves.";
                            }

                            leaf drops {
                                type yang:counter32;
                                description "Total number of dropped packets.";
                            }

                        } // container received

                        container transmitted {
                            description "Transmit message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf leaves {
                                type yang:counter32;
                                description "Leaves.";
                            }

                            leaf drops {
                                type yang:counter32;
                                description "Total number of dropped packets.";
                            }

                            leaf errors {
                                type yang:counter32;
                                description "Transmission Errors.";
                            }

                        } // container transmitted

                        container forwarded {
                            description "Forwarded message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf leaves {
                                type yang:counter32;
                                description "Leaves.";
                            }

                            leaf drops {
                                type yang:counter32;
                                description "Total number of dropped packets.";
                            }

                            leaf unknown-types {
                                type yang:counter32;
                                description "Unknown types.";
                            }

                            leaf errors {
                                type yang:counter32;
                                description "Forwarding Errors.";
                            }

                        } // container forwarded

                        container error {
                            description "Error message statistics.";

                            leaf bad-length {
                                type yang:counter32;
                                description "Bad length.";
                            }

                            leaf unknown-type {
                                type yang:counter32;
                                description "Unknown type.";
                            }

                            leaf wrong-version {
                                type yang:counter32;
                                description "Wrong version.";
                            }

                            leaf import-policy-drops {
                                type yang:counter32;
                                description
                                    "Number of times we matched the host IP address or group or
                                     source addresses specified in the import policy.";
                            }

                            leaf missing-router-alert {
                                type yang:counter32;
                                description "Router alert flag is not set.";
                            }

                            leaf bad-encoding {
                                type yang:counter32;
                                description "Badly encoded.";
                            }

                            leaf local-scope {
                                type yang:counter32;
                                description "Link-local scope multicast group address.";
                            }

                            leaf reserved-scope {
                                type yang:counter32;
                                description "Reserved scope multicast group address.";
                            }

                            leaf reached-maximum-number-groups {
                                type yang:counter32;
                                description
                                    "Number of times a join is dropped because we reached the maximum
                                     number of groups.";
                            }

                            leaf reached-maximum-number-group-sources {
                                type yang:counter32;
                                description
                                    "Number of times a join is dropped because we reached the maximum
                                     number group-source combinations.";
                            }

                            leaf reached-maximum-number-sources {
                                type yang:counter32;
                                description
                                    "Number of times a join is dropped because we reached the maximum
                                     number of sources per group.";
                            }

                            leaf out-of-memory-drops {
                                type yang:counter32;
                                description "Number of times a join is dropped because we ran out of memory.";
                            }

                            leaf bad-mld-checksum {
                                type yang:counter32;
                                description
                                    "Number of times a packet is dropped because of a bad MLD
                                     header checksum.";
                            }

                            leaf zero-source-ip-addr {
                                type yang:counter32;
                                description "Number of times a packet is dropped because it has a zero source ip address.";
                            }

                            leaf send-query-cfg-drops {
                                type yang:counter32;
                                description "Number of times a query is dropped because send-queries is configured.";
                            }

                        } // container error

                    } // container statistics

                    list group {
                        key "group-address";
                        description "Multicast group membership information that joined on this port.";

                        leaf group-address {
                            type types-sros:ipv6-multicast-address;
                            description "Group address of multicast channel";
                        }

                        leaf group-type {
                            type types-igmp:learn-type;
                        }

                        leaf filter-mode {
                            type types-igmp:filter-mode;
                        }

                        leaf expiry-time {
                            type uint32;
                            units "seconds";
                            description "The time left before multicast group timeout.";
                        }

                        leaf up-time {
                            type uint32;
                            units "seconds";
                            description "The time elapsed since this entry was created.";
                        }

                        leaf v1-host-timer {
                            type uint32;
                            units "seconds";
                            description
                                "The time remaining until the local router will assume that
                                 there are no longer any version 1 members.";
                        }

                        leaf mld-compatibility-mode {
                            type types-igmp:mld-version;
                            description "Compatibility with older version routers.";
                        }

                        list source {
                            key "source-address";
                            description "List of multicast source information of the multicast group.";

                            leaf source-address {
                                type types-sros:ipv6-address;
                                description "Source address of multicast channel.";
                            }

                            leaf source-type {
                                type types-igmp:learn-type;
                            }

                            leaf forwarding-state {
                                type types-igmp:forwarding-state;
                                description "Traffic forwardeding state on this port.";
                            }

                            leaf expiry-time {
                                type uint32;
                                units "seconds";
                                description "The time left before multicast group timeout.";
                            }

                            leaf up-time {
                                type uint32;
                                units "seconds";
                                description "The time elapsed since this entry was created.";
                            }

                        } // list source

                    } // list group

                } // container mld-snooping

                container pim-snooping {
                    description "PIM parameters.";

                    container ipv4 {
                        description "PIM parameters for ipv4 on this service.";

                        leaf oper-state {
                            type types-sros:oper-state;
                            description
                                "The value of the this object indicates the operational
                                 state of PIM for this interface.";
                        }

                        leaf up-time {
                            type uint32;
                            units "seconds";
                            description "The time since this interface became operational.";
                        }

                        leaf group-count {
                            type uint32;
                            description
                                "The number of multicast groups which currently have this
                                 interface as an outgoing interface.";
                        }

                        leaf maximum-groups-until-now {
                            type uint32;
                            description "The highest value that 'group-count' had till now.";
                        }

                        leaf pseudo-wire-forwarder {
                            type boolean;
                            description
                                "Whether this interface is the forwarding interface
                                 of a pair of redundant pseudo-wire ports.";
                        }

                        container statistics {
                            description "The PIM statistics for Ipv4.";

                            leaf rx-packets {
                                type yang:counter32;
                                description "The number of multicast data packets received on this interface.";
                            }

                            leaf rx-hellos {
                                type yang:counter32;
                                description "The number of PIM hello messages received on this interface.";
                            }

                            leaf rx-join-prunes {
                                type yang:counter32;
                                description
                                    "The number of PIM
                                     Join Prune messages received on this interface.";
                            }

                            leaf tx-packets {
                                type yang:counter32;
                                description "The number of multicast data packets transmitted on this interface.";
                            }

                            leaf tx-join-prunes {
                                type yang:counter32;
                                description
                                    "The number of PIM
                                     Join Prune messages transmitted on this interface.";
                            }

                            leaf rx-hellos-dropped {
                                type yang:counter32;
                                description
                                    "The number of PIM Hello messages which were received on this interface but were
                                     dropped.";
                            }

                            leaf rx-neighbor-unknown {
                                type yang:counter32;
                                description
                                    "The number of PIM messages (other than Hello messages) which were received on this
                                     interface and were rejected because the adjacency with the neighbor
                                     router was not already established.";
                            }

                            leaf rx-bad-checksum-discard {
                                type yang:counter32;
                                description
                                    "The number of PIM messages received on this interface which were discarded because
                                     of bad checksum.";
                            }

                            leaf rx-bad-version-discard {
                                type yang:counter32;
                                description "The number of PIM messages with bad versions received on this interface.";
                            }

                            leaf rx-bad-encodings {
                                type yang:counter32;
                                description "The number of PIM messages with bad encodings received on this interface.";
                            }

                            leaf join-policy-drops {
                                type yang:counter32;
                                description
                                    "The number of times the join policy match resulted in dropping PIM Join-Prune
                                     Message or one of the source group contained in the message.";
                            }

                            leaf rx-join-prune-errors {
                                type yang:counter32;
                                description
                                    "The number of errors while processing Join-Prune messages received on this
                                     interface.";
                            }

                        } // container statistics

                        list neighbor {
                            key "neighbor-address";
                            description "List of the router's PIM neighbors.";

                            leaf neighbor-address {
                                type types-sros:ipv4-address;
                                description "This value indicates the IPv4 address of the PIM neighbor.";
                            }

                            leaf dr-priority {
                                type uint32;
                                description
                                    "This value indicates neighbor's DR priority which is received
                                     in the hello message. If the Hello Message did not contain
                                     the DR priority field, the value of priority will be '1'.";
                            }

                            leaf dr-priority-present {
                                type boolean;
                                description
                                    "This value of indicates whether the DR priority field was present
                                     in the Hello message received from the PIM neighbor.";
                            }

                            leaf tracking-support {
                                type boolean;
                                description
                                    "This value indicates whether the T bit in the LAN Prune Delay
                                     option was present in the Hello message. This indicates the
                                     neighbor's capability to disable Join message suppression.";
                            }

                            leaf lan-delay {
                                type uint32;
                                units "milliseconds";
                                description
                                    "This value indicates the value of lan delay field present in
                                     the Hello message received from the neighbor. ";
                            }

                            leaf lan-delay-present {
                                type boolean;
                                description
                                    "This value indicates whether the Hello message received from
                                     the neighbor contained the Lan Delay field.";
                            }

                            leaf generated-id {
                                type uint32;
                                description
                                    "This value indicates a randomly generated 32-bit value that is
                                     regenerated each time PIM forwarding is started or restarted on
                                     the interface, including when the router itself restarts.";
                            }

                            leaf override-interval {
                                type uint32;
                                units "milliseconds";
                                description
                                    "This value indicates the value of the override interval present
                                     in the Hello message.";
                            }

                            leaf up-time {
                                type uint32;
                                units "seconds";
                                description
                                    "This value indicates the time since this PIM neighbor (last)
                                     became a neighbor of the local router.";
                            }

                            leaf expiry-time {
                                type uint32;
                                units "seconds";
                                description
                                    "This value indicates the minimum time remaining before this
                                     PIM neighbor will be aged out.";
                            }

                            leaf hold-time {
                                type uint32;
                                units "seconds";
                                description
                                    "This value indicates the value of the hold time present in the
                                     Hello message.";
                            }

                            leaf join-attribute-support {
                                type boolean;
                                description
                                    "This value indicates whether the Hello Message received from
                                     the neighbor contained the Join Attribute field.";
                            }

                            list secondary-neighbor {
                                key "secondary-neighbor-address";
                                description "Each entry represents the secondary addresses advertised by PIM neighbor.";

                                leaf secondary-neighbor-address {
                                    type types-sros:ipv4-address;
                                    description
                                        "This value indicates the IPv4 address of the secondary PIM
                                         neighbor.";
                                }

                            } // list secondary-neighbor

                        } // list neighbor

                        list sg {
                            key "group-address source-address";
                            description "List of (*,G) and (S,G) entries for which this particular interface has state.";

                            leaf group-address {
                                type types-sros:ipv4-address;
                                description "The multicast group address of the entry.";
                            }

                            leaf source-address {
                                type types-sros:ipv4-address;
                                description "The source address of the multicast sender.";
                            }

                            leaf up-time {
                                type uint32;
                                units "seconds";
                                description "The time since this source group entry got created.";
                            }

                            leaf join-prune-state {
                                type types-pim:join-prune-state;
                                description
                                    "The Join Prune state for this entry on the interface.

                                     PIM Join or Prune messages are sent by the downstream routers
                                     towards the RPF' neighbor.";
                            }

                            leaf join-prune-timer {
                                type uint32;
                                units "seconds";
                                description
                                    "The time remaining before the router transitions the value of
                                     join-prune-state to 'no-info'.

                                     The timer is started or restarted when a valid Join message is
                                     received. If the value of this object is zero and
                                     join-prune-state is 'join' state, it means that the
                                     downstream router sent a holdtime of '0xffff'. In this case,
                                     join-prune-state will not transition until an appropriate
                                     cancelling of Join or Prune message is received.";
                            }

                            leaf prune-pending-timer {
                                type uint32;
                                units "seconds";
                                description
                                    "The time remaining before the router transitions the value of
                                     join-prune-state to 'no-info'.

                                     The timer is set when the PIM Prune message is received.";
                            }

                            leaf join-prune-rpt-state {
                                type types-pim:join-prune-state;
                                description
                                    "The Join Prune Rpt state for this entry on the interface.

                                     PIM Join or Prune messages are sent by the downstream routers towards the
                                     RPF' neighbor. (S,G,rpt) state is a result of receiving (S,G, rpt) JP message
                                     from the downstream router on the RP tree.";
                            }

                            leaf join-prune-rpt-timer {
                                type uint32;
                                units "seconds";
                                description
                                    "The time remaining before the router transitions the value of
                                     join-prune-rpt-state to 'no-info'.

                                     The timer is started or restarted when a valid Join message is
                                     received. If the value of this object is zero and
                                     join-prune-rpt-state is in 'join' state, it means that the
                                     downstream router sent a holdtime of '0xffff'. In this case,
                                     join-prune-rpt-state will not transition until an appropriate
                                     cancelling of Join or Prune message is received from the
                                     downstream router.";
                            }

                            leaf join-prune-rpt-pending-timer {
                                type uint32;
                                units "seconds";
                                description
                                    "The time remaining before the router transitions the value of
                                     join-prune-rpt-state to 'no-info'.

                                     The timer is set when the (S,G,rpt) PIM Prune message is received.";
                            }

                        } // list sg

                    } // container ipv4

                    container ipv6 {
                        description "PIM parameters for ipv6 on this service.";

                        leaf oper-state {
                            type types-sros:oper-state;
                            description
                                "The value of the this object indicates the operational
                                 state of PIM for this interface.";
                        }

                        leaf up-time {
                            type uint32;
                            units "seconds";
                            description "The time since this interface became operational.";
                        }

                        leaf group-count {
                            type uint32;
                            description
                                "The number of multicast groups which currently have this
                                 interface as an outgoing interface.";
                        }

                        leaf maximum-groups-until-now {
                            type uint32;
                            description "The highest value that 'group-count' had till now.";
                        }

                        leaf pseudo-wire-forwarder {
                            type boolean;
                            description
                                "Whether this interface is the forwarding interface
                                 of a pair of redundant pseudo-wire ports.";
                        }

                        container statistics {
                            description "The PIM statistics for Ipv6.";

                            leaf rx-packets {
                                type yang:counter32;
                                description "The number of multicast data packets received on this interface.";
                            }

                            leaf rx-hellos {
                                type yang:counter32;
                                description "The number of PIM hello messages received on this interface.";
                            }

                            leaf rx-join-prunes {
                                type yang:counter32;
                                description
                                    "The number of PIM
                                     Join Prune messages received on this interface.";
                            }

                            leaf tx-packets {
                                type yang:counter32;
                                description "The number of multicast data packets transmitted on this interface.";
                            }

                            leaf tx-join-prunes {
                                type yang:counter32;
                                description
                                    "The number of PIM
                                     Join Prune messages transmitted on this interface.";
                            }

                            leaf rx-hellos-dropped {
                                type yang:counter32;
                                description
                                    "The number of PIM Hello messages which were received on this interface but were
                                     dropped.";
                            }

                            leaf rx-neighbor-unknown {
                                type yang:counter32;
                                description
                                    "The number of PIM messages (other than Hello messages) which were received on this
                                     interface and were rejected because the adjacency with the neighbor
                                     router was not already established.";
                            }

                            leaf rx-bad-checksum-discard {
                                type yang:counter32;
                                description
                                    "The number of PIM messages received on this interface which were discarded because
                                     of bad checksum.";
                            }

                            leaf rx-bad-version-discard {
                                type yang:counter32;
                                description "The number of PIM messages with bad versions received on this interface.";
                            }

                            leaf rx-bad-encodings {
                                type yang:counter32;
                                description "The number of PIM messages with bad encodings received on this interface.";
                            }

                            leaf join-policy-drops {
                                type yang:counter32;
                                description
                                    "The number of times the join policy match resulted in dropping PIM Join-Prune
                                     Message or one of the source group contained in the message.";
                            }

                            leaf rx-join-prune-errors {
                                type yang:counter32;
                                description
                                    "The number of errors while processing Join-Prune messages received on this
                                     interface.";
                            }

                        } // container statistics

                        list neighbor {
                            key "neighbor-address";
                            description "List of the router's PIM neighbors.";

                            leaf neighbor-address {
                                type types-sros:ipv6-address;
                                description "This value indicates the IPv6 address of the PIM neighbor.";
                            }

                            leaf dr-priority {
                                type uint32;
                                description
                                    "This value indicates neighbor's DR priority which is received
                                     in the hello message. If the Hello Message did not contain
                                     the DR priority field, the value of priority will be '1'.";
                            }

                            leaf dr-priority-present {
                                type boolean;
                                description
                                    "This value of indicates whether the DR priority field was present
                                     in the Hello message received from the PIM neighbor.";
                            }

                            leaf tracking-support {
                                type boolean;
                                description
                                    "This value indicates whether the T bit in the LAN Prune Delay
                                     option was present in the Hello message. This indicates the
                                     neighbor's capability to disable Join message suppression.";
                            }

                            leaf lan-delay {
                                type uint32;
                                units "milliseconds";
                                description
                                    "This value indicates the value of lan delay field present in
                                     the Hello message received from the neighbor. ";
                            }

                            leaf lan-delay-present {
                                type boolean;
                                description
                                    "This value indicates whether the Hello message received from
                                     the neighbor contained the Lan Delay field.";
                            }

                            leaf generated-id {
                                type uint32;
                                description
                                    "This value indicates a randomly generated 32-bit value that is
                                     regenerated each time PIM forwarding is started or restarted on
                                     the interface, including when the router itself restarts.";
                            }

                            leaf override-interval {
                                type uint32;
                                units "milliseconds";
                                description
                                    "This value indicates the value of the override interval present
                                     in the Hello message.";
                            }

                            leaf up-time {
                                type uint32;
                                units "seconds";
                                description
                                    "This value indicates the time since this PIM neighbor (last)
                                     became a neighbor of the local router.";
                            }

                            leaf expiry-time {
                                type uint32;
                                units "seconds";
                                description
                                    "This value indicates the minimum time remaining before this
                                     PIM neighbor will be aged out.";
                            }

                            leaf hold-time {
                                type uint32;
                                units "seconds";
                                description
                                    "This value indicates the value of the hold time present in the
                                     Hello message.";
                            }

                            leaf join-attribute-support {
                                type boolean;
                                description
                                    "This value indicates whether the Hello Message received from
                                     the neighbor contained the Join Attribute field.";
                            }

                            list secondary-neighbor {
                                key "secondary-neighbor-address";
                                description "Each entry represents the secondary addresses advertised by PIM neighbor.";

                                leaf secondary-neighbor-address {
                                    type types-sros:ipv6-address;
                                    description
                                        "This value indicates the IPv6 address of the secondary PIM
                                         neighbor.";
                                }

                            } // list secondary-neighbor

                        } // list neighbor

                        list sg {
                            key "group-address source-address";
                            description "List of (*,G) and (S,G) entries for which this particular interface has state.";

                            leaf group-address {
                                type types-sros:ipv6-address;
                                description "The multicast group address of the entry.";
                            }

                            leaf source-address {
                                type types-sros:ipv6-address;
                                description "The source address of the multicast sender.";
                            }

                            leaf up-time {
                                type uint32;
                                units "seconds";
                                description "The time since this source group entry got created.";
                            }

                            leaf join-prune-state {
                                type types-pim:join-prune-state;
                                description
                                    "The Join Prune state for this entry on the interface.

                                     PIM Join or Prune messages are sent by the downstream routers
                                     towards the RPF' neighbor.";
                            }

                            leaf join-prune-timer {
                                type uint32;
                                units "seconds";
                                description
                                    "The time remaining before the router transitions the value of
                                     join-prune-state to 'no-info'.

                                     The timer is started or restarted when a valid Join message is
                                     received. If the value of this object is zero and
                                     join-prune-state is 'join' state, it means that the
                                     downstream router sent a holdtime of '0xffff'. In this case,
                                     join-prune-state will not transition until an appropriate
                                     cancelling of Join or Prune message is received.";
                            }

                            leaf prune-pending-timer {
                                type uint32;
                                units "seconds";
                                description
                                    "The time remaining before the router transitions the value of
                                     join-prune-state to 'no-info'.

                                     The timer is set when the PIM Prune message is received.";
                            }

                            leaf join-prune-rpt-state {
                                type types-pim:join-prune-state;
                                description
                                    "The Join Prune Rpt state for this entry on the interface.

                                     PIM Join or Prune messages are sent by the downstream routers towards the
                                     RPF' neighbor. (S,G,rpt) state is a result of receiving (S,G, rpt) JP message
                                     from the downstream router on the RP tree.";
                            }

                            leaf join-prune-rpt-timer {
                                type uint32;
                                units "seconds";
                                description
                                    "The time remaining before the router transitions the value of
                                     join-prune-rpt-state to 'no-info'.

                                     The timer is started or restarted when a valid Join message is
                                     received. If the value of this object is zero and
                                     join-prune-rpt-state is in 'join' state, it means that the
                                     downstream router sent a holdtime of '0xffff'. In this case,
                                     join-prune-rpt-state will not transition until an appropriate
                                     cancelling of Join or Prune message is received from the
                                     downstream router.";
                            }

                            leaf join-prune-rpt-pending-timer {
                                type uint32;
                                units "seconds";
                                description
                                    "The time remaining before the router transitions the value of
                                     join-prune-rpt-state to 'no-info'.

                                     The timer is set when the (S,G,rpt) PIM Prune message is received.";
                            }

                        } // list sg

                    } // container ipv6

                } // container pim-snooping

                container eth-cfm {
                    description "Enter the eth-cfm context";

                    list mep {
                        key "md-admin-name ma-admin-name mep-id";
                        description "Enter the mep list instance";

                        leaf md-admin-name {
                            type leafref {
                                path "../../../../../../eth-cfm/domain/md-admin-name";
                            }
                            description "Admin-assigned maintenance domain index value";
                        }

                        leaf ma-admin-name {
                            type leafref {
                                path "../../../../../../eth-cfm/domain[md-admin-name=current()/../md-admin-name]/association/ma-admin-name";
                            }
                            description "Admin-assigned maintenance association index value";
                        }

                        leaf mep-id {
                            type types-eth-cfm:mep-id-type;
                            description "MEP identifier";
                        }

                    } // list mep

                } // container eth-cfm

            } // list mesh-sdp

            list bgp-mh-site {
                key "site-name";
                description "Enter the bgp-mh-site list instance";

                leaf site-name {
                    type types-sros:named-item;
                    description "Name for the specific site";
                }

                leaf oper-state {
                    type enumeration {
                        enum "up"                           { value 1; }
                        enum "down"                         { value 2; }
                        enum "out-of-resource"              { value 3; }
                    }
                    description "Operational status of the site";
                }

                leaf active-timer-remain {
                    type uint32;
                    units "seconds";
                    description "Remaining time in the active-timer";
                }

                leaf boot-timer-remain {
                    type uint32;
                    units "seconds";
                    description "Remaining time in the boot-timer";
                }

                leaf min-down-timer-remain {
                    type uint32;
                    units "seconds";
                    description "Remaining time in the down-timer";
                }

                container designated-forwarder {
                    description "Designated forwarder";

                    leaf state {
                        type boolean;
                        description "State of designated forwarder";
                    }

                    leaf up-time {
                        type uint32;
                        units "seconds";
                        description "Uptime of the designated forwarder";
                    }

                    leaf change-count {
                        type uint32;
                        description "Number of times designated forwarder has changed";
                    }

                } // container designated-forwarder

            } // list bgp-mh-site

            list sap {
                key "sap-id";
                description "Enter the sap list instance";

                leaf sap-id {
                    type types-sros:sap;
                    description "SAP identifier";
                }

                leaf oper-state {
                    type enumeration {
                        enum "up"                           { value 1; }
                        enum "down"                         { value 2; }
                    }
                    description "Operating state of this SAP";
                }

                leaf oper-flags {
                    type types-services:l2-sap-oper-flags;
                    description "Conditions that affect the operating status of this SAP.";
                }

                leaf mirror-state {
                    type enumeration {
                        enum "ingress"                      { value 1; }
                        enum "egress"                       { value 2; }
                        enum "ingress-and-egress"           { value 3; }
                        enum "disabled"                     { value 4; }
                    }
                    description "Indicates whether traffic mirroring has been enabled on this SAP";
                }

                leaf template-used {
                    type types-sros:named-item-or-empty;
                    description "Name of the sap-template used to create this sap.";
                }

                leaf bpdu-translated-frames-encap {
                    type enumeration {
                        enum "undefined"                    { value 1; }
                        enum "disabled"                     { value 2; }
                        enum "pvst"                         { value 3; }
                        enum "stp"                          { value 4; }
                        enum "pvst-rw"                      { value 5; }
                    }
                    description
                        "Operational bpdu encapsulation used for BPDU
                         translated frames.";
                }

                leaf oper-dist-cpu-prot-policy {
                    type types-sros:named-item-or-empty;
                    description "Operational Distributed CPU Protection Policy.";
                }

                container statistics {
                    description "Statistics information";

                    container authentication {
                        description "Authentication statistics information";

                        leaf discarded-packets {
                            type yang:counter32;
                            description
                                "The number of DHCP packets discarded
                                 as result of authentication.";
                        }

                        leaf success-packets {
                            type yang:counter32;
                            description "The number of DHCP packets successfully authenticated.";
                        }

                    } // container authentication

                } // container statistics

                container ingress {
                    description "Enter the ingress context";

                    container qos {
                        description "Enter the qos context";

                        container sap-ingress {
                            description "Enter the sap-ingress context";

                            container forwarding-engine {
                                description "Forwarding engine information";

                                container statistics {
                                    description "Statistics information";

                                    leaf dropped-packets {
                                        type yang:counter64;
                                        description "Policy identifier";
                                    }

                                    leaf dropped-octets {
                                        type yang:counter64;
                                        description
                                            "The number of octets dropped by the
                                             ingress packet processor due to: SAP state,
                                             ingress MAC, IP or IPv6 filter, same segment
                                             discard, bad checksum, etc.";
                                    }

                                    leaf received-valid-packets {
                                        type yang:counter64;
                                        description
                                            "The value of received-valid indicates
                                             number of received valid packets, as determined by the SAP
                                             ingress QoS policy, offered by the packet processor to the traffic manager.";
                                    }

                                    leaf received-valid-octets {
                                        type yang:counter64;
                                        description
                                            "The value of received-valid indicates
                                             number of received valid octets, as determined by the SAP
                                             ingress QoS policy, offered by the packet processor to the traffic manager.";
                                    }

                                    leaf high-priority-offered-packets {
                                        type yang:counter64;
                                        description
                                            "The number of high priority packets,
                                             as determined by the SAP ingress QoS
                                             policy, offered by the packet processor to the
                                             traffic manager.";
                                    }

                                    leaf high-priority-offered-octets {
                                        type yang:counter64;
                                        description
                                            "The number of high priority octets,
                                             as determined by the SAP ingress QoS
                                             policy, offered by the packet processor to the
                                             traffic manager.";
                                    }

                                    leaf low-priority-offered-packets {
                                        type yang:counter64;
                                        description
                                            "The number of low priority packets,
                                             as determined by the SAP ingress QoS
                                             policy, offered by the packet processor to the
                                             traffic manager.";
                                    }

                                    leaf low-priority-offered-octets {
                                        type yang:counter64;
                                        description
                                            "The number of low priority octets,
                                             as determined by the SAP ingress QoS
                                             policy, offered by the packet processor to the
                                             traffic manager.";
                                    }

                                    leaf uncolor-offered-packets {
                                        type yang:counter64;
                                        description
                                            "The number of uncolored packets,
                                             as determined by the SAP ingress QoS
                                             policy, offered by the packet processor to the
                                             traffic manager.";
                                    }

                                    leaf uncolor-offered-octets {
                                        type yang:counter64;
                                        description
                                            "The number of uncolored octets,
                                             as determined by the SAP ingress QoS
                                             policy, offered by the packet processor to the
                                             traffic manager.";
                                    }

                                    leaf managed-offered-packets {
                                        type yang:counter64;
                                        description
                                            "The value of managed-offered indicates
                                             number of managed multicast packets, as determined by the SAP
                                             ingress QoS policy, offered by the packet processor to the traffic manager.";
                                    }

                                    leaf managed-offered-octets {
                                        type yang:counter64;
                                        description
                                            "The value of managed-offered indicates
                                             number of managed multicast octets, as determined by the SAP
                                             ingress QoS policy, offered by the packet processor to the traffic manager.";
                                    }

                                    leaf aggregate-offered-packets {
                                        type yang:counter64;
                                        description
                                            "The value of aggregate-offered indicates aggregate
                                             number of hi, lo priority and uncolour packets,
                                             as determined by the SAP ingress QoS policy,
                                             offered by the packet processor to the traffic manager.";
                                    }

                                    leaf aggregate-offered-octets {
                                        type yang:counter64;
                                        description
                                            "The value of managed-offered indicates aggregate
                                             number of hi, lo priority and uncolour octets,
                                             as determined by the SAP ingress QoS policy,
                                             offered by the packet processor to the traffic manager.";
                                    }

                                    leaf last-cleared-time {
                                        type yang:date-and-time;
                                        description "Time when the counters in this table were last cleared.";
                                    }

                                } // container statistics

                            } // container forwarding-engine

                            container traffic-manager {
                                description "Traffic manager information";

                                container statistics {
                                    description "Statistics information";

                                    leaf cpm-packets {
                                        type yang:counter64;
                                        description
                                            "The value of cpm-packets indicates
                                             ingress traffic in terms of packets destined to CPM
                                             associated with this SAP.";
                                    }

                                    leaf cpm-octets {
                                        type yang:counter64;
                                        description
                                            "The value of cpm indicates
                                             ingress traffic in terms of bytes destined to CPM
                                             associated with this SAP.";
                                    }

                                    leaf high-priority-dropped-packets {
                                        type yang:counter64;
                                        description
                                            "The number of high priority packets,
                                             as determined by the SAP ingress QoS
                                             policy, dropped by the traffic manager due to:
                                             MBS exceeded, buffer pool limit
                                             exceeded, etc.";
                                    }

                                    leaf high-priority-dropped-octets {
                                        type yang:counter64;
                                        description
                                            "The number of high priority octets,
                                             as determined by the SAP ingress QoS
                                             policy, dropped by the traffic manager due to:
                                             MBS exceeded, buffer pool limit
                                             exceeded, etc.";
                                    }

                                    leaf low-priority-dropped-packets {
                                        type yang:counter64;
                                        description
                                            "The number of low priority packets,
                                             as determined by the SAP ingress QoS
                                             policy, dropped by the traffic manager due to:
                                             MBS exceeded, buffer pool limit
                                             exceeded, etc.";
                                    }

                                    leaf low-priority-dropped-octets {
                                        type yang:counter64;
                                        description
                                            "The number of low priority octets,
                                             as determined by the SAP ingress QoS
                                             policy, dropped by the traffic manager due to:
                                             MBS exceeded, buffer pool limit
                                             exceeded, etc.";
                                    }

                                    leaf in-profile-forwarded-packets {
                                        type yang:counter64;
                                        description
                                            "The number of in-profile packets
                                             (rate below CIR) forwarded by the
                                             ingress traffic manager.";
                                    }

                                    leaf in-profile-forwarded-octets {
                                        type yang:counter64;
                                        description
                                            "The number of in-profile octets
                                             (rate below CIR) forwarded by the
                                             ingress traffic manager.";
                                    }

                                    leaf out-profile-forwarded-packets {
                                        type yang:counter64;
                                        description
                                            "The number of out-of-profile packets
                                             (rate above CIR) forwarded by the
                                             ingress traffic manager.";
                                    }

                                    leaf out-profile-forwarded-octets {
                                        type yang:counter64;
                                        description
                                            "The number of out-of-profile octets
                                             (rate above CIR) forwarded by the
                                             ingress traffic manager.";
                                    }

                                    leaf aggregate-forwarded-packets {
                                        type yang:counter64;
                                        description
                                            "The aggregate number of in and out-of profile
                                              packets forwarded by the ingress traffic manager.";
                                    }

                                    leaf aggregate-forwarded-octets {
                                        type yang:counter64;
                                        description
                                            "The aggregate number of in and out-of-profile
                                             octets forwarded by the ingress traffic manager.";
                                    }

                                    leaf aggregate-dropped-packets {
                                        type yang:counter64;
                                        description
                                            "The aggregate number of in and out-of profile
                                             packets, dropped by the traffic manager due to:
                                             MBS exceeded, buffer pool limit
                                             exceeded, etc.";
                                    }

                                    leaf aggregate-dropped-octets {
                                        type yang:counter64;
                                        description
                                            "The aggregate number of in and out-of profile
                                             octets, dropped by the traffic manager due to:
                                             MBS exceeded, buffer pool limit
                                             exceeded, etc.";
                                    }

                                    leaf last-cleared-time {
                                        type yang:date-and-time;
                                        description "Time when the counters in this table were last cleared.";
                                    }

                                } // container statistics

                            } // container traffic-manager

                            list queue {
                                key "queue-id";
                                description "SAP Ingress Queue statistics.";

                                leaf queue-id {
                                    type types-qos:ingress-queue-id;
                                    description "The unique identifier for the queue.";
                                }

                                container statistics {
                                    description "SAP Ingress Queue statistics.";

                                    choice stat-mode {
                                        case unicast-priority {

                                            container unicast-priority {

                                                leaf high-priority-offered-packets {
                                                    type yang:counter64;
                                                    description "The number of high-priority packets offered by packet processor to traffic manager.";
                                                }

                                                leaf high-priority-offered-octets {
                                                    type yang:counter64;
                                                    description "The number of high-priority octets offered by packet processor to traffic manager.";
                                                }

                                                leaf low-priority-offered-packets {
                                                    type yang:counter64;
                                                    description "The number of low-priority packets offered by packet processor to traffic manager.";
                                                }

                                                leaf low-priority-offered-octets {
                                                    type yang:counter64;
                                                    description "The number of low-priority octets offered by packet processor to traffic manager.";
                                                }

                                                leaf high-priority-dropped-packets {
                                                    type yang:counter64;
                                                    description "The number of high-priority packets dropped by packet processor to traffic manager.";
                                                }

                                                leaf high-priority-dropped-octets {
                                                    type yang:counter64;
                                                    description "The number of high-priority octets dropped by packet processor to traffic manager.";
                                                }

                                                leaf low-priority-dropped-packets {
                                                    type yang:counter64;
                                                    description "The number of low-priority packets dropped by packet processor to traffic manager.";
                                                }

                                                leaf low-priority-dropped-octets {
                                                    type yang:counter64;
                                                    description "The number of low-priority octets dropped by packet processor to traffic manager.";
                                                }

                                                leaf in-profile-forwarded-packets {
                                                    type yang:counter64;
                                                    description "The number of in-profile packets (rate below CIR) forwarded.";
                                                }

                                                leaf in-profile-forwarded-octets {
                                                    type yang:counter64;
                                                    description "The number of in-profile octets (rate below CIR) forwarded.";
                                                }

                                                leaf out-profile-forwarded-packets {
                                                    type yang:counter64;
                                                    description "The number of out-of-profile packets (rate below CIR) forwarded.";
                                                }

                                                leaf out-profile-forwarded-octets {
                                                    type yang:counter64;
                                                    description "The number of out-of-profile octets (rate below CIR) forwarded.";
                                                }

                                            } // container unicast-priority

                                        }
                                        case unicast-profile {

                                            container unicast-profile {

                                                leaf color-in-offered-packets {
                                                    type yang:counter64;
                                                    description "The number of color-in packets offered to traffic manager.";
                                                }

                                                leaf color-in-offered-octets {
                                                    type yang:counter64;
                                                    description "The number of color-in octets offered to traffic manager.";
                                                }

                                                leaf color-out-offered-packets {
                                                    type yang:counter64;
                                                    description "The number of color-out packets offered to traffic manager.";
                                                }

                                                leaf color-out-offered-octets {
                                                    type yang:counter64;
                                                    description "The number of color-out octets offered to traffic manager.";
                                                }

                                                leaf uncolor-offered-packets {
                                                    type yang:counter64;
                                                    description "The number of uncolor packets offered to traffic manager.";
                                                }

                                                leaf uncolor-offered-octets {
                                                    type yang:counter64;
                                                    description "The number of uncolor octets offered to traffic manager.";
                                                }

                                                leaf color-out-dropped-packets {
                                                    type yang:counter64;
                                                    description "The number of color-out packets dropped.";
                                                }

                                                leaf color-out-dropped-octets {
                                                    type yang:counter64;
                                                    description "The number of color-out octets dropped.";
                                                }

                                                leaf color-in-uncolor-dropped-packets {
                                                    type yang:counter64;
                                                    description "The number of color-in/uncolor packets dropped.";
                                                }

                                                leaf color-in-uncolor-dropped-octets {
                                                    type yang:counter64;
                                                    description "The number of color-in/uncolor octets dropped.";
                                                }

                                                leaf in-profile-forwarded-packets {
                                                    type yang:counter64;
                                                    description "The number of in-profile packets (rate below CIR) forwarded.";
                                                }

                                                leaf in-profile-forwarded-octets {
                                                    type yang:counter64;
                                                    description "The number of in-profile octets (rate below CIR) forwarded.";
                                                }

                                                leaf out-profile-forwarded-packets {
                                                    type yang:counter64;
                                                    description "The number of out-of-profile packets (rate below CIR) forwarded.";
                                                }

                                                leaf out-profile-forwarded-octets {
                                                    type yang:counter64;
                                                    description "The number of out-of-profile octets (rate below CIR) forwarded.";
                                                }

                                            } // container unicast-profile

                                        }
                                        case multipoint-priority {

                                            container multipoint-priority {

                                                leaf high-priority-offered-packets {
                                                    type yang:counter64;
                                                    description "The number of high-priority packets offered by packet processor to traffic manager.";
                                                }

                                                leaf high-priority-offered-octets {
                                                    type yang:counter64;
                                                    description "The number of high-priority octets offered by packet processor to traffic manager.";
                                                }

                                                leaf low-priority-offered-packets {
                                                    type yang:counter64;
                                                    description "The number of low-priority packets offered by packet processor to traffic manager.";
                                                }

                                                leaf low-priority-offered-octets {
                                                    type yang:counter64;
                                                    description "The number of low-priority octets offered by packet processor to traffic manager.";
                                                }

                                                leaf managed-offered-packets {
                                                    type yang:counter64;
                                                    description "The number of managed packets offered by packet processor to traffic manager.";
                                                }

                                                leaf managed-offered-octets {
                                                    type yang:counter64;
                                                    description "The number of managed octets offered by packet processor to traffic manager.";
                                                }

                                                leaf high-priority-dropped-packets {
                                                    type yang:counter64;
                                                    description "The number of high-priority packets dropped by packet processor to traffic manager.";
                                                }

                                                leaf high-priority-dropped-octets {
                                                    type yang:counter64;
                                                    description "The number of high-priority octets dropped by packet processor to traffic manager.";
                                                }

                                                leaf low-priority-dropped-packets {
                                                    type yang:counter64;
                                                    description "The number of low-priority packets dropped by packet processor to traffic manager.";
                                                }

                                                leaf low-priority-dropped-octets {
                                                    type yang:counter64;
                                                    description "The number of low-priority octets dropped by packet processor to traffic manager.";
                                                }

                                                leaf in-profile-forwarded-packets {
                                                    type yang:counter64;
                                                    description "The number of in-profile packets (rate below CIR) forwarded.";
                                                }

                                                leaf in-profile-forwarded-octets {
                                                    type yang:counter64;
                                                    description "The number of in-profile octets (rate below CIR) forwarded.";
                                                }

                                                leaf out-profile-forwarded-packets {
                                                    type yang:counter64;
                                                    description "The number of out-of-profile packets (rate below CIR) forwarded.";
                                                }

                                                leaf out-profile-forwarded-octets {
                                                    type yang:counter64;
                                                    description "The number of out-of-profile octets (rate below CIR) forwarded.";
                                                }

                                            } // container multipoint-priority

                                        }
                                        case multipoint-profile {

                                            container multipoint-profile {

                                                leaf color-in-offered-packets {
                                                    type yang:counter64;
                                                    description "The number of color-in packets offered to traffic manager.";
                                                }

                                                leaf color-in-offered-octets {
                                                    type yang:counter64;
                                                    description "The number of color-in octets offered to traffic manager.";
                                                }

                                                leaf color-out-offered-packets {
                                                    type yang:counter64;
                                                    description "The number of color-out packets offered to traffic manager.";
                                                }

                                                leaf color-out-offered-octets {
                                                    type yang:counter64;
                                                    description "The number of color-out octets offered to traffic manager.";
                                                }

                                                leaf uncolor-offered-packets {
                                                    type yang:counter64;
                                                    description "The number of uncolor packets offered to traffic manager.";
                                                }

                                                leaf uncolor-offered-octets {
                                                    type yang:counter64;
                                                    description "The number of uncolor octets offered to traffic manager.";
                                                }

                                                leaf managed-offered-packets {
                                                    type yang:counter64;
                                                    description "The number of managed packets offered by packet processor to traffic manager.";
                                                }

                                                leaf managed-offered-octets {
                                                    type yang:counter64;
                                                    description "The number of managed octets offered by packet processor to traffic manager.";
                                                }

                                                leaf color-out-dropped-packets {
                                                    type yang:counter64;
                                                    description "The number of color-out packets dropped.";
                                                }

                                                leaf color-out-dropped-octets {
                                                    type yang:counter64;
                                                    description "The number of color-out octets dropped.";
                                                }

                                                leaf color-in-uncolor-dropped-packets {
                                                    type yang:counter64;
                                                    description "The number of color-in/uncolor packets dropped.";
                                                }

                                                leaf color-in-uncolor-dropped-octets {
                                                    type yang:counter64;
                                                    description "The number of color-in/uncolor octets dropped.";
                                                }

                                                leaf in-profile-forwarded-packets {
                                                    type yang:counter64;
                                                    description "The number of in-profile packets (rate below CIR) forwarded.";
                                                }

                                                leaf in-profile-forwarded-octets {
                                                    type yang:counter64;
                                                    description "The number of in-profile octets (rate below CIR) forwarded.";
                                                }

                                                leaf out-profile-forwarded-packets {
                                                    type yang:counter64;
                                                    description "The number of out-of-profile packets (rate below CIR) forwarded.";
                                                }

                                                leaf out-profile-forwarded-octets {
                                                    type yang:counter64;
                                                    description "The number of out-of-profile octets (rate below CIR) forwarded.";
                                                }

                                            } // container multipoint-profile

                                        }
                                        case v4-v6 {

                                            container v4-v6 {

                                                leaf ipv4-offered-packets {
                                                    type yang:counter64;
                                                    description "The number of ipv4 packets offered by packet processor to traffic manager.";
                                                }

                                                leaf ipv4-offered-octets {
                                                    type yang:counter64;
                                                    description "The number of ipv4 octets offered by packet processor to traffic manager.";
                                                }

                                                leaf ipv6-offered-packets {
                                                    type yang:counter64;
                                                    description "The number of ipv6 packets offered by packet processor to traffic manager.";
                                                }

                                                leaf ipv6-offered-octets {
                                                    type yang:counter64;
                                                    description "The number of ipv6 octets offered by packet processor to traffic manager.";
                                                }

                                                leaf ipv4-dropped-packets {
                                                    type yang:counter64;
                                                    description "The number of ipv4 packets dropped by packet processor to traffic manager.";
                                                }

                                                leaf ipv4-dropped-octets {
                                                    type yang:counter64;
                                                    description "The number of ipv4 octets dropped by packet processor to traffic manager.";
                                                }

                                                leaf ipv6-dropped-packets {
                                                    type yang:counter64;
                                                    description "The number of ipv6 packets dropped by packet processor to traffic manager.";
                                                }

                                                leaf ipv6-dropped-octets {
                                                    type yang:counter64;
                                                    description "The number of ipv6 octets dropped by packet processor to traffic manager.";
                                                }

                                                leaf ipv4-forwarded-packets {
                                                    type yang:counter64;
                                                    description "The number of ipv4 packets forwarded.";
                                                }

                                                leaf ipv4-forwarded-octets {
                                                    type yang:counter64;
                                                    description "The number of ipv4 octets forwarded.";
                                                }

                                                leaf ipv6-forwarded-packets {
                                                    type yang:counter64;
                                                    description "The number of ipv6 packets forwarded.";
                                                }

                                                leaf ipv6-forwarded-octets {
                                                    type yang:counter64;
                                                    description "The number of ipv6 octets forwarded.";
                                                }

                                            } // container v4-v6

                                        }
                                    }
                                } // container statistics

                            } // list queue

                            list policer {
                                key "policer-id";
                                description "SAP Ingress Policer statistics.";

                                leaf policer-id {
                                    type types-qos:ingress-policer-id;
                                    description "The unique identifier for the policer.";
                                }

                                container statistics {
                                    description "SAP Ingress Policer statistics.";

                                    choice stat-mode {
                                        case minimal {

                                            container minimal {

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf all-dropped-packets {
                                                    type yang:counter64;
                                                    description "The number of all the priority packets dropped by the packet processor to traffic manager";
                                                }

                                                leaf all-dropped-octets {
                                                    type yang:counter64;
                                                    description "The number of all the priority octets dropped by the packet processor to traffic manager";
                                                }

                                                leaf all-forwarded-packets {
                                                    type yang:counter64;
                                                    description "The number of all the priority packets forwarded by the packet processor to traffic manager";
                                                }

                                                leaf all-forwarded-octets {
                                                    type yang:counter64;
                                                    description "The number of all the priority octets forwarded by the packet processor to traffic manager";
                                                }

                                            } // container minimal

                                        }
                                        case offered-profile-no-cir {

                                            container offered-profile-no-cir {

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-no-cir

                                        }
                                        case offered-priority-no-cir {

                                            container offered-priority-no-cir {

                                                leaf high-priority-offered-packets {
                                                    type yang:counter64;
                                                    description "The number of high-priority packets offered by the packet processor to traffic manager";
                                                }

                                                leaf high-priority-offered-octets {
                                                    type yang:counter64;
                                                    description "The number of high-priority octets offered by the packet processor to traffic manager";
                                                }

                                                leaf low-priority-offered-packets {
                                                    type yang:counter64;
                                                    description "The number of low-priority packets offered by the packet processor to traffic manager";
                                                }

                                                leaf low-priority-offered-octets {
                                                    type yang:counter64;
                                                    description "The number of low-priority octets offered by the packet processor to traffic manager";
                                                }

                                                leaf high-priority-dropped-packets {
                                                    type yang:counter64;
                                                    description "The number of high-priority packets dropped by the packet processor to traffic manager";
                                                }

                                                leaf high-priority-dropped-octets {
                                                    type yang:counter64;
                                                    description "The number of high-priority octets dropped by the packet processor to traffic manager";
                                                }

                                                leaf low-priority-dropped-packets {
                                                    type yang:counter64;
                                                    description "The number of low-priority packets dropped by the packet processor to traffic manager";
                                                }

                                                leaf low-priority-dropped-octets {
                                                    type yang:counter64;
                                                    description "The number of low-priority octets dropped by the packet processor to traffic manager";
                                                }

                                                leaf high-priority-forwarded-packets {
                                                    type yang:counter64;
                                                    description "The number of high-priority packets forwarded by the packet processor to traffic manager";
                                                }

                                                leaf high-priority-forwarded-octets {
                                                    type yang:counter64;
                                                    description "The number of high-priority octets forwarded by the packet processor to traffic manager";
                                                }

                                                leaf low-priority-forwarded-packets {
                                                    type yang:counter64;
                                                    description "The number of low-priority packets forwarded by the packet processor to traffic manager";
                                                }

                                                leaf low-priority-forwarded-octets {
                                                    type yang:counter64;
                                                    description "The number of low-priority octets forwarded by the packet processor to traffic manager";
                                                }

                                            } // container offered-priority-no-cir

                                        }
                                        case offered-profile-cir {

                                            container offered-profile-cir {

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf uncolor-offered-packets {
                                                    type yang:counter64;
                                                    description "The number of uncolor packets offered by the packet processor to traffic manager";
                                                }

                                                leaf uncolor-offered-octets {
                                                    type yang:counter64;
                                                    description "The number of uncolor octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-cir

                                        }
                                        case offered-priority-cir {

                                            container offered-priority-cir {

                                                leaf high-priority-offered-packets {
                                                    type yang:counter64;
                                                    description "The number of high-priority packets offered by the packet processor to traffic manager";
                                                }

                                                leaf high-priority-offered-octets {
                                                    type yang:counter64;
                                                    description "The number of high-priority octets offered by the packet processor to traffic manager";
                                                }

                                                leaf low-priority-offered-packets {
                                                    type yang:counter64;
                                                    description "The number of low-priority packets offered by the packet processor to traffic manager";
                                                }

                                                leaf low-priority-offered-octets {
                                                    type yang:counter64;
                                                    description "The number of low-priority octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-priority-cir

                                        }
                                        case offered-total-cir {

                                            container offered-total-cir {

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-total-cir

                                        }
                                        case offered-limited-profile-cir {

                                            container offered-limited-profile-cir {

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf uncolor-offered-packets {
                                                    type yang:counter64;
                                                    description "The number of uncolor packets offered by the packet processor to traffic manager";
                                                }

                                                leaf uncolor-offered-octets {
                                                    type yang:counter64;
                                                    description "The number of uncolor octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-limited-profile-cir

                                        }
                                        case offered-profile-capped-cir {

                                            container offered-profile-capped-cir {

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf uncolor-offered-packets {
                                                    type yang:counter64;
                                                    description "The number of uncolor packets offered by the packet processor to traffic manager";
                                                }

                                                leaf uncolor-offered-octets {
                                                    type yang:counter64;
                                                    description "The number of uncolor octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-capped-cir

                                        }
                                        case offered-limited-capped-cir {

                                            container offered-limited-capped-cir {

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                                leaf uncolor-offered-packets {
                                                    type yang:counter64;
                                                    description "The number of out-of-rofile packets offered by the packet processor to traffic manager";
                                                }

                                                leaf uncolor-offered-octets {
                                                    type yang:counter64;
                                                    description "The number of out-of-profile octets offered by the packet processor to traffic manager";
                                                }

                                            } // container offered-limited-capped-cir

                                        }
                                        case v4-v6 {

                                            container v4-v6 {

                                                leaf ipv4-offered-packets {
                                                    type yang:counter64;
                                                    description "The number of ipv4 packets offered by the packet processor to traffic manager";
                                                }

                                                leaf ipv4-offered-octets {
                                                    type yang:counter64;
                                                    description "The number of ipv4 octets offered by the packet processor to traffic manager";
                                                }

                                                leaf ipv6-offered-packets {
                                                    type yang:counter64;
                                                    description "The number of ipv6 packets offered by the packet processor to traffic manager";
                                                }

                                                leaf ipv6-offered-octets {
                                                    type yang:counter64;
                                                    description "The number of ipv6 octets offered by the packet processor to traffic manager";
                                                }

                                                leaf ipv4-dropped-packets {
                                                    type yang:counter64;
                                                    description "The number of ipv4 packets dropped by the packet processor to traffic manager";
                                                }

                                                leaf ipv4-dropped-octets {
                                                    type yang:counter64;
                                                    description "The number of ipv4 octets dropped by the packet processor to traffic manager";
                                                }

                                                leaf ipv6-dropped-packets {
                                                    type yang:counter64;
                                                    description "The number of ipv6 packets dropped by the packet processor to traffic manager";
                                                }

                                                leaf ipv6-dropped-octets {
                                                    type yang:counter64;
                                                    description "The number of ipv6 octets dropped by the packet processor to traffic manager";
                                                }

                                                leaf ipv4-forwarded-packets {
                                                    type yang:counter64;
                                                    description "The number of ipv4 packets forwarded by the packet processor to traffic manager";
                                                }

                                                leaf ipv4-forwarded-octets {
                                                    type yang:counter64;
                                                    description "The number of ipv4 octets forwarded by the packet processor to traffic manager";
                                                }

                                                leaf ipv6-forwarded-packets {
                                                    type yang:counter64;
                                                    description "The number of ipv6 packets forwarded by the packet processor to traffic manager";
                                                }

                                                leaf ipv6-forwarded-octets {
                                                    type yang:counter64;
                                                    description "The number of ipv6 octets forwarded by the packet processor to traffic manager";
                                                }

                                            } // container v4-v6

                                        }
                                    }
                                } // container statistics

                            } // list policer

                        } // container sap-ingress

                    } // container qos

                } // container ingress

                container egress {
                    description "Enter the egress context";

                    container qos {
                        description "Enter the qos context";

                        container sap-egress {
                            description "Enter the sap-egress context";

                            container traffic-manager {
                                description "Traffic manager information";

                                container statistics {
                                    description "Statistics information";

                                    leaf in-inplus-profile-dropped-packets {
                                        type yang:counter64;
                                        description "Policy identifier";
                                    }

                                    leaf in-inplus-profile-dropped-octets {
                                        type yang:counter64;
                                        description
                                            "The number of in-profile octets
                                             discarded by the egress traffic manager due
                                             to: MBS exceeded, buffer pool limit
                                             exceeded, etc.";
                                    }

                                    leaf out-exceed-profile-dropped-packets {
                                        type yang:counter64;
                                        description
                                            "The number of out-of-profile packets
                                             discarded by the egress traffic manager due
                                             to: MBS exceeded, buffer pool limit
                                             exceeded, etc.";
                                    }

                                    leaf out-exceed-profile-dropped-octets {
                                        type yang:counter64;
                                        description
                                            "The number of out-of-profile packets
                                             discarded by the egress traffic manager due
                                             to: MBS exceeded, buffer pool limit
                                             exceeded, etc.";
                                    }

                                    leaf in-inplus-profile-forwarded-packets {
                                        type yang:counter64;
                                        description
                                            "The number of in-profile packets
                                             (rate below CIR) forwarded by the
                                             egress traffic manager.";
                                    }

                                    leaf in-inplus-profile-forwarded-octets {
                                        type yang:counter64;
                                        description
                                            "The number of in-profile octets
                                             (rate below CIR) forwarded by the
                                             egress traffic manager.";
                                    }

                                    leaf out-exceed-profile-forwarded-packets {
                                        type yang:counter64;
                                        description
                                            "The number of out-of-profile packets
                                             (rate above CIR) forwarded by the
                                             egress traffic manager.";
                                    }

                                    leaf out-exceed-profile-forwarded-octets {
                                        type yang:counter64;
                                        description
                                            "The number of out-of-profile octets
                                             (rate above CIR) forwarded by the
                                             egress traffic manager.";
                                    }

                                    leaf aggregate-forwarded-packets {
                                        type yang:counter64;
                                        description
                                            "The aggregate number of in and out-of profile
                                             packets forwarded by the egress traffic manager.";
                                    }

                                    leaf aggregate-forwarded-octets {
                                        type yang:counter64;
                                        description
                                            "The aggregate number of in and out-of profile
                                             octets forwarded by the egress traffic manager.";
                                    }

                                    leaf aggregate-dropped-packets {
                                        type yang:counter64;
                                        description
                                            "The aggregate number of in and out-of profile
                                             packets discarded by the egress traffic manager due
                                             to: MBS exceeded, buffer pool limit
                                             exceeded, etc.";
                                    }

                                    leaf aggregate-dropped-octets {
                                        type yang:counter64;
                                        description
                                            "The aggregate number of in and out-of profile
                                             octets discarded by the egress traffic manager due
                                             to: MBS exceeded, buffer pool limit
                                             exceeded, etc.";
                                    }

                                    leaf last-cleared-time {
                                        type yang:date-and-time;
                                        description "Time when the counters in this table were last cleared.";
                                    }

                                } // container statistics

                            } // container traffic-manager

                            list queue {
                                key "queue-id";
                                description "SAP Egress Queue statistics.";

                                leaf queue-id {
                                    type types-qos:egress-queue-id;
                                    description "The unique identifier for the queue.";
                                }

                                container statistics {
                                    description "SAP Egress Queue statistics.";

                                    choice stat-mode {
                                        case profile {

                                            container profile {

                                                leaf in-inplus-profile-forwarded-packets {
                                                    type yang:counter64;
                                                    description
                                                        "The number of in-profile/in-plus-profile packets
                                                         (rate below CIR) forwarded.";
                                                }

                                                leaf in-inplus-profile-forwarded-octets {
                                                    type yang:counter64;
                                                    description
                                                        "The number of in-profile/in-plus-profile octets
                                                         (rate below CIR) forwarded.";
                                                }

                                                leaf out-exceed-profile-forwarded-packets {
                                                    type yang:counter64;
                                                    description
                                                        "The number of out-profile/exceed-profile packets
                                                         (rate above CIR) forwarded.";
                                                }

                                                leaf out-exceed-profile-forwarded-octets {
                                                    type yang:counter64;
                                                    description
                                                        "The number of out-profile/exceed-profile octets
                                                         (rate above CIR) forwarded.";
                                                }

                                                leaf in-inplus-profile-dropped-packets {
                                                    type yang:counter64;
                                                    description
                                                        "The number of in-profile/in-plus-profile packets
                                                         discarded.";
                                                }

                                                leaf in-inplus-profile-dropped-octets {
                                                    type yang:counter64;
                                                    description
                                                        "The number of in-profile/in-plus-profile octets
                                                         discarded.";
                                                }

                                                leaf out-exceed-profile-dropped-packets {
                                                    type yang:counter64;
                                                    description
                                                        "The number of out-profile/exceed-profile packets
                                                         discarded.";
                                                }

                                                leaf out-exceed-profile-dropped-octets {
                                                    type yang:counter64;
                                                    description
                                                        "The number of out-profile/exceed-profile octets
                                                         discarded.";
                                                }

                                            } // container profile

                                        }
                                        case v4-v6 {

                                            container v4-v6 {

                                                leaf ipv4-dropped-packets {
                                                    type yang:counter64;
                                                    description "The number of ipv4 packets discarded.";
                                                }

                                                leaf ipv4-dropped-octets {
                                                    type yang:counter64;
                                                    description "The number of ipv4 octets discarded.";
                                                }

                                                leaf ipv6-dropped-packets {
                                                    type yang:counter64;
                                                    description "The number of ipv6 packets discarded.";
                                                }

                                                leaf ipv6-dropped-octets {
                                                    type yang:counter64;
                                                    description "The number of ipv6 octets discarded.";
                                                }

                                                leaf ipv4-forwarded-packets {
                                                    type yang:counter64;
                                                    description "The number of ipv4 packets forwarded.";
                                                }

                                                leaf ipv4-forwarded-octets {
                                                    type yang:counter64;
                                                    description "The number of ipv4 octets forwarded.";
                                                }

                                                leaf ipv6-forwarded-packets {
                                                    type yang:counter64;
                                                    description "The number of ipv6 packets forwarded.";
                                                }

                                                leaf ipv6-forwarded-octets {
                                                    type yang:counter64;
                                                    description "The number of ipv6 octets forwarded.";
                                                }

                                            } // container v4-v6

                                        }
                                    }
                                } // container statistics

                            } // list queue

                            list policer {
                                key "policer-id";
                                description "SAP Egress Policer statistics.";

                                leaf policer-id {
                                    type types-qos:sap-egress-policer-id;
                                    description "The unique identifier for the policer.";
                                }

                                container statistics {
                                    description "SAP Egress Policer statistics.";

                                    choice stat-mode {
                                        case minimal {

                                            container minimal {

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf all-dropped-packets {
                                                    type yang:counter64;
                                                    description "The number of all the priority packets dropped by the packet processor to traffic manager";
                                                }

                                                leaf all-dropped-octets {
                                                    type yang:counter64;
                                                    description "The number of all the priority octets dropped by the packet processor to traffic manager";
                                                }

                                                leaf all-forwarded-packets {
                                                    type yang:counter64;
                                                    description "The number of all the priority packets forwarded by the packet processor to traffic manager";
                                                }

                                                leaf all-forwarded-octets {
                                                    type yang:counter64;
                                                    description "The number of all the priority octets forwarded by the packet processor to traffic manager";
                                                }

                                            } // container minimal

                                        }
                                        case offered-profile-no-cir {

                                            container offered-profile-no-cir {

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-no-cir

                                        }
                                        case offered-profile-cir {

                                            container offered-profile-cir {

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf uncolor-offered-packets {
                                                    type yang:counter64;
                                                    description "The number of uncolor packets offered by the packet processor to traffic manager";
                                                }

                                                leaf uncolor-offered-octets {
                                                    type yang:counter64;
                                                    description "The number of uncolor octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-cir

                                        }
                                        case offered-total-cir {

                                            container offered-total-cir {

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-total-cir

                                        }
                                        case offered-limited-capped-cir {

                                            container offered-limited-capped-cir {

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                                leaf out-profile-offered-packets {
                                                    type yang:counter64;
                                                    description "The number of out-of-rofile packets offered by the packet processor to traffic manager";
                                                }

                                                leaf out-profile-offered-octets {
                                                    type yang:counter64;
                                                    description "The number of out-of-profile octets offered by the packet processor to traffic manager";
                                                }

                                            } // container offered-limited-capped-cir

                                        }
                                        case offered-profile-capped-cir {

                                            container offered-profile-capped-cir {

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf uncolor-offered-packets {
                                                    type yang:counter64;
                                                    description "The number of uncolor packets offered by the packet processor to traffic manager";
                                                }

                                                leaf uncolor-offered-octets {
                                                    type yang:counter64;
                                                    description "The number of uncolor octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-capped-cir

                                        }
                                        case offered-total-cir-exceed {

                                            container offered-total-cir-exceed {

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf exceed-profile-dropped-packets {
                                                    type yang:counter64;
                                                    description "The number of exceed-profile packets dropped by the packet processor to traffic manager";
                                                }

                                                leaf exceed-profile-dropped-octets {
                                                    type yang:counter64;
                                                    description "The number of exceed-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                                leaf exceed-profile-forwarded-packets {
                                                    type yang:counter64;
                                                    description "The number of exceed-profile packets forwarded by the packet processor to traffic manager";
                                                }

                                                leaf exceed-profile-forwarded-octets {
                                                    type yang:counter64;
                                                    description "The number of exceed-profile octets forwarded by the packet processor to traffic manager";
                                                }

                                            } // container offered-total-cir-exceed

                                        }
                                        case offered-four-profile-no-cir {

                                            container offered-four-profile-no-cir {

                                                leaf inplus-profile-offered-packets {
                                                    type yang:counter64;
                                                    description "The number of inplus-profile packets offered by the packet processor to traffic manager";
                                                }

                                                leaf inplus-profile-offered-octets {
                                                    type yang:counter64;
                                                    description "The number of inplus-profile octets offered by the packet processor to traffic manager";
                                                }

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf exceed-profile-offered-packets {
                                                    type yang:counter64;
                                                    description "The number of exceed-profile packets offered by the packet processor to traffic manager";
                                                }

                                                leaf exceed-profile-offered-octets {
                                                    type yang:counter64;
                                                    description "The number of exceed-profile octets offered by the packet processor to traffic manager";
                                                }

                                                leaf inplus-profile-dropped-packets {
                                                    type yang:counter64;
                                                    description "The number of inplus-profile packets dropped by the packet processor to traffic manager";
                                                }

                                                leaf inplus-profile-dropped-octets {
                                                    type yang:counter64;
                                                    description "The number of inplus-profile octets dropped by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf exceed-profile-dropped-packets {
                                                    type yang:counter64;
                                                    description "The number of exceed-profile packets dropped by the packet processor to traffic manager";
                                                }

                                                leaf exceed-profile-dropped-octets {
                                                    type yang:counter64;
                                                    description "The number of exceed-profile octets dropped by the packet processor to traffic manager";
                                                }

                                                leaf inplus-profile-forwarded-packets {
                                                    type yang:counter64;
                                                    description "The number of inplus-profile packets forwarded by the packet processor to traffic manager";
                                                }

                                                leaf inplus-profile-forwarded-octets {
                                                    type yang:counter64;
                                                    description "The number of inplus-profile octets forwarded by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                                leaf exceed-profile-forwarded-packets {
                                                    type yang:counter64;
                                                    description "The number of exceed-profile packets forwarded by the packet processor to traffic manager";
                                                }

                                                leaf exceed-profile-forwarded-octets {
                                                    type yang:counter64;
                                                    description "The number of exceed-profile octets forwarded by the packet processor to traffic manager";
                                                }

                                            } // container offered-four-profile-no-cir

                                        }
                                        case offered-total-cir-four-profile {

                                            container offered-total-cir-four-profile {

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf inplus-profile-dropped-packets {
                                                    type yang:counter64;
                                                    description "The number of inplus-profile packets dropped by the packet processor to traffic manager";
                                                }

                                                leaf inplus-profile-dropped-octets {
                                                    type yang:counter64;
                                                    description "The number of inplus-profile octets dropped by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf exceed-profile-dropped-packets {
                                                    type yang:counter64;
                                                    description "The number of exceed-profile packets dropped by the packet processor to traffic manager";
                                                }

                                                leaf exceed-profile-dropped-octets {
                                                    type yang:counter64;
                                                    description "The number of exceed-profile octets dropped by the packet processor to traffic manager";
                                                }

                                                leaf inplus-profile-forwarded-packets {
                                                    type yang:counter64;
                                                    description "The number of inplus-profile packets forwarded by the packet processor to traffic manager";
                                                }

                                                leaf inplus-profile-forwarded-octets {
                                                    type yang:counter64;
                                                    description "The number of inplus-profile octets forwarded by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                                leaf exceed-profile-forwarded-packets {
                                                    type yang:counter64;
                                                    description "The number of exceed-profile packets forwarded by the packet processor to traffic manager";
                                                }

                                                leaf exceed-profile-forwarded-octets {
                                                    type yang:counter64;
                                                    description "The number of exceed-profile octets forwarded by the packet processor to traffic manager";
                                                }

                                            } // container offered-total-cir-four-profile

                                        }
                                        case v4-v6 {

                                            container v4-v6 {

                                                leaf ipv4-offered-packets {
                                                    type yang:counter64;
                                                    description "The number of ipv4 packets offered by the packet processor to traffic manager";
                                                }

                                                leaf ipv4-offered-octets {
                                                    type yang:counter64;
                                                    description "The number of ipv4 octets offered by the packet processor to traffic manager";
                                                }

                                                leaf ipv6-offered-packets {
                                                    type yang:counter64;
                                                    description "The number of ipv6 packets offered by the packet processor to traffic manager";
                                                }

                                                leaf ipv6-offered-octets {
                                                    type yang:counter64;
                                                    description "The number of ipv6 octets offered by the packet processor to traffic manager";
                                                }

                                                leaf ipv4-dropped-packets {
                                                    type yang:counter64;
                                                    description "The number of ipv4 packets dropped by the packet processor to traffic manager";
                                                }

                                                leaf ipv4-dropped-octets {
                                                    type yang:counter64;
                                                    description "The number of ipv4 octets dropped by the packet processor to traffic manager";
                                                }

                                                leaf ipv6-dropped-packets {
                                                    type yang:counter64;
                                                    description "The number of ipv6 packets dropped by the packet processor to traffic manager";
                                                }

                                                leaf ipv6-dropped-octets {
                                                    type yang:counter64;
                                                    description "The number of ipv6 octets dropped by the packet processor to traffic manager";
                                                }

                                                leaf ipv4-forwarded-packets {
                                                    type yang:counter64;
                                                    description "The number of ipv4 packets forwarded by the packet processor to traffic manager";
                                                }

                                                leaf ipv4-forwarded-octets {
                                                    type yang:counter64;
                                                    description "The number of ipv4 octets forwarded by the packet processor to traffic manager";
                                                }

                                                leaf ipv6-forwarded-packets {
                                                    type yang:counter64;
                                                    description "The number of ipv6 packets forwarded by the packet processor to traffic manager";
                                                }

                                                leaf ipv6-forwarded-octets {
                                                    type yang:counter64;
                                                    description "The number of ipv6 octets forwarded by the packet processor to traffic manager";
                                                }

                                            } // container v4-v6

                                        }
                                        case bonding {

                                            container bonding {

                                                leaf connection-1-offered-packets {
                                                    type yang:counter64;
                                                    description "The number of connection-1 packets offered by the packet processor to traffic manager";
                                                }

                                                leaf connection-1-offered-octets {
                                                    type yang:counter64;
                                                    description "The number of connection-1 octets offered by the packet processor to traffic manager";
                                                }

                                                leaf connection-2-offered-packets {
                                                    type yang:counter64;
                                                    description "The number of connection-2 packets offered by the packet processor to traffic manager";
                                                }

                                                leaf connection-2-offered-octets {
                                                    type yang:counter64;
                                                    description "The number of connection-2 octets offered by the packet processor to traffic manager";
                                                }

                                                leaf connection-1-dropped-packets {
                                                    type yang:counter64;
                                                    description "The number of connection-1 packets dropped by the packet processor to traffic manager";
                                                }

                                                leaf connection-1-dropped-octets {
                                                    type yang:counter64;
                                                    description "The number of connection-1 octets dropped by the packet processor to traffic manager";
                                                }

                                                leaf connection-2-dropped-packets {
                                                    type yang:counter64;
                                                    description "The number of connection-2 packets dropped by the packet processor to traffic manager";
                                                }

                                                leaf connection-2-dropped-octets {
                                                    type yang:counter64;
                                                    description "The number of connection-2 octets dropped by the packet processor to traffic manager";
                                                }

                                                leaf connection-1-forwarded-packets {
                                                    type yang:counter64;
                                                    description "The number of connection-1 packets forwarded by the packet processor to traffic manager";
                                                }

                                                leaf connection-1-forwarded-octets {
                                                    type yang:counter64;
                                                    description "The number of connection-1 octets forwarded by the packet processor to traffic manager";
                                                }

                                                leaf connection-2-forwarded-packets {
                                                    type yang:counter64;
                                                    description "The number of connection-2 packets forwarded by the packet processor to traffic manager";
                                                }

                                                leaf connection-2-forwarded-octets {
                                                    type yang:counter64;
                                                    description "The number of connection-2 octets forwarded by the packet processor to traffic manager";
                                                }

                                            } // container bonding

                                        }
                                    }
                                } // container statistics

                            } // list policer

                        } // container sap-egress

                    } // container qos

                } // container egress

                container igmp-host-tracking {
                    description "Enter the igmp-host-tracking context";

                    leaf group-count {
                        type int32;
                        description "The number of multicast groups which have been learned on this interface.";
                    }

                    list host-statistics {
                        key "host-address";
                        description "Statistics associated with this multicast stream";

                        leaf host-address {
                            type types-sros:ipv4-address;
                            description "The IP address of this host.";
                        }

                        leaf v2-reports {
                            type yang:counter32;
                            description "V2 Reports.";
                        }

                        leaf leaves {
                            type yang:counter32;
                            description "V2 Leaves.";
                        }

                        leaf v3-reports {
                            type yang:counter32;
                            description "V3 Reports.";
                        }

                        leaf drops {
                            type yang:counter32;
                            description "Total number of dropped packets.";
                        }

                        leaf group-joins {
                            type yang:counter32;
                            description "Total number of joins.";
                        }

                        leaf group-leaves {
                            type yang:counter32;
                            description "Total number of leaves.";
                        }

                        leaf group-expiries {
                            type yang:counter32;
                            description "Total number of group expiries.";
                        }

                        leaf import-policy-drops {
                            type yang:counter32;
                            description
                                "Number of times we matched the host IP address or
                                 group or source addresses specified in the import
                                 policy.";
                        }

                        leaf maximum-number-groups-drops {
                            type yang:counter32;
                            description
                                "Number of times a join is dropped because we reached
                                 the maximum number of groups.";
                        }

                        leaf maximum-number-sources-drops {
                            type yang:counter32;
                            description
                                "Number of times a join is dropped because we reached
                                 the maximum number of sources per group.";
                        }

                        leaf maximum-number-group-sources-drops {
                            type yang:counter32;
                            description
                                "Number of times a join is dropped because we reached
                                 the maximum number group-source combinations.";
                        }

                    } // list host-statistics

                    list host-group-sources {
                        key "host-address group-address source-address";
                        description
                            "Information about a particular host associated with this
                             multicast stream";

                        leaf host-address {
                            type types-sros:ipv4-address;
                            description "The IP address of this host.";
                        }

                        leaf group-address {
                            type types-sros:ipv4-multicast-address;
                            description "Group address of static IGMP multicast channel";
                        }

                        leaf source-address {
                            type types-sros:ipv4-address;
                            description "Source address of multicast channel.";
                        }

                        leaf bandwidth {
                            type uint32;
                            units "kilobps";
                            description
                                "The bandwidth allocated to this host for this multicast
                                 stream.";
                        }

                        leaf up-time {
                            type uint32;
                            units "seconds";
                            description "The time elapsed since this entry was created.";
                        }

                        leaf expiry-time {
                            type uint32;
                            units "seconds";
                            description "The time remaining before this entry is aged out.";
                        }

                        leaf subscriber-id {
                            type types-sros:named-item;
                            description "The subscriber identification of this subscriber host.";
                        }

                    } // list host-group-sources

                } // container igmp-host-tracking

                container igmp-snooping {
                    description "Enter the igmp-snooping context";

                    container mcac {
                        description "Enter the mcac context";

                        leaf in-use-mandatory-bandwidth {
                            type uint32;
                            units "kilobps";
                            description
                                "The in-use bandwidth for the mandatory channels for this
                                 protocol interface instance.";
                        }

                        leaf in-use-optional-bandwidth {
                            type uint32;
                            units "kilobps";
                            description
                                "The in-use bandwidth for the optional channels for this
                                 protocol interface instance.";
                        }

                        leaf available-mandatory-bandwidth {
                            type uint32;
                            units "kilobps";
                            description
                                "The pre-reserved bandwidth for the mandatory channels for
                                 this interface instance.";
                        }

                        leaf available-optional-bandwidth {
                            type uint32;
                            units "kilobps";
                            description "The available bandwidth for this interface instance.";
                        }

                        leaf values-in-transit {
                            type boolean;
                            description
                                "The operational (available and in-use mandatory/optional) value for the
                                 following objects is in transition due to configuration change:
                                 - available-mandatory-bandwidth
                                 - available-bandwidth
                                 - in-use-mandatory-bandwidth
                                 - in-use-optional-bandwidth.";
                        }

                    } // container mcac

                    container statistics {
                        description "The IGMP statistics.";

                        container received {
                            description "Received message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                        } // container received

                        container transmitted {
                            description "Transmit message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                            leaf errors {
                                type yang:counter32;
                                description "Transmission Errors.";
                            }

                        } // container transmitted

                        container forwarded {
                            description "Forwarded message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf v3-reports {
                                type yang:counter32;
                                description "V3 Reports.";
                            }

                            leaf leaves {
                                type yang:counter32;
                                description "Leaves.";
                            }

                            leaf drops {
                                type yang:counter32;
                                description "Total number of dropped packets.";
                            }

                            leaf unknown-types {
                                type yang:counter32;
                                description "Unknown types.";
                            }

                            leaf errors {
                                type yang:counter32;
                                description "Forwarding Errors.";
                            }

                        } // container forwarded

                        container error {
                            description "Error message statistics.";

                            leaf bad-length {
                                type yang:counter32;
                                description "Bad length.";
                            }

                            leaf bad-ip-checksum {
                                type yang:counter32;
                                description "Bad Ip checksum.";
                            }

                            leaf unknown-type {
                                type yang:counter32;
                                description "Unknown type.";
                            }

                            leaf wrong-version {
                                type yang:counter32;
                                description "Wrong version.";
                            }

                            leaf import-policy-drops {
                                type yang:counter32;
                                description
                                    "Number of times we matched the host IP address or group or
                                     source addresses specified in the import policy.";
                            }

                            leaf missing-router-alert {
                                type yang:counter32;
                                description "Router alert flag is not set.";
                            }

                            leaf bad-encoding {
                                type yang:counter32;
                                description "Badly encoded.";
                            }

                            leaf local-scope {
                                type yang:counter32;
                                description "Link-local scope multicast group address.";
                            }

                            leaf mcac-policy-drops {
                                type yang:counter32;
                                description
                                    "Number of times a join is dropped because of applying a
                                     multicast CAC policy.";
                            }

                            leaf reached-maximum-number-groups {
                                type yang:counter32;
                                description
                                    "Number of times a join is dropped because we reached the maximum
                                     number of groups.";
                            }

                            leaf reached-maximum-number-group-sources {
                                type yang:counter32;
                                description
                                    "Number of times a join is dropped because we reached the maximum
                                     number group-source combinations.";
                            }

                            leaf reached-maximum-number-sources {
                                type yang:counter32;
                                description
                                    "Number of times a join is dropped because we reached the maximum
                                     number of sources per group.";
                            }

                            leaf out-of-memory-drops {
                                type yang:counter32;
                                description "Number of times a join is dropped because we ran out of memory.";
                            }

                            leaf mcs-failures {
                                type yang:counter32;
                                description "Number of times a group could not be synced through multi chassis synchronisation (MCS).";
                            }

                            leaf bad-igmp-checksum {
                                type yang:counter32;
                                description
                                    "Number of times a packet is dropped because of a bad IGMP
                                     header checksum.";
                            }

                            leaf zero-source-ip-addr {
                                type yang:counter32;
                                description "Number of times a packet is dropped because it has a zero source ip address.";
                            }

                            leaf send-query-cfg-drops {
                                type yang:counter32;
                                description "Number of times a query is dropped because send-queries is configured.";
                            }

                            leaf mvr-from-vpls-cfg-drops {
                                type yang:counter32;
                                description "Number of times a packet is dropped because mvr from-vpls could not be applied.";
                            }

                            leaf mvr-to-sap-cfg-drops {
                                type yang:counter32;
                                description "Number of times a packet is dropped because it has mvr to-sap configuration.";
                            }

                        } // container error

                    } // container statistics

                    list group {
                        key "group-address";
                        description "Multicast group membership information that joined on this port.";

                        leaf group-address {
                            type types-sros:ipv4-multicast-address;
                            description "Group address of static IGMP multicast channel";
                        }

                        leaf group-type {
                            type types-igmp:learn-type;
                        }

                        leaf filter-mode {
                            type types-igmp:filter-mode;
                        }

                        leaf expiry-time {
                            type uint32;
                            units "seconds";
                            description "The time left before multicast group timeout.";
                        }

                        leaf up-time {
                            type uint32;
                            units "seconds";
                            description "The time elapsed since this entry was created.";
                        }

                        leaf v1-host-timer {
                            type uint32;
                            units "seconds";
                            description
                                "The time remaining until the local router will assume that
                                 there are no longer any version 1 members.";
                        }

                        leaf v2-host-timer {
                            type uint32;
                            units "seconds";
                            description
                                "The time remaining until the local router will assume that
                                 there are no longer any version 2 members.";
                        }

                        leaf igmp-compatibility-mode {
                            type types-igmp:igmp-version;
                            description "Compatibility with older version routers.";
                        }

                        leaf mvr-from-vpls-name {
                            type types-services:service-name;
                            description
                                "The name of the vpls service from which the multicast streams
                                 corresponding to this group are copied.";
                        }

                        leaf mvr-to-sap-id {
                            type types-sros:sap;
                            description
                                "The sap to which the multicast streams corresponding to this
                                 group are copied.";
                        }

                        list source {
                            key "source-address";
                            description "List of multicast source information of the multicast group.";

                            leaf source-address {
                                type types-sros:ipv4-address;
                                description "Source address of multicast channel.";
                            }

                            leaf source-type {
                                type types-igmp:learn-type;
                            }

                            leaf forwarding-state {
                                type types-igmp:forwarding-state;
                                description "Traffic forwardeding state on this port.";
                            }

                            leaf expiry-time {
                                type uint32;
                                units "seconds";
                                description "The time left before multicast group timeout.";
                            }

                            leaf up-time {
                                type uint32;
                                units "seconds";
                                description "The time elapsed since this entry was created.";
                            }

                        } // list source

                    } // list group

                } // container igmp-snooping

                container mld-snooping {
                    description "Enter the mld-snooping context";

                    container statistics {
                        description "The MLD statistics.";

                        container received {
                            description "Received message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf leaves {
                                type yang:counter32;
                                description "Leaves.";
                            }

                            leaf drops {
                                type yang:counter32;
                                description "Total number of dropped packets.";
                            }

                        } // container received

                        container transmitted {
                            description "Transmit message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf leaves {
                                type yang:counter32;
                                description "Leaves.";
                            }

                            leaf drops {
                                type yang:counter32;
                                description "Total number of dropped packets.";
                            }

                            leaf errors {
                                type yang:counter32;
                                description "Transmission Errors.";
                            }

                        } // container transmitted

                        container forwarded {
                            description "Forwarded message statistics.";

                            leaf general-queries {
                                type yang:counter32;
                                description "General Queries.";
                            }

                            leaf group-queries {
                                type yang:counter32;
                                description "Group Specific Queries.";
                            }

                            leaf group-source-queries {
                                type yang:counter32;
                                description "Group and Source Specific Queries.";
                            }

                            leaf v1-reports {
                                type yang:counter32;
                                description "V1 Reports.";
                            }

                            leaf v2-reports {
                                type yang:counter32;
                                description "V2 Reports.";
                            }

                            leaf leaves {
                                type yang:counter32;
                                description "Leaves.";
                            }

                            leaf drops {
                                type yang:counter32;
                                description "Total number of dropped packets.";
                            }

                            leaf unknown-types {
                                type yang:counter32;
                                description "Unknown types.";
                            }

                            leaf errors {
                                type yang:counter32;
                                description "Forwarding Errors.";
                            }

                        } // container forwarded

                        container error {
                            description "Error message statistics.";

                            leaf bad-length {
                                type yang:counter32;
                                description "Bad length.";
                            }

                            leaf unknown-type {
                                type yang:counter32;
                                description "Unknown type.";
                            }

                            leaf wrong-version {
                                type yang:counter32;
                                description "Wrong version.";
                            }

                            leaf import-policy-drops {
                                type yang:counter32;
                                description
                                    "Number of times we matched the host IP address or group or
                                     source addresses specified in the import policy.";
                            }

                            leaf missing-router-alert {
                                type yang:counter32;
                                description "Router alert flag is not set.";
                            }

                            leaf bad-encoding {
                                type yang:counter32;
                                description "Badly encoded.";
                            }

                            leaf local-scope {
                                type yang:counter32;
                                description "Link-local scope multicast group address.";
                            }

                            leaf reserved-scope {
                                type yang:counter32;
                                description "Reserved scope multicast group address.";
                            }

                            leaf reached-maximum-number-groups {
                                type yang:counter32;
                                description
                                    "Number of times a join is dropped because we reached the maximum
                                     number of groups.";
                            }

                            leaf reached-maximum-number-group-sources {
                                type yang:counter32;
                                description
                                    "Number of times a join is dropped because we reached the maximum
                                     number group-source combinations.";
                            }

                            leaf reached-maximum-number-sources {
                                type yang:counter32;
                                description
                                    "Number of times a join is dropped because we reached the maximum
                                     number of sources per group.";
                            }

                            leaf out-of-memory-drops {
                                type yang:counter32;
                                description "Number of times a join is dropped because we ran out of memory.";
                            }

                            leaf mcs-failures {
                                type yang:counter32;
                                description "Number of times a group could not be synced through multi chassis synchronisation (MCS).";
                            }

                            leaf bad-mld-checksum {
                                type yang:counter32;
                                description
                                    "Number of times a packet is dropped because of a bad MLD
                                     header checksum.";
                            }

                            leaf zero-source-ip-addr {
                                type yang:counter32;
                                description "Number of times a packet is dropped because it has a zero source ip address.";
                            }

                            leaf send-query-cfg-drops {
                                type yang:counter32;
                                description "Number of times a query is dropped because send-queries is configured.";
                            }

                            leaf mvr-from-vpls-cfg-drops {
                                type yang:counter32;
                                description "Number of times a packet is dropped because mvr from-vpls could not be applied.";
                            }

                            leaf mvr-to-sap-cfg-drops {
                                type yang:counter32;
                                description "Number of times a packet is dropped because it has mvr to-sap configuration.";
                            }

                        } // container error

                    } // container statistics

                    list group {
                        key "group-address";
                        description "Multicast group membership information that joined on this port.";

                        leaf group-address {
                            type types-sros:ipv6-multicast-address;
                            description "Group address of multicast channel";
                        }

                        leaf group-type {
                            type types-igmp:learn-type;
                        }

                        leaf filter-mode {
                            type types-igmp:filter-mode;
                        }

                        leaf expiry-time {
                            type uint32;
                            units "seconds";
                            description "The time left before multicast group timeout.";
                        }

                        leaf up-time {
                            type uint32;
                            units "seconds";
                            description "The time elapsed since this entry was created.";
                        }

                        leaf v1-host-timer {
                            type uint32;
                            units "seconds";
                            description
                                "The time remaining until the local router will assume that
                                 there are no longer any version 1 members.";
                        }

                        leaf mld-compatibility-mode {
                            type types-igmp:mld-version;
                            description "Compatibility with older version routers.";
                        }

                        leaf mvr-from-vpls-name {
                            type types-services:service-name;
                            description
                                "The name of the vpls service from which the multicast streams
                                 corresponding to this group are copied.";
                        }

                        leaf mvr-to-sap-id {
                            type types-sros:sap;
                            description
                                "The sap to which the multicast streams corresponding to this
                                 group are copied.";
                        }

                        list source {
                            key "source-address";
                            description "List of multicast source information of the multicast group.";

                            leaf source-address {
                                type types-sros:ipv6-address;
                                description "Source address of multicast channel.";
                            }

                            leaf source-type {
                                type types-igmp:learn-type;
                            }

                            leaf forwarding-state {
                                type types-igmp:forwarding-state;
                                description "Traffic forwardeding state on this port.";
                            }

                            leaf expiry-time {
                                type uint32;
                                units "seconds";
                                description "The time left before multicast group timeout.";
                            }

                            leaf up-time {
                                type uint32;
                                units "seconds";
                                description "The time elapsed since this entry was created.";
                            }

                        } // list source

                    } // list group

                } // container mld-snooping

                container pim-snooping {
                    description "Enter the pim-snooping context";

                    container ipv4 {
                        description "PIM parameters for ipv4 on this service.";

                        leaf oper-state {
                            type types-sros:oper-state;
                            description
                                "The value of the this object indicates the operational
                                 state of PIM for this interface.";
                        }

                        leaf up-time {
                            type uint32;
                            units "seconds";
                            description "The time since this interface became operational.";
                        }

                        leaf group-count {
                            type uint32;
                            description
                                "The number of multicast groups which currently have this
                                 interface as an outgoing interface.";
                        }

                        leaf maximum-groups-until-now {
                            type uint32;
                            description "The highest value that 'group-count' had till now.";
                        }

                        leaf pseudo-wire-forwarder {
                            type boolean;
                            description
                                "Whether this interface is the forwarding interface
                                 of a pair of redundant pseudo-wire ports.";
                        }

                        container statistics {
                            description "The PIM statistics for Ipv4.";

                            leaf rx-packets {
                                type yang:counter32;
                                description "The number of multicast data packets received on this interface.";
                            }

                            leaf rx-hellos {
                                type yang:counter32;
                                description "The number of PIM hello messages received on this interface.";
                            }

                            leaf rx-join-prunes {
                                type yang:counter32;
                                description
                                    "The number of PIM
                                     Join Prune messages received on this interface.";
                            }

                            leaf tx-packets {
                                type yang:counter32;
                                description "The number of multicast data packets transmitted on this interface.";
                            }

                            leaf tx-join-prunes {
                                type yang:counter32;
                                description
                                    "The number of PIM
                                     Join Prune messages transmitted on this interface.";
                            }

                            leaf rx-hellos-dropped {
                                type yang:counter32;
                                description
                                    "The number of PIM Hello messages which were received on this interface but were
                                     dropped.";
                            }

                            leaf rx-neighbor-unknown {
                                type yang:counter32;
                                description
                                    "The number of PIM messages (other than Hello messages) which were received on this
                                     interface and were rejected because the adjacency with the neighbor
                                     router was not already established.";
                            }

                            leaf rx-bad-checksum-discard {
                                type yang:counter32;
                                description
                                    "The number of PIM messages received on this interface which were discarded because
                                     of bad checksum.";
                            }

                            leaf rx-bad-version-discard {
                                type yang:counter32;
                                description "The number of PIM messages with bad versions received on this interface.";
                            }

                            leaf rx-bad-encodings {
                                type yang:counter32;
                                description "The number of PIM messages with bad encodings received on this interface.";
                            }

                            leaf join-policy-drops {
                                type yang:counter32;
                                description
                                    "The number of times the join policy match resulted in dropping PIM Join-Prune
                                     Message or one of the source group contained in the message.";
                            }

                            leaf rx-join-prune-errors {
                                type yang:counter32;
                                description
                                    "The number of errors while processing Join-Prune messages received on this
                                     interface.";
                            }

                        } // container statistics

                        list neighbor {
                            key "neighbor-address";
                            description "List of the router's PIM neighbors.";

                            leaf neighbor-address {
                                type types-sros:ipv4-address;
                                description "This value indicates the IPv4 address of the PIM neighbor.";
                            }

                            leaf dr-priority {
                                type uint32;
                                description
                                    "This value indicates neighbor's DR priority which is received
                                     in the hello message. If the Hello Message did not contain
                                     the DR priority field, the value of priority will be '1'.";
                            }

                            leaf dr-priority-present {
                                type boolean;
                                description
                                    "This value of indicates whether the DR priority field was present
                                     in the Hello message received from the PIM neighbor.";
                            }

                            leaf tracking-support {
                                type boolean;
                                description
                                    "This value indicates whether the T bit in the LAN Prune Delay
                                     option was present in the Hello message. This indicates the
                                     neighbor's capability to disable Join message suppression.";
                            }

                            leaf lan-delay {
                                type uint32;
                                units "milliseconds";
                                description
                                    "This value indicates the value of lan delay field present in
                                     the Hello message received from the neighbor. ";
                            }

                            leaf lan-delay-present {
                                type boolean;
                                description
                                    "This value indicates whether the Hello message received from
                                     the neighbor contained the Lan Delay field.";
                            }

                            leaf generated-id {
                                type uint32;
                                description
                                    "This value indicates a randomly generated 32-bit value that is
                                     regenerated each time PIM forwarding is started or restarted on
                                     the interface, including when the router itself restarts.";
                            }

                            leaf override-interval {
                                type uint32;
                                units "milliseconds";
                                description
                                    "This value indicates the value of the override interval present
                                     in the Hello message.";
                            }

                            leaf up-time {
                                type uint32;
                                units "seconds";
                                description
                                    "This value indicates the time since this PIM neighbor (last)
                                     became a neighbor of the local router.";
                            }

                            leaf expiry-time {
                                type uint32;
                                units "seconds";
                                description
                                    "This value indicates the minimum time remaining before this
                                     PIM neighbor will be aged out.";
                            }

                            leaf hold-time {
                                type uint32;
                                units "seconds";
                                description
                                    "This value indicates the value of the hold time present in the
                                     Hello message.";
                            }

                            leaf join-attribute-support {
                                type boolean;
                                description
                                    "This value indicates whether the Hello Message received from
                                     the neighbor contained the Join Attribute field.";
                            }

                            list secondary-neighbor {
                                key "secondary-neighbor-address";
                                description "Each entry represents the secondary addresses advertised by PIM neighbor.";

                                leaf secondary-neighbor-address {
                                    type types-sros:ipv4-address;
                                    description
                                        "This value indicates the IPv4 address of the secondary PIM
                                         neighbor.";
                                }

                            } // list secondary-neighbor

                        } // list neighbor

                        list sg {
                            key "group-address source-address";
                            description "List of (*,G) and (S,G) entries for which this particular interface has state.";

                            leaf group-address {
                                type types-sros:ipv4-address;
                                description "The multicast group address of the entry.";
                            }

                            leaf source-address {
                                type types-sros:ipv4-address;
                                description "The source address of the multicast sender.";
                            }

                            leaf up-time {
                                type uint32;
                                units "seconds";
                                description "The time since this source group entry got created.";
                            }

                            leaf join-prune-state {
                                type types-pim:join-prune-state;
                                description
                                    "The Join Prune state for this entry on the interface.

                                     PIM Join or Prune messages are sent by the downstream routers
                                     towards the RPF' neighbor.";
                            }

                            leaf join-prune-timer {
                                type uint32;
                                units "seconds";
                                description
                                    "The time remaining before the router transitions the value of
                                     join-prune-state to 'no-info'.

                                     The timer is started or restarted when a valid Join message is
                                     received. If the value of this object is zero and
                                     join-prune-state is 'join' state, it means that the
                                     downstream router sent a holdtime of '0xffff'. In this case,
                                     join-prune-state will not transition until an appropriate
                                     cancelling of Join or Prune message is received.";
                            }

                            leaf prune-pending-timer {
                                type uint32;
                                units "seconds";
                                description
                                    "The time remaining before the router transitions the value of
                                     join-prune-state to 'no-info'.

                                     The timer is set when the PIM Prune message is received.";
                            }

                            leaf join-prune-rpt-state {
                                type types-pim:join-prune-state;
                                description
                                    "The Join Prune Rpt state for this entry on the interface.

                                     PIM Join or Prune messages are sent by the downstream routers towards the
                                     RPF' neighbor. (S,G,rpt) state is a result of receiving (S,G, rpt) JP message
                                     from the downstream router on the RP tree.";
                            }

                            leaf join-prune-rpt-timer {
                                type uint32;
                                units "seconds";
                                description
                                    "The time remaining before the router transitions the value of
                                     join-prune-rpt-state to 'no-info'.

                                     The timer is started or restarted when a valid Join message is
                                     received. If the value of this object is zero and
                                     join-prune-rpt-state is in 'join' state, it means that the
                                     downstream router sent a holdtime of '0xffff'. In this case,
                                     join-prune-rpt-state will not transition until an appropriate
                                     cancelling of Join or Prune message is received from the
                                     downstream router.";
                            }

                            leaf join-prune-rpt-pending-timer {
                                type uint32;
                                units "seconds";
                                description
                                    "The time remaining before the router transitions the value of
                                     join-prune-rpt-state to 'no-info'.

                                     The timer is set when the (S,G,rpt) PIM Prune message is received.";
                            }

                        } // list sg

                    } // container ipv4

                    container ipv6 {
                        description "PIM parameters for ipv6 on this service.";

                        leaf oper-state {
                            type types-sros:oper-state;
                            description
                                "The value of the this object indicates the operational
                                 state of PIM for this interface.";
                        }

                        leaf up-time {
                            type uint32;
                            units "seconds";
                            description "The time since this interface became operational.";
                        }

                        leaf group-count {
                            type uint32;
                            description
                                "The number of multicast groups which currently have this
                                 interface as an outgoing interface.";
                        }

                        leaf maximum-groups-until-now {
                            type uint32;
                            description "The highest value that 'group-count' had till now.";
                        }

                        leaf pseudo-wire-forwarder {
                            type boolean;
                            description
                                "Whether this interface is the forwarding interface
                                 of a pair of redundant pseudo-wire ports.";
                        }

                        container statistics {
                            description "The PIM statistics for Ipv6.";

                            leaf rx-packets {
                                type yang:counter32;
                                description "The number of multicast data packets received on this interface.";
                            }

                            leaf rx-hellos {
                                type yang:counter32;
                                description "The number of PIM hello messages received on this interface.";
                            }

                            leaf rx-join-prunes {
                                type yang:counter32;
                                description
                                    "The number of PIM
                                     Join Prune messages received on this interface.";
                            }

                            leaf tx-packets {
                                type yang:counter32;
                                description "The number of multicast data packets transmitted on this interface.";
                            }

                            leaf tx-join-prunes {
                                type yang:counter32;
                                description
                                    "The number of PIM
                                     Join Prune messages transmitted on this interface.";
                            }

                            leaf rx-hellos-dropped {
                                type yang:counter32;
                                description
                                    "The number of PIM Hello messages which were received on this interface but were
                                     dropped.";
                            }

                            leaf rx-neighbor-unknown {
                                type yang:counter32;
                                description
                                    "The number of PIM messages (other than Hello messages) which were received on this
                                     interface and were rejected because the adjacency with the neighbor
                                     router was not already established.";
                            }

                            leaf rx-bad-checksum-discard {
                                type yang:counter32;
                                description
                                    "The number of PIM messages received on this interface which were discarded because
                                     of bad checksum.";
                            }

                            leaf rx-bad-version-discard {
                                type yang:counter32;
                                description "The number of PIM messages with bad versions received on this interface.";
                            }

                            leaf rx-bad-encodings {
                                type yang:counter32;
                                description "The number of PIM messages with bad encodings received on this interface.";
                            }

                            leaf join-policy-drops {
                                type yang:counter32;
                                description
                                    "The number of times the join policy match resulted in dropping PIM Join-Prune
                                     Message or one of the source group contained in the message.";
                            }

                            leaf rx-join-prune-errors {
                                type yang:counter32;
                                description
                                    "The number of errors while processing Join-Prune messages received on this
                                     interface.";
                            }

                        } // container statistics

                        list neighbor {
                            key "neighbor-address";
                            description "List of the router's PIM neighbors.";

                            leaf neighbor-address {
                                type types-sros:ipv6-address;
                                description "This value indicates the IPv6 address of the PIM neighbor.";
                            }

                            leaf dr-priority {
                                type uint32;
                                description
                                    "This value indicates neighbor's DR priority which is received
                                     in the hello message. If the Hello Message did not contain
                                     the DR priority field, the value of priority will be '1'.";
                            }

                            leaf dr-priority-present {
                                type boolean;
                                description
                                    "This value of indicates whether the DR priority field was present
                                     in the Hello message received from the PIM neighbor.";
                            }

                            leaf tracking-support {
                                type boolean;
                                description
                                    "This value indicates whether the T bit in the LAN Prune Delay
                                     option was present in the Hello message. This indicates the
                                     neighbor's capability to disable Join message suppression.";
                            }

                            leaf lan-delay {
                                type uint32;
                                units "milliseconds";
                                description
                                    "This value indicates the value of lan delay field present in
                                     the Hello message received from the neighbor. ";
                            }

                            leaf lan-delay-present {
                                type boolean;
                                description
                                    "This value indicates whether the Hello message received from
                                     the neighbor contained the Lan Delay field.";
                            }

                            leaf generated-id {
                                type uint32;
                                description
                                    "This value indicates a randomly generated 32-bit value that is
                                     regenerated each time PIM forwarding is started or restarted on
                                     the interface, including when the router itself restarts.";
                            }

                            leaf override-interval {
                                type uint32;
                                units "milliseconds";
                                description
                                    "This value indicates the value of the override interval present
                                     in the Hello message.";
                            }

                            leaf up-time {
                                type uint32;
                                units "seconds";
                                description
                                    "This value indicates the time since this PIM neighbor (last)
                                     became a neighbor of the local router.";
                            }

                            leaf expiry-time {
                                type uint32;
                                units "seconds";
                                description
                                    "This value indicates the minimum time remaining before this
                                     PIM neighbor will be aged out.";
                            }

                            leaf hold-time {
                                type uint32;
                                units "seconds";
                                description
                                    "This value indicates the value of the hold time present in the
                                     Hello message.";
                            }

                            leaf join-attribute-support {
                                type boolean;
                                description
                                    "This value indicates whether the Hello Message received from
                                     the neighbor contained the Join Attribute field.";
                            }

                            list secondary-neighbor {
                                key "secondary-neighbor-address";
                                description "Each entry represents the secondary addresses advertised by PIM neighbor.";

                                leaf secondary-neighbor-address {
                                    type types-sros:ipv6-address;
                                    description
                                        "This value indicates the IPv6 address of the secondary PIM
                                         neighbor.";
                                }

                            } // list secondary-neighbor

                        } // list neighbor

                        list sg {
                            key "group-address source-address";
                            description "List of (*,G) and (S,G) entries for which this particular interface has state.";

                            leaf group-address {
                                type types-sros:ipv6-address;
                                description "The multicast group address of the entry.";
                            }

                            leaf source-address {
                                type types-sros:ipv6-address;
                                description "The source address of the multicast sender.";
                            }

                            leaf up-time {
                                type uint32;
                                units "seconds";
                                description "The time since this source group entry got created.";
                            }

                            leaf join-prune-state {
                                type types-pim:join-prune-state;
                                description
                                    "The Join Prune state for this entry on the interface.

                                     PIM Join or Prune messages are sent by the downstream routers
                                     towards the RPF' neighbor.";
                            }

                            leaf join-prune-timer {
                                type uint32;
                                units "seconds";
                                description
                                    "The time remaining before the router transitions the value of
                                     join-prune-state to 'no-info'.

                                     The timer is started or restarted when a valid Join message is
                                     received. If the value of this object is zero and
                                     join-prune-state is 'join' state, it means that the
                                     downstream router sent a holdtime of '0xffff'. In this case,
                                     join-prune-state will not transition until an appropriate
                                     cancelling of Join or Prune message is received.";
                            }

                            leaf prune-pending-timer {
                                type uint32;
                                units "seconds";
                                description
                                    "The time remaining before the router transitions the value of
                                     join-prune-state to 'no-info'.

                                     The timer is set when the PIM Prune message is received.";
                            }

                            leaf join-prune-rpt-state {
                                type types-pim:join-prune-state;
                                description
                                    "The Join Prune Rpt state for this entry on the interface.

                                     PIM Join or Prune messages are sent by the downstream routers towards the
                                     RPF' neighbor. (S,G,rpt) state is a result of receiving (S,G, rpt) JP message
                                     from the downstream router on the RP tree.";
                            }

                            leaf join-prune-rpt-timer {
                                type uint32;
                                units "seconds";
                                description
                                    "The time remaining before the router transitions the value of
                                     join-prune-rpt-state to 'no-info'.

                                     The timer is started or restarted when a valid Join message is
                                     received. If the value of this object is zero and
                                     join-prune-rpt-state is in 'join' state, it means that the
                                     downstream router sent a holdtime of '0xffff'. In this case,
                                     join-prune-rpt-state will not transition until an appropriate
                                     cancelling of Join or Prune message is received from the
                                     downstream router.";
                            }

                            leaf join-prune-rpt-pending-timer {
                                type uint32;
                                units "seconds";
                                description
                                    "The time remaining before the router transitions the value of
                                     join-prune-rpt-state to 'no-info'.

                                     The timer is set when the (S,G,rpt) PIM Prune message is received.";
                            }

                        } // list sg

                    } // container ipv6

                } // container pim-snooping

                container stp {
                    description "Enter the stp context";

                    list mst-instance {
                        key "mst-inst-number";
                        description "Enter the mst-instance list instance";

                        leaf mst-inst-number {
                            type uint32 {
                                range "1..4094";
                            }
                            description "Multiple Spanning Tree Instance number";
                        }

                        leaf port-role {
                            type enumeration {
                                enum "master"                       { value 0; }
                                enum "root"                         { value 1; }
                                enum "designated"                   { value 2; }
                                enum "alternate"                    { value 3; }
                                enum "backup"                       { value 4; }
                                enum "disabled"                     { value 5; }
                            }
                            description "The current role of the sap in the MSTI as defined by the Spanning Tree Protocol.";
                        }

                        leaf port-state {
                            type enumeration {
                                enum "disabled"                     { value 1; }
                                enum "blocking"                     { value 2; }
                                enum "listening"                    { value 3; }
                                enum "learning"                     { value 4; }
                                enum "forwarding"                   { value 5; }
                                enum "broken"                       { value 6; }
                                enum "discarding"                   { value 7; }
                            }
                            description
                                "The port's current state as defined by application of the
                                 Spanning Tree Protocol.";
                        }

                        leaf designated-bridge {
                            type binary {
                                length "8";
                            }
                            description
                                "The bridge identifier of the bridge which this port considers
                                 to be the designated bridge for this port's segment for this MSTI.";
                        }

                        leaf designated-port {
                            type int32;
                            description
                                "The port identifier of the port on the Designated Bridge
                                 for this port's segment for this MSTI.";
                        }

                    } // list mst-instance

                } // container stp

                container fdb {
                    description "Enter the fdb context";

                    container mac-move {
                        description "Mac-move information";

                        leaf remaining-down-time {
                            type union {
                                type uint32 {
                                    range "1..65534";
                                }
                                type enumeration {
                                    enum "never"                        { value 0; }
                                    enum "indefinite"                   { value 65535; }
                                }
                            }
                            units "seconds";
                            description
                                "The time remaining until the relearn-limit-exceeded oper-flag is cleared.
                                 When the value is 'indefinite', this flag will not be cleared automatically.
                                 Relearn-limit-exceeded oper-flag is set when sap is brought down 
                                 when mac-move max-rate is exceeded.";
                        }

                        leaf remaining-retry-reset-time {
                            type union {
                                type uint32 {
                                    range "1..4294967295";
                                }
                                type enumeration {
                                    enum "never"                        { value 0; }
                                }
                            }
                            units "seconds";
                            description
                                "The time remaining to reset the mac-move retries-left
                                 when the oper-state of sap is up.";
                        }

                        leaf rate-exceed-times-left {
                            type union {
                                type uint32 {
                                    range "1..4294967294";
                                }
                                type enumeration {
                                    enum "unlimited"                    { value -1; }
                                    enum "none"                         { value 0; }
                                }
                            }
                            description
                                "Counts down the number of times this SAP can exceed the
                                 VPLS mac-move max-rate and still be automatically
                                 brought up.";
                        }

                    } // container mac-move

                    container protected-src-mac-violation {
                        description "Protected source MAC violation state information";

                        leaf oper-state {
                            type boolean;
                            description "Operational state of the protected-source MAC violation feature.";
                        }

                        leaf oper-action {
                            type enumeration {
                                enum "oper-down"                    { value 1; }
                                enum "alarm-only"                   { value 2; }
                                enum "discard-frame"                { value 3; }
                            }
                            description "Operation state of the protected-source MAC violation action.";
                        }

                    } // container protected-src-mac-violation

                    container statistics {
                        description "FDB usage information";

                        leaf total {
                            type int32;
                            description "Number of entries allocated in the FDB ";
                        }

                        leaf static {
                            type int32;
                            description "Number of static entries in the FDB";
                        }

                        leaf learned {
                            type int32;
                            description "Number of learned entries in the FDB";
                        }

                        leaf oam {
                            type int32;
                            description "Number of OAM entries in the FDB";
                        }

                        leaf conditional-static {
                            type int32;
                            description "Number of conditional static entries in the FDB";
                        }

                        leaf dhcp {
                            type int32;
                            description "Number of dhcp-learned entries in the FDB";
                        }

                        leaf host {
                            type int32;
                            description "Number of host-learned entries in the FDB";
                        }

                        leaf interface {
                            type int32;
                            description "Number of interface entries in the FDB";
                        }

                        leaf bgp-evpn {
                            type int32;
                            description "Number of bgp-evpn entries in the FDB";
                        }

                        leaf evpn-static {
                            type int32;
                            description "Number of evpn static entries in the FDB";
                        }

                    } // container statistics

                } // container fdb

                container l2tpv3-session {
                    description "Enter the l2tpv3-session context";

                    leaf oper-state {
                        type types-sros:oper-state;
                        description "Operational status of this entry.";
                    }

                    leaf tunnel-status {
                        type enumeration {
                            enum "down"                         { value 1; }
                            enum "inprogress"                   { value 2; }
                            enum "connected"                    { value 3; }
                        }
                        description "State of the L2tpv3 tunnel.";
                    }

                    leaf oper-flags {
                        type bits {
                            bit sap-down                       { position 0; }
                            bit router-unreachable             { position 1; }
                            bit admin-down                     { position 2; }
                            bit tunnel-not-unique              { position 3; }
                        }
                        description "Reason why the L2tpv3 tunnel is operationally down.";
                    }

                    leaf last-oper-changed {
                        type yang:date-and-time;
                        description "Uptime at the time of the last operational status change of this l2tpv3 tunnel.";
                    }

                } // container l2tpv3-session

                container mvpls {
                    description "MVPLS state information";

                    leaf prune-state {
                        type types-services:mvpls-prune-state;
                        description
                            "The mVPLS prune state of the SAP. The leaf will be set to
                             not-applicable if the SAP is not managed by a mVPLS. If
                             the SAP is managed the state reflects whether or not
                             the SAP is pruned by the STP instance running in the
                             MVPLS instance.";
                    }

                    leaf service {
                        type types-sros:named-item-or-empty;
                        description
                            "Service name of the service where the STP instance is
                             running that is managing this SAP. This leaf is
                             only valid if mvpls-prune-state is different from
                             not-applicable.";
                    }

                    leaf sap {
                        type types-sros:sap;
                        description
                            "SAP in the MVPLS instance specified in mgmt-service
                             that is controlling this SAP.
                             This leaf is only valid if mvpls-prune-state is
                             different from not-applicable.";
                    }

                    leaf msti {
                        type types-services:msti-instance-or-zero;
                        description
                            "MST-instance in the MVPLS instance specified in
                             mgmt-service that is controlling this SAP. A
                             value of 0 indicates the CIST.
                             This leaf is only valid if mvpls-prune-state is
                             different from not-applicable.";
                    }

                } // container mvpls

                container data-instantiating-sap {
                    description "Data SAP instantiating information";

                    leaf status {
                        type types-services:sap-instance-status;
                        description
                            "Status of the SAP which is instantiating other SAPs controlled
                             by this SAP.
                             This leaf is valid for m-vpls services.";
                    }

                    leaf last-error {
                        type string;
                        description
                            "Last error encountered while instantiating SAPs controlled
                             by this SAP.
                             This leaf is valid for m-vpls services.";
                    }

                } // container data-instantiating-sap

                container topology-change-bit {
                    description "Topology change bit state information";

                    leaf in-bpdus {
                        type uint32;
                        description
                            "Number of BPDUs received on this SAP
                             with the Topology Change bit set.";
                    }

                    leaf out-bpdus {
                        type uint32;
                        description
                            "Number of BPDUs sent out this SAP
                             with the Topology Change bit set.";
                    }

                } // container topology-change-bit

                container lag {
                    description "Lag information";

                    leaf active-port {
                        type types-sros:port;
                        description
                            "Port on the lag associated with this SAP, that is used when
                             lag-per-link-hash is enabled on the lag or when lag-link-map-profile
                             is configured on this SAP.";
                    }

                    container per-link-hash-oper {
                        description "Lag per-link-hash information";

                        leaf class {
                            type int32;
                            description "Operational value for class associated with this SAP.";
                        }

                        leaf weight {
                            type int32;
                            description "Operational value used for weight associated with this SAP.";
                        }

                        leaf is-overriden {
                            type boolean;
                            description
                                "Whether administrative values, subscriber management determined
                                 operational weight and class are used for this SAP.";
                        }

                    } // container per-link-hash-oper

                } // container lag

                container msap {
                    description "Managed SAPs.";

                    leaf capture-sap-id {
                        type types-sros:sap;
                        description "SAP identifier of the capture sap that created this MSAP";
                    }

                    leaf capture-service {
                        type types-services:service-name;
                        description "Service identifier of the capture sap that created this MSAP";
                    }

                    leaf msap-policy {
                        type types-sros:named-item;
                        description "The msap-policy used to create this MSAP";
                    }

                    leaf idle {
                        type boolean;
                        description "A managed SAP is considered idle when no hosts are associated with it.";
                    }

                    leaf sticky {
                        type boolean;
                        description "A sticky managed SAP will not be removed automatically.";
                    }

                } // container msap

                container arp-host {
                    description "Enter the arp-host context";

                    container statistics {

                        leaf last-cleared-time {
                            type yang:date-and-time;
                            description "The last time that these stats were cleared";
                        }

                        leaf hosts {
                            type yang:gauge32;
                            description "The actual number of ARP hosts on this SAP";
                        }

                        leaf triggers-received {
                            type yang:counter32;
                            description "The number of ARP triggers received on this SAP";
                        }

                        leaf error-triggers-dropped {
                            type yang:counter32;
                            description "ARP triggers that are dropped due to various error conditions";
                        }

                        leaf overload-triggers-dropped {
                            type yang:counter32;
                            description
                                "ARP triggers that are dropped because of too many outstanding
                                 requests";
                        }

                        leaf forced-verifications {
                            type yang:counter32;
                            description "The number of times a host connectivity verification was forced";
                        }

                        leaf hosts-created {
                            type yang:counter32;
                            description "The number of times an ARP host was created on this SAP";
                        }

                        leaf hosts-deleted {
                            type yang:counter32;
                            description "The number of times an ARP host was deleted on this SAP";
                        }

                        leaf hosts-updated {
                            type yang:counter32;
                            description "The number of times an ARP host was updated on this SAP";
                        }

                        leaf authentication-requests {
                            type yang:counter32;
                            description
                                "The number of times an authentication request was initiated
                                 by the system for an ARP host on this SAP";
                        }

                    } // container statistics

                } // container arp-host

                container dhcp {
                    description "Enter the dhcp context";

                    container lease-populate {
                        description "Enter the lease-populate context";

                        leaf current-lease-states {
                            type uint32 {
                                range "0..131071";
                            }
                            description "The number of DHCP lease states currently allocated on this interface.";
                        }

                    } // container lease-populate

                    container statistics {
                        description "Packet statistics";

                        container client-packets {
                            description "Client packet statistics";

                            leaf snooped {
                                type yang:counter32;
                                description "The number of DHCP client packets that have been snooped on this SAP.";
                            }

                            leaf forwarded {
                                type yang:counter32;
                                description "The number  of  DHCP  client  packets  that have been forwarded on this SAP.";
                            }

                            leaf dropped {
                                type yang:counter32;
                                description "The number  of  DHCP  client  packets  that have been dropped on this SAP.";
                            }

                            container proxied {
                                description "Proxied packet statistics";

                                leaf radius {
                                    type yang:counter32;
                                    description
                                        "The number of DHCP client packets that have been proxied on this SAP
                                         based on data received from a RADIUS server.";
                                }

                                leaf lease-split {
                                    type yang:counter32;
                                    description
                                        "The number of DHCP client packets that have been proxied on this SAP
                                         based on lease state.";
                                }

                            } // container proxied

                        } // container client-packets

                        container server-packets {
                            description "Server packet statistics";

                            leaf snooped {
                                type yang:counter32;
                                description "The number of DHCP server packets that have been snooped on this SAP.";
                            }

                            leaf forwarded {
                                type yang:counter32;
                                description "The number  of  DHCP  server  packets  that have been forwarded on this SAP.";
                            }

                            leaf dropped {
                                type yang:counter32;
                                description "The number  of  DHCP  server  packets  that have been dropped on this SAP.";
                            }

                        } // container server-packets

                        container spoofed {
                            description "Spoofed packet statistics";

                            leaf force-renews {
                                type yang:counter32;
                                description "The number of DHCP FORCERENEW messages spoofed on this SAP to the DHCP clients.";
                            }

                            leaf releases {
                                type yang:counter32;
                                description "The number of DHCP RELEASE messages spoofed on this SAP to the DHCP server.";
                            }

                        } // container spoofed

                    } // container statistics

                } // container dhcp

                container static-host {
                    description "Enter the static-host context";

                    list ipv4 {
                        key "ip mac";
                        description "Enter the ipv4 list instance";

                        leaf ip {
                            type types-sros:ipv4-address;
                            description "IP address";
                        }

                        leaf mac {
                            type types-sros:mac-unicast-address;
                            description "MAC address";
                        }

                        leaf dynamic-mac {
                            type yang:mac-address;
                            description "The dynamically learned MAC address for this host.";
                        }

                        leaf retail-service {
                            type types-services:service-name;
                            description
                                "The service name of the retailer service
                                 to which this static host belongs.";
                        }

                        leaf retail-interface {
                            type types-sros:named-item;
                            description
                                "The interface name of the retailer service interface to which
                                 this static host belongs.";
                        }

                        leaf forwarding-state {
                            type types-sros:oper-state;
                            description "Forwarding state of this static host.";
                        }

                        container shcv {
                            description "Enter the shcv context";

                            leaf oper-state {
                                type enumeration {
                                    enum "disabled"                     { value 1; }
                                    enum "down"                         { value 2; }
                                    enum "up"                           { value 3; }
                                }
                                description
                                    "The state of the subscriber host connectivity
                                     check for this static host.";
                            }

                            leaf checks {
                                type yang:gauge32;
                                description "The number of connectivity checks for this static host.";
                            }

                            leaf replies {
                                type yang:gauge32;
                                description "The number of host replies for this static host.";
                            }

                            leaf reply-time {
                                type yang:timestamp;
                                description
                                    "The timestamp of the last successful connectivity
                                     check for this static host.";
                            }

                        } // container shcv

                    } // list ipv4

                } // container static-host

                container eth-cfm {
                    description "Enter the eth-cfm context";

                    list mep {
                        key "md-admin-name ma-admin-name mep-id";
                        description "Enter the mep list instance";

                        leaf md-admin-name {
                            type leafref {
                                path "../../../../../../eth-cfm/domain/md-admin-name";
                            }
                            description "Admin-assigned maintenance domain index value";
                        }

                        leaf ma-admin-name {
                            type leafref {
                                path "../../../../../../eth-cfm/domain[md-admin-name=current()/../md-admin-name]/association/ma-admin-name";
                            }
                            description "Admin-assigned maintenance association index value";
                        }

                        leaf mep-id {
                            type types-eth-cfm:mep-id-type;
                            description "MEP identifier";
                        }

                    } // list mep

                } // container eth-cfm

                list locked-out-host {
                    key "id";
                    description "Locked out host";

                    leaf id {
                        type uint32;
                        description "Id of the locked out host";
                    }

                    leaf mac-address {
                        type yang:mac-address;
                        description "Mac-address of the locked out host";
                    }

                    leaf circuit-id {
                        type binary {
                            length "1..256";
                        }
                        description "Circuit-id of the locked out host";
                    }

                    leaf remote-id {
                        type binary {
                            length "1..256";
                        }
                        description "Remote-id of the locked out host";
                    }

                    leaf elapsed-reset-time {
                        type uint32;
                        units "seconds";
                        description "Elapsed reset time";
                    }

                    leaf elapsed-lock-time {
                        type uint32;
                        units "seconds";
                        description "Elapsed lock time";
                    }

                    leaf current-lock-timeout {
                        type uint32;
                        units "seconds";
                        description "The timeout for the current lock interval";
                    }

                    leaf next-lock-timeout {
                        type uint32;
                        units "seconds";
                        description "The timeout for the next lock interval";
                    }

                    leaf lockout-count {
                        type uint32;
                        description "Number of lockouts";
                    }

                    leaf lockout-state {
                        type enumeration {
                            enum "graceful"                     { value 1; description "The host is allowed to authenticate and the reset timer
                            is running. Another authentication failure for this host
                            while in this state while change the state to active.
                            If the reset timer expires, the lock out for this host
                            is removed."; }
                            enum "active"                       { value 2; description "The host is not allowed to authenticate and the lock-out
                            timer is running. When the timer expires, the state is
                            changed to graceful."; }
                        }
                        description "Lockout state for this host";
                    }

                } // list locked-out-host

            } // list sap

            list capture-sap {
                key "sap-id";
                description "Enter the capture-sap list instance";

                leaf sap-id {
                    type types-sros:sap;
                    description "SAP identifier";
                }

                container trigger-packet {
                    description "Enter the trigger-packet context";

                    list statistics {
                        key "packet-type";
                        description "Statistics for the capture sap trigger packets";

                        leaf packet-type {
                            type enumeration {
                                enum "dhcp"                         { value 1; }
                                enum "pppoe"                        { value 2; }
                                enum "arp"                          { value 3; }
                                enum "dhcp6"                        { value 4; }
                                enum "ppp"                          { value 5; }
                                enum "rtrsol"                       { value 6; }
                                enum "data"                         { value 7; }
                            }
                            description "The trigger-packet type for which statistics are returned";
                        }

                        leaf received {
                            type yang:counter32;
                            description "The number of packets received";
                        }

                        leaf redirected {
                            type yang:counter32;
                            description "The number of packets redirected";
                        }

                        leaf dropped {
                            type yang:counter32;
                            description "The number of packets dropped";
                        }

                    } // list statistics

                } // container trigger-packet

                list locked-out-host {
                    key "id";
                    description "Locked out host";

                    leaf id {
                        type uint32;
                        description "Id of the locked out host";
                    }

                    leaf mac-address {
                        type yang:mac-address;
                        description "Mac-address of the locked out host";
                    }

                    leaf circuit-id {
                        type binary {
                            length "1..256";
                        }
                        description "Circuit-id of the locked out host";
                    }

                    leaf remote-id {
                        type binary {
                            length "1..256";
                        }
                        description "Remote-id of the locked out host";
                    }

                    leaf elapsed-reset-time {
                        type uint32;
                        units "seconds";
                        description "Elapsed reset time";
                    }

                    leaf elapsed-lock-time {
                        type uint32;
                        units "seconds";
                        description "Elapsed lock time";
                    }

                    leaf current-lock-timeout {
                        type uint32;
                        units "seconds";
                        description "The timeout for the current lock interval";
                    }

                    leaf next-lock-timeout {
                        type uint32;
                        units "seconds";
                        description "The timeout for the next lock interval";
                    }

                    leaf lockout-count {
                        type uint32;
                        description "Number of lockouts";
                    }

                    leaf lockout-state {
                        type enumeration {
                            enum "graceful"                     { value 1; description "The host is allowed to authenticate and the reset timer
                            is running. Another authentication failure for this host
                            while in this state while change the state to active.
                            If the reset timer expires, the lock out for this host
                            is removed."; }
                            enum "active"                       { value 2; description "The host is not allowed to authenticate and the lock-out
                            timer is running. When the timer expires, the state is
                            changed to graceful."; }
                        }
                        description "Lockout state for this host";
                    }

                } // list locked-out-host

            } // list capture-sap

            list interface {
                key "interface-name";
                description "Enter the interface list instance";

                leaf interface-name {
                    type types-sros:interface-name;
                    description "Router interface name";
                }

                leaf if-index {
                    type int32;
                    description "The interface index.";
                }

                leaf system-if-index {
                    type int32;
                    description "The interface system index.";
                }

                container hold-time {
                    description "Enter the hold-time context";

                    container ipv4 {
                        description "Enter the ipv4 context";

                        leaf hold-timer {
                            type uint32;
                            units "seconds";
                            description
                                "The hold-timer indicates the time left before
                                 the interface comes up or goes down, depending on the ongoing
                                 transition state of the interface.";
                        }

                    } // container ipv4

                } // container hold-time

                container ipv4 {
                    description "Enter the ipv4 context";

                    leaf oper-state {
                        type types-sros:oper-state;
                        description "The current IPv4 operational status of this router interface.";
                    }

                    leaf down-reason {
                        type bits {
                            bit admin-disabled                 { position 0; }
                            bit service-admin-disabled         { position 1; }
                            bit port-down                      { position 2; }
                            bit address-or-parent-not-ready    { position 3; }
                            bit associated-object-not-ready    { position 4; }
                            bit rvpls-down                     { position 5; }
                            bit operational-group-down         { position 6; }
                            bit admin-destroy                  { position 7; }
                            bit no-address                     { position 8; }
                            bit no-info                        { position 9; }
                            bit hold-down-timer-running        { position 10; }
                            bit protocol-down                  { position 11; }
                            bit invalid-port-configuration     { position 12; }
                            bit unknown                        { position 13; }
                            bit no-route-distinguisher         { position 14; }
                            bit wlan-gateway-redundancy-standby { position 15; }
                            bit wlan-gateway-group-degraded    { position 16; }
                            bit ip-control-tunnel-down         { position 17; }
                            bit pdn-address-mismatch           { position 18; }
                        }
                        description
                            "Indicates the reason for why the interface is operationally down.
                                             
                             Values:
                                 admin-disabled                  - Administratively disabled.
                                 service-admin-disabled          - Assiocated service is administratively disabled.
                                 port-down                       - Associated SAP/port is operationally down.
                                 address-or-parent-not-ready     - Associated address or parent interface is not ready.
                                 associated-object-not-ready     - Associated object is not ready.
                                 rvpls-down                      - Associated R-VPLS service is operationally down.
                                 operational-group-down          - Associated operational group is operationally down.
                                 admin-destroy                   - The interface is being destroyed.
                                 no-address                      - There is no address configured.
                                 no-info                         - The interface info is not present.
                                 hold-down-timer-running         - The hold down timer is running.
                                 protocol-down                   - The protocols are operationally down.
                                 invalid-port-configuration      - Invalid port configuration.
                                 unknown                         - The interface is operationally down due to some unknown reason.
                                 no-route-distinguisher          - No route-distinguisher configured in the VRF.
                                 wlan-gateway-redundancy-standby - The interface is in standby state for WLAN-GW redundancy.
                                 wlan-gateway-group-degraded     - The interface associated WLAN-GW group is in a degraded state.
                                 ip-control-tunnel-down          - The IP tunnel associated to a control-tunnel interface is operationally down.
                                 pdn-address-mismatch            - The IP address learned from the packet data network does not match the configured primary IP address.";
                    }

                    container primary {
                        description "Enter the primary context";

                        leaf oper-address {
                            type types-sros:ip-address;
                            description "Indicates the operational address of this entry.";
                        }

                        leaf creation-origin {
                            type types-sros:creation-origin;
                            description "Indicates the mechanism used to create this entry.";
                        }

                    } // container primary

                    container neighbor-discovery {
                        description "Enter the neighbor-discovery context";

                        list neighbor {
                            key "ipv4-address";
                            description "IP-to-MAC address mapping state parameters on the interface.";

                            leaf ipv4-address {
                                type types-sros:ipv4-address;
                                description "IPv4 address corresponding to the media-dependent physical address";
                            }

                            leaf oper-state {
                                type types-sros:oper-state;
                                description "Indicates if the ARP entry is being used actively in the ARP table.";
                            }

                            leaf mac-address {
                                type yang:mac-address;
                                description "The media-dependent physical address.";
                            }

                            leaf type {
                                type enumeration {
                                    enum "other"                        { value 0; }
                                    enum "static"                       { value 1; }
                                    enum "dynamic"                      { value 2; }
                                    enum "managed"                      { value 100; }
                                    enum "evpn"                         { value 101; }
                                }
                                description "The type of mapping.";
                            }

                            leaf timer {
                                type uint32 {
                                    range "0..65535";
                                }
                                units "seconds";
                                description
                                    "Indicates how much longer an ARP entry remains in the ARP cache.

                                     When timer has a value of zero, the entry is cleared from the cache.";
                            }

                        } // list neighbor

                    } // container neighbor-discovery

                } // container ipv4

            } // list interface

        } // list vpls

    } // grouping state-svc-vpls

}
