module nokia-types-rsvp {

    yang-version "1.1";

    namespace "urn:nokia.com:sros:ns:yang:sr:types-rsvp";

    prefix "types-rsvp";

    import nokia-sros-yang-extensions     { prefix "sros-ext"; }


    sros-ext:sros-major-release "rel19";

    organization "Nokia";

    contact
        "Nokia SR OS Support
         Web: <http://www.nokia.com>";

    description
        "Common rsvp types data types used in the SR OS management system.

         Copyright 2016 Nokia. All rights reserved. Reproduction of this document
         is authorized on the condition that the foregoing copyright notice is included.

         This nokia-types-rsvp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2018-02-08";

    typedef rsvp-te-threshold-level {
        type int32 {
            range "0..100";
        }
        description
            "Is an integer in the range of (0..100)
             that defines the traffic engineering (TE) threshold level.";
    }

}
