submodule nokia-state-submgt-wlangw {

    yang-version "1.1";

    belongs-to nokia-state { prefix "state"; }

    import ietf-yang-types                { prefix "yang"; }
    import nokia-sros-yang-extensions     { prefix "sros-ext"; }
    import nokia-types-isa                { prefix "types-isa"; }
    import nokia-types-nat                { prefix "types-nat"; }
    import nokia-types-qos                { prefix "types-qos"; }
    import nokia-types-services           { prefix "types-services"; }
    import nokia-types-sros               { prefix "types-sros"; }
    import nokia-types-wlangw             { prefix "types-wlangw"; }


    sros-ext:sros-major-release "rel21";

    organization "Nokia";

    contact
        "Nokia SR OS Support
         Web: <http://www.nokia.com>";

    description
        "Nokia YANG Data model with operational state for subscriber management WLAN Gateway on SR OS based routers.

         Copyright 2016 Nokia. All rights reserved. Reproduction of this document
         is authorized on the condition that the foregoing copyright notice is included.

         This nokia-state-submgt-wlangw YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-11-19";

    grouping state-submgt-wlangw-wlan-gw {
        container wlan-gw {
            description "Enter the wlan-gw context";

            container queries {
                description "Enter the queries context";

                list ue {
                    key "name";
                    description "Enter the ue list instance";

                    leaf name {
                        type types-sros:named-item;
                        description "Textual identification for the UE query";
                    }

                    leaf id {
                        type uint32;
                        description "The unique ID of this query";
                    }

                    leaf num-results {
                        type uint32;
                        description "The current number of UEs matching this query";
                    }

                    list result {
                        key "id";
                        description "Enter the result list instance";

                        leaf id {
                            type types-sros:hex-string {
                                length "18";
                            }
                            description "The identifier of the returned UE";
                        }

                        leaf bridge-domain {
                            type uint32;
                            description "The identifier of the Bridge Domain associated with this UE";
                        }

                        leaf mac-address {
                            type types-sros:mac-unicast-address;
                            description "The MAC address of the UE";
                        }

                        leaf connection-state {
                            type enumeration {
                                enum "new"                          { value 1; description "The UE is being created. This is a short-lived transient
                                state"; }
                                enum "data-triggered"               { value 2; description "The UE has been created and is being authenticated due
                                to a data-trigger"; }
                                enum "dhcp-triggered"               { value 3; description "The UE has been created and is being authenticated due
                                to a DHCP-trigger"; }
                                enum "ip-assigned"                  { value 4; description "The UE has been created and has been assigned an IP
                                address, but still needs authentication"; }
                                enum "authorized-only"              { value 5; description "The UE has been created and has been authorized but has
                                not received or requested an IP address yet"; }
                                enum "ip-assigned-authorized"       { value 6; description "The UE has been authorized, has been assigned an IP
                                address and is awaiting data traffic to be promoted to
                                Portal, DSM or ESM"; }
                                enum "already-signed-in"            { value 7; description "The UE has signed in successfully and is waiting for the
                                CPM to create ESM state"; }
                                enum "portal"                       { value 8; description "The UE has limited connectivity to a captive portal for
                                further authentication"; }
                                enum "dsm"                          { value 9; description "The UE is fully connected using distributed subscriber
                                management"; }
                                enum "esm"                          { value 10; description "The UE is fully connected using enhanced subscriber
                                management"; }
                                enum "l2"                           { value 11; description "The UE is fully connected to a VPLS service"; }
                                enum "gtp-authorized"               { value 12; description "The UE has been authorized for GTP but has not received
                                or requested an IP address yet"; }
                                enum "delete-pending"               { value 13; description "The UE is being removed"; }
                                enum "cross-connect"                { value 14; description "The UE is fully connected to a cross-connect tunnel"; }
                            }
                            description "The connection state of the UE";
                        }

                        leaf http-redirect-policy {
                            type types-sros:named-item;
                            description "The HTTP redirect policy of this UE";
                        }

                        leaf idle-timeout {
                            type uint32;
                            units "seconds";
                            description
                                "The time that this UE can remain inactive before it will be
                                 removed";
                        }

                        leaf session-timeout {
                            type yang:date-and-time;
                            description "The time when this UE's system context will be removed";
                        }

                        leaf last-forward {
                            type yang:date-and-time;
                            description "The last time that a packet from this UE was forwarded";
                        }

                        leaf nat-policy {
                            type types-sros:named-item;
                            description "The NAT policy used for DSM or ISA portal authentication";
                        }

                        leaf vlan {
                            type types-sros:qtag-full-range;
                            description "The VLAN tag present in the traffic received from this UE";
                        }

                        leaf mpls-label {
                            type types-sros:mpls-label-full-range;
                            description "The MPLS label present in the traffic received from this UE";
                        }

                        leaf wlan-gw-group {
                            type types-isa:wlan-gw-group-id;
                            description "The WLAN-GW ISA group associated with this UE";
                        }

                        leaf group-member {
                            type types-nat:bb-group-member;
                            description "The member of the WLAN-GW ISA group associated with this UE";
                        }

                        container address {
                            description "Enter the address context";

                            container ipv4 {
                                description "Enter the ipv4 context";

                                leaf address {
                                    type types-sros:ipv4-unicast-address;
                                    description "The IPv4 address assigned to this UE";
                                }

                                leaf deprecated {
                                    type boolean;
                                    description "Whether the IPv4 address is deprecated or not";
                                }

                                leaf expiration-time {
                                    type yang:date-and-time;
                                    description "When the lease of the IPv4 address will expire";
                                }

                            } // container ipv4

                            container dhcp6 {
                                description "Enter the dhcp6 context";

                                leaf addresss {
                                    type types-sros:ipv6-unicast-address;
                                    description "The DHCPv6 address assigned to this UE";
                                }

                                leaf deprecated {
                                    type boolean;
                                    description "Whether the DHCPv6 address is deprecated or not";
                                }

                                leaf expiration-time {
                                    type yang:date-and-time;
                                    description "When the lease of the DHCPv6 address will expire";
                                }

                                leaf identity-association-identifier {
                                    type uint32;
                                    description
                                        "The DHCPv6 Identity Association Identifier (IAID) of
                                         this UE";
                                }

                            } // container dhcp6

                            container slaac {
                                description "Enter the slaac context";

                                leaf prefix {
                                    type types-sros:ipv6-unicast-address;
                                    description "The SLAAC prefix assigned to this UE";
                                }

                                leaf-list addresses {
                                    type types-sros:ipv6-unicast-address;
                                    description "The SLAAC addresses used by this UE";
                                }

                                leaf expiration-time {
                                    type yang:date-and-time;
                                    description "When the SLAAC prefix and addresses will expire";
                                }

                            } // container slaac

                        } // container address

                        container access-point {
                            description "Enter the access-point context";

                            leaf last-move-time {
                                type yang:date-and-time;
                                description "The time of the most recent Access Point move of this UE";
                            }

                            leaf mac-address {
                                type types-sros:mac-unicast-address;
                                description "The MAC address of the Access Point of this UE";
                            }

                            leaf ssid {
                                type types-sros:named-item;
                                description "The Service Set ID (SSID) of this UE";
                            }

                        } // container access-point

                        container dsm {
                            description "Enter the dsm context";

                            container accounting {
                                description "Enter the accounting context";

                                leaf policy {
                                    type types-sros:named-item;
                                    description "The ISA RADIUS accounting policy assigned to this UE";
                                }

                                leaf update-interval {
                                    type uint32;
                                    units "seconds";
                                    description
                                        "The time interval between consecutive Interim
                                         Accounting Update messages";
                                }

                                leaf last-update-time {
                                    type yang:date-and-time;
                                    description
                                        "The time when the last accounting update for this UE
                                         was transmitted";
                                }

                            } // container accounting

                            container egress {
                                description "Enter the egress context";

                                leaf oper-cir {
                                    type types-qos:isa-policer-cir-rate;
                                    description "The actual egress CIR (Committed Information Rate)";
                                }

                                leaf oper-pir {
                                    type types-qos:isa-policer-pir-rate;
                                    description "The actual egress PIR (Peak Information Rate)";
                                }

                            } // container egress

                            container ingress {
                                description "Enter the ingress context";

                                leaf ip-filter {
                                    type types-sros:named-item;
                                    description "The ISA filter assigned to this UE";
                                }

                                leaf oper-cir {
                                    type types-qos:isa-policer-cir-rate;
                                    description "The actual ingress CIR (Committed Information Rate)";
                                }

                                leaf oper-pir {
                                    type types-qos:isa-policer-pir-rate;
                                    description "The actual ingress PIR (Peak Information Rate)";
                                }

                            } // container ingress

                            container statistics {
                                description "Enter the statistics context";

                                leaf rx-octets {
                                    type yang:counter64;
                                    description "Octets received from this UE";
                                }

                                leaf rx-packets {
                                    type yang:counter64;
                                    description "Packets received from this UE";
                                }

                                leaf tx-octets {
                                    type yang:counter64;
                                    description "Octets transmitted to this UE";
                                }

                                leaf tx-packets {
                                    type yang:counter64;
                                    description "Packets transmitted to this UE";
                                }

                            } // container statistics

                        } // container dsm

                        container tunnel {
                            description "Enter the tunnel context";

                            leaf router-instance {
                                type types-sros:router-instance;
                                description "The router-instance where the tunneled UE traffic is routed";
                            }

                            leaf remote-address {
                                type types-sros:ip-address;
                                description
                                    "IP address of the remote endpoint (Access Point) of this
                                     UE's tunnel";
                            }

                            leaf local-address {
                                type types-sros:ip-address;
                                description "IP address of the local endpoint of this UE's tunnel";
                            }

                            leaf encapsulation {
                                type types-wlangw:encapsulation;
                                description "Tunnel encapsulation type for this UE";
                            }

                        } // container tunnel

                    } // list result

                } // list ue

                list tunnel {
                    key "name";
                    description "Enter the tunnel list instance";

                    leaf name {
                        type types-sros:named-item;
                        description "Textual identification for the tunnel query";
                    }

                    leaf id {
                        type uint32;
                        description "The unique ID of this query";
                    }

                    leaf num-results {
                        type uint32;
                        description "The current number of tunnels matching this query";
                    }

                    list result {
                        key "router-instance encapsulation remote-address local-address";
                        description "Enter the result list instance";

                        leaf router-instance {
                            type types-sros:router-instance;
                            description "The router-instance where the tunneled traffic is routed";
                        }

                        leaf encapsulation {
                            type types-wlangw:encapsulation;
                            description "The encapsulation of this tunnel";
                        }

                        leaf remote-address {
                            type types-sros:ip-address;
                            description "IP address of the remote endpoint (Access Point) of this tunnel";
                        }

                        leaf local-address {
                            type types-sros:ip-address;
                            description "IP address of the local endpoint of this tunnel";
                        }

                        leaf service {
                            type types-services:service-name;
                            description "The service of the interface associated with this tunnel";
                        }

                        leaf subscriber-interface {
                            type types-sros:named-item;
                            description "The subscriber interface associated with this tunnel";
                        }

                        leaf group-interface {
                            type types-sros:named-item;
                            description "The group interface associated with this tunnel";
                        }

                        leaf wlan-gw-group {
                            type types-isa:wlan-gw-group-id;
                            description "The WLAN Gateway ISA group that processes this tunnel";
                        }

                        leaf group-member {
                            type types-nat:bb-group-member;
                            description "The ISA Group member that processes this tunnel";
                        }

                        container access-point {
                            description "Enter the access-point context";

                            leaf mac-address {
                                type types-sros:mac-unicast-address;
                                description "MAC address of the Access Point, as learned by this system";
                            }

                            leaf mac-learn-failed {
                                type boolean;
                                description
                                    "Whether learning of the MAC address of the Access Point
                                     failed";
                            }

                        } // container access-point

                        container l2 {
                            description "Enter the l2 context";

                            leaf sap {
                                type types-sros:sap;
                                description "The SAP of the L2 Access Point, as learned by this system";
                            }

                            leaf inner-vlan {
                                type types-sros:qtag-full-range;
                                description "Inner tag in case of qinq encapsulation";
                            }

                            leaf outer-vlan {
                                type types-sros:qtag-full-range;
                                description
                                    "VLAN tag in case of IEEE 802.1Q encapsulation, or the outer
                                     tag in case of qinq encapsulation";
                            }

                        } // container l2

                        container l2tp {
                            description "Enter the l2tp context";

                            leaf remote-udp-port {
                                type uint32;
                                description
                                    "The UDP port of the remote endpoint (access-point) in case
                                     of L2TPv3oUDP encapsulation";
                            }

                        } // container l2tp

                        container statistics {
                            description "Enter the statistics context";

                            container ue {
                                description "Enter the ue context";

                                leaf total {
                                    type yang:gauge32;
                                    description "The total number of UEs in this tunnel";
                                }

                                leaf migrant {
                                    type yang:gauge32;
                                    description "The number of migrant UEs in this tunnel";
                                }

                                leaf dsm {
                                    type yang:gauge32;
                                    description "The number of DSM UEs in this tunnel";
                                }

                                leaf esm {
                                    type yang:gauge32;
                                    description "The number of ESM UEs in this tunnel";
                                }

                                leaf l2 {
                                    type yang:gauge32;
                                    description "The number of Layer-2 Wholesale UEs in this tunnel";
                                }

                                leaf cross-connect {
                                    type yang:gauge32;
                                    description "The number of cross-connect UEs in this tunnel";
                                }

                            } // container ue

                        } // container statistics

                    } // list result

                } // list tunnel

            } // container queries

            container statistics {
                description "Enter the statistics context";

                leaf number-of-access-points {
                    type yang:gauge32;
                    description "Actual number of access points";
                }

                leaf peak-number-of-access-points {
                    type yang:gauge32;
                    description "Peak number of access points";
                }

                leaf number-of-ues {
                    type yang:gauge32;
                    description "Actual number of UEs";
                }

                leaf peak-number-of-ues {
                    type yang:gauge32;
                    description "Peak number of UEs";
                }

            } // container statistics

            list ssid {
                key "id";
                description "Enter the ssid list instance";

                leaf id {
                    type types-sros:named-item;
                    description "The 802.11 SSID";
                }

                leaf number-of-ues {
                    type yang:gauge32;
                    description
                        "The number of User Equipment's connected to this system
                         using this SSID";
                }

            } // list ssid

        } // container wlan-gw

    } // grouping state-submgt-wlangw-wlan-gw

}
