module nokia-sr-openconfig-mpls-augments {

    namespace "urn:nokia.com:sros:ns:yang:sr:nokia_sr_openconfig_mpls_augments";

    prefix "nokia-sr-oc-mpls-augments-devs";

    import nokia-sros-yang-extensions     { prefix "sros-ext"; }
    import openconfig-extensions          { prefix "oc-ext"; }
    import openconfig-inet-types          { prefix "oc-inet"; }
    import openconfig-interfaces          { prefix "oc-if"; }
    import openconfig-mpls                { prefix "oc-mpls"; }
    import openconfig-mpls-rsvp           { prefix "oc-rsvp"; }
    import openconfig-mpls-types          { prefix "oc-mplst"; }
    import openconfig-network-instance    { prefix "oc-netinst"; }
    import openconfig-rsvp-sr-ext         { prefix "oc-sr-rsvp-ext"; }
    import openconfig-types               { prefix "oc-types"; }

    sros-ext:sros-major-release "rel21";

    organization "Nokia";

    contact
        "Nokia SR OS Support
         Web: <http://www.nokia.com>";

    description
        "This module contains the list of augments against the -openconfig-mpls
          module for the Nokia SR OS based routers.

         Copyright 2016 Nokia. All rights reserved. Reproduction of this document
         is authorized on the condition that the foregoing copyright notice is included.

         This nokia-sr-openconfig-mpls-augments YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2017-03-22";

    augment /oc-netinst:network-instances/oc-netinst:network-instance/oc-netinst:mpls/oc-netinst:lsps/oc-netinst:constrained-path/oc-netinst:tunnels/oc-netinst:tunnel/oc-netinst:bandwidth/oc-netinst:auto-bandwidth/oc-netinst:config {
        description "Augment the lsps constrained-path tunnel auto-bandwidth config with the adjust and sample multipliers.";

        leaf sample-multiplier {
            type uint32 {
                range "1..511";
            }
            default "1";
            description "Configure collection intervals in a sample interval.";
        }

        leaf adjust-multiplier {
            type uint32 {
                range "1..16383";
            }
            default "288";
            description "Configure collection intervals in an adjust interval.";
        }

    }

    augment /oc-netinst:network-instances/oc-netinst:network-instance/oc-netinst:mpls/oc-netinst:lsps/oc-netinst:constrained-path/oc-netinst:tunnels/oc-netinst:tunnel/oc-netinst:p2p-tunnel-attributes/oc-netinst:p2p-secondary-paths/oc-netinst:p2p-secondary-path/oc-netinst:config {
        description "Augment the lsps constrained-path p2p tunnel attributes secondary path with the possibility to enable/disable the srlg path computation.";

        leaf srlg {
            type boolean;
            default "false";
            description "Enable/disable SRLG for secondary path computation.";
        }

    }

    augment /oc-netinst:network-instances/oc-netinst:network-instance/oc-netinst:mpls/oc-netinst:global/oc-netinst:state {
        description "Augment the MPLS global state with the srlg-frr.";

        leaf srlg-frr {
            type enumeration {
                enum "loose"                        { value 1; }
                enum "strict"                       { value 2; }
            }
            description "Enable/disable Shared Risk Link Group (SRLG) for fast reroute (FRR) path computation.";
        }

    }

    augment /oc-netinst:network-instances/oc-netinst:network-instance/oc-netinst:mpls/oc-netinst:lsps/oc-netinst:constrained-path/oc-netinst:tunnels/oc-netinst:tunnel/oc-netinst:state {
        description "Augment the lsps constrained-path tunnel state with the accounting policy id.";

        leaf policy-id {
            type uint32 {
                range "1..99";
            }
            description "Accounting policy unique identifier.";
        }

    }

    augment /oc-netinst:network-instances/oc-netinst:network-instance/oc-netinst:mpls/oc-netinst:signaling-protocols/oc-netinst:rsvp-te/oc-netinst:interface-attributes/oc-netinst:interface {
        description "Augment the signaling protocols rsvp-te global neighbors to the per-interface RSVP configuration.";

        container neighbors {
            description "Enter the neighbors context";

            list neighbor {
                key "address";
                config false;
                description "Enter the neighbor list instance";

                leaf address {
                    type leafref {
                        path "/oc-netinst:network-instances/oc-netinst:network-instance/oc-netinst:mpls/oc-netinst:signaling-protocols/oc-netinst:rsvp-te/oc-netinst:interface-attributes/oc-netinst:interface/nokia-sr-oc-mpls-augments-devs:neighbors/nokia-sr-oc-mpls-augments-devs:neighbor/nokia-sr-oc-mpls-augments-devs:state/nokia-sr-oc-mpls-augments-devs:address";
                    }
                    description "Reference to the address of the RSVP neighbor";
                }

                container state {
                    description "Enter the state context";

                    leaf address {
                        type oc-inet:ip-address;
                        description "Address of RSVP neighbor";
                    }

                    leaf detected-interface {
                        type string;
                        description "Interface where RSVP neighbor was detected";
                    }

                    leaf neighbor-status {
                        type enumeration {
                            enum "UP"                           { value 0; description "RSVP hello messages are detected from the neighbor"; }
                            enum "DOWN"                         { value 1; description "RSVP neighbor not detected as up, due to a
                            communication failure or IGP notification
                            the neighbor is unavailable"; }
                        }
                        description "Enumuration of possible RSVP neighbor states";
                    }

                    leaf refresh-reduction {
                        type boolean;
                        description "Suppport of neighbor for RSVP refresh reduction";
                    }

                } // container state

            } // list neighbor

        } // container neighbors

    }

    augment /oc-netinst:network-instances/oc-netinst:network-instance/oc-netinst:mpls/oc-netinst:lsps/oc-netinst:constrained-path/oc-netinst:tunnels/oc-netinst:tunnel/oc-netinst:p2p-tunnel-attributes/oc-netinst:p2p-secondary-paths/oc-netinst:p2p-secondary-path/oc-netinst:state {
        description "Augment the lsps constrained-path p2p tunnel attributes secondary path with the possibility to enable/disable the srlg path computation.";

        leaf srlg {
            type boolean;
            default "false";
            description "Enable/disable SRLG for secondary path computation.";
        }

    }

    augment /oc-netinst:network-instances/oc-netinst:network-instance/oc-netinst:mpls/oc-netinst:global {

    }

    augment /oc-netinst:network-instances/oc-netinst:network-instance/oc-netinst:mpls/oc-netinst:signaling-protocols/oc-netinst:rsvp-te/oc-netinst:global {
        description "Augment the signaling protocols rsvp-te global configuration with the protection bypass-optimize-interval.";

        container protection {
            description "Enter the protection context";

            container config {
                description "Enter the config context";

                leaf bypass-optimize-interval {
                    type uint32 {
                        range "1800..604800";
                    }
                    units "seconds";
                    description
                        "interval between periodic optimization
                         of the bypass LSPs";
                }

            } // container config

            container state {
                config false;
                description "Enter the state context";

                leaf bypass-optimize-interval {
                    type uint32 {
                        range "1800..604800";
                    }
                    units "seconds";
                    description
                        "interval between periodic optimization
                         of the bypass LSPs";
                }

            } // container state

        } // container protection

    }

    augment /oc-netinst:network-instances/oc-netinst:network-instance/oc-netinst:mpls/oc-netinst:lsps/oc-netinst:constrained-path/oc-netinst:tunnels/oc-netinst:tunnel/oc-netinst:config {
        description "Augment the lsps constrained-path tunnel config with the accounting policy id.";

        leaf policy-id {
            type uint32 {
                range "1..99";
            }
            description "Accounting policy unique identifier.";
        }

    }

    augment /oc-netinst:network-instances/oc-netinst:network-instance/oc-netinst:mpls/oc-netinst:global/oc-netinst:config {
        description "Augment the MPLS global config with the possibility to enable/disable the SRLG for FRR path computation.";

        leaf srlg-frr {
            type enumeration {
                enum "loose"                        { value 1; }
                enum "strict"                       { value 2; }
            }
            description "Enable/disable Shared Risk Link Group (SRLG) for fast reroute (FRR) path computation.";
        }

    }

    augment /oc-netinst:network-instances/oc-netinst:network-instance/oc-netinst:mpls/oc-netinst:lsps/oc-netinst:constrained-path/oc-netinst:tunnels/oc-netinst:tunnel/oc-netinst:bandwidth/oc-netinst:auto-bandwidth/oc-netinst:state {
        description "Augment the lsps constrained-path tunnel auto-bandwidth state with the adjust and sample multipliers.";

        leaf sample-multiplier {
            type uint32 {
                range "1..511";
            }
            default "1";
            description "Configure collection intervals in a sample interval.";
        }

        leaf adjust-multiplier {
            type uint32 {
                range "1..16383";
            }
            default "288";
            description "Configure collection intervals in an adjust interval.";
        }

    }

}
