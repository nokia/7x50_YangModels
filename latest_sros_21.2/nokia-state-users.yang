submodule nokia-state-users {

    yang-version "1.1";

    belongs-to nokia-state { prefix "state"; }

    import ietf-yang-types                { prefix "yang"; }
    import nokia-sros-yang-extensions     { prefix "sros-ext"; }
    import nokia-types-sros               { prefix "types-sros"; }
    import nokia-types-system             { prefix "types-system"; }


    sros-ext:sros-major-release "rel21";

    organization "Nokia";

    contact
        "Nokia SR OS Support
         Web: <http://www.nokia.com>";

    description
        "Nokia YANG Data model with operational state for users lists on SR OS based routers.

         Copyright 2016 Nokia. All rights reserved. Reproduction of this document
         is authorized on the condition that the foregoing copyright notice is included.

         This nokia-state-users YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-08-08";

    grouping state-users {
        container users {
            description "Enter the users context";

            list session {
                key "session-id";
                description "Enter the session list instance";

                leaf session-id {
                    type uint32;
                    description "The unique identifier of session";
                }

                leaf user {
                    type types-sros:named-item;
                    description "Name of the user";
                }

                leaf router-instance {
                    type types-sros:named-item-64-or-empty;
                    description "The value indicates the routing context of a connection";
                }

                leaf connection-ip {
                    type types-sros:ip-address-with-zone;
                    description "Connection ip address";
                }

                leaf connection-type {
                    type types-system:session-type;
                    description "The type of the connection used for the cli session";
                }

                leaf login-time {
                    type yang:date-and-time;
                    description "The time the user logged in and created the session";
                }

                leaf idle-time {
                    type types-sros:time-duration;
                    units "seconds";
                    description "Indicates the session's idle time";
                }

                leaf current-active-session {
                    type boolean;
                    description "Indicates the current active session";
                }

            } // list session

        } // container users

    } // grouping state-users

}
