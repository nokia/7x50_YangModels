module nokia-types-operation {

    yang-version "1.1";

    namespace "urn:nokia.com:sros:ns:yang:sr:types-operation";

    prefix "types-operation";

    import nokia-sros-yang-extensions     { prefix "sros-ext"; }


    sros-ext:sros-major-release "rel21";

    organization "Nokia";

    contact
        "Nokia SR OS Support
         Web: <http://www.nokia.com>";

    description
        "Common operation types data types used in the SR OS management system.

         Copyright 2016 Nokia. All rights reserved. Reproduction of this document
         is authorized on the condition that the foregoing copyright notice is included.

         This nokia-types-operation YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-11-25";

    typedef operation-status {
        type enumeration {
            enum "in-progress"                  { value 0; }
            enum "completed"                    { value 1; }
            enum "terminated-incomplete"        { value 2; }
        }
        description "Describes the status of an operation.";
    }

    typedef operation-message {
        type string {
            length "1..255";
        }
        description "Error/warning/info message reported by operations.";
    }

    typedef operation-timeout {
        type union {
            type uint32 {
                range "1..604800";
            }
            type enumeration {
                enum "never"                        { value 0; }
            }
        }
        units "seconds";
        description "Timeout for operation execution or its data retention.";
    }

}
