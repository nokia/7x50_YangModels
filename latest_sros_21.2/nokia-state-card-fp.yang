submodule nokia-state-card-fp {

    yang-version "1.1";

    belongs-to nokia-state { prefix "state"; }

    import ietf-yang-types                { prefix "yang"; }
    import nokia-sros-yang-extensions     { prefix "sros-ext"; }
    import nokia-types-card               { prefix "types-card"; }
    import nokia-types-qos                { prefix "types-qos"; }
    import nokia-types-sros               { prefix "types-sros"; }

    include nokia-state-qos;

    sros-ext:sros-major-release "rel21";

    organization "Nokia";

    contact
        "Nokia SR OS Support
         Web: <http://www.nokia.com>";

    description
        "Nokia YANG Data model with operational state for card forwarding plane on SR OS based routers.

         Copyright 2016 Nokia. All rights reserved. Reproduction of this document
         is authorized on the condition that the foregoing copyright notice is included.

         This nokia-state-card-fp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-12-15";

    grouping state-card-fp {
        list fp {
            key "fp-number";
            description "Enter the fp list instance";

            leaf fp-number {
                type uint32 {
                    range "1..8";
                }
                description "Forwarding plane within a specific IOM card";
            }

            leaf total-policy-accounting-in-use {
                type uint32;
                description "Indicates the total number of statistics resources currently in use.";
            }

            leaf generation {
                type types-card:fp-generation;
                description "Indicates the generation of the FP network processor.";
            }

            container hi-bw-mcast-src {
                description "Enter the hi-bw-mcast-src context";

                leaf tap-count {
                    type uint32;
                    description
                        "Indicates the number of high bandwidth multicast traffic taps
                         on this forwarding plane.";
                }

            } // container hi-bw-mcast-src

            container ingress {
                description "Enter the ingress context";

                container access {
                    description "Enter the access context";

                    list queue-group {
                        key "queue-group-name instance-id";
                        description "Enter the queue-group list instance";

                        leaf queue-group-name {
                            type leafref {
                                path "../../../../../../qos/queue-group-templates/ingress/queue-group/ingress-queue-group-name";
                            }
                            description "Queue group name";
                        }

                        leaf instance-id {
                            type uint16 {
                                range "1..65535";
                            }
                            description "Instance ID";
                        }

                        container policer-control-policy {
                            description "Enter the policer-control-policy context";

                            list arbiter {
                                key "arbiter-name";
                                description "Enter the arbiter list instance";

                                leaf arbiter-name {
                                    type types-sros:named-item;
                                    description "Arbiter name";
                                }

                                container statistics {
                                    description "Enter the statistics context";

                                    leaf forwarded-packets {
                                        type yang:counter64;
                                        description "The number of forwarded packets.";
                                    }

                                    leaf forwarded-octets {
                                        type yang:counter64;
                                        description "The number of forwarded octets.";
                                    }

                                } // container statistics

                            } // list arbiter

                        } // container policer-control-policy

                        list policer {
                            key "policer-id";
                            description "Enter the policer list instance";

                            leaf policer-id {
                                type types-qos:ingress-policer-id;
                                description "The unique identifier for the policer.";
                            }

                            container statistics {
                                description "Enter the statistics context";

                                choice stat-mode {
                                    case minimal {

                                        container minimal {
                                            description "Enter the minimal context";

                                            leaf all-offered-packets {
                                                type yang:counter64;
                                                description "The number of all the priority packets offered by the packet processor to traffic manager";
                                            }

                                            leaf all-offered-octets {
                                                type yang:counter64;
                                                description "The number of all the priority octets offered by the packet processor to traffic manager";
                                            }

                                            leaf all-dropped-packets {
                                                type yang:counter64;
                                                description "The number of all the priority packets dropped by the packet processor to traffic manager";
                                            }

                                            leaf all-dropped-octets {
                                                type yang:counter64;
                                                description "The number of all the priority octets dropped by the packet processor to traffic manager";
                                            }

                                            leaf all-forwarded-packets {
                                                type yang:counter64;
                                                description "The number of all the priority packets forwarded by the packet processor to traffic manager";
                                            }

                                            leaf all-forwarded-octets {
                                                type yang:counter64;
                                                description "The number of all the priority octets forwarded by the packet processor to traffic manager";
                                            }

                                        } // container minimal

                                    }
                                    case offered-profile-no-cir {

                                        container offered-profile-no-cir {
                                            description "Enter the offered-profile-no-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-profile-no-cir

                                    }
                                    case offered-priority-no-cir {

                                        container offered-priority-no-cir {
                                            description "Enter the offered-priority-no-cir context";

                                            leaf high-priority-offered-packets {
                                                type yang:counter64;
                                                description "The number of high-priority packets offered by the packet processor to traffic manager";
                                            }

                                            leaf high-priority-offered-octets {
                                                type yang:counter64;
                                                description "The number of high-priority octets offered by the packet processor to traffic manager";
                                            }

                                            leaf low-priority-offered-packets {
                                                type yang:counter64;
                                                description "The number of low-priority packets offered by the packet processor to traffic manager";
                                            }

                                            leaf low-priority-offered-octets {
                                                type yang:counter64;
                                                description "The number of low-priority octets offered by the packet processor to traffic manager";
                                            }

                                            leaf high-priority-dropped-packets {
                                                type yang:counter64;
                                                description "The number of high-priority packets dropped by the packet processor to traffic manager";
                                            }

                                            leaf high-priority-dropped-octets {
                                                type yang:counter64;
                                                description "The number of high-priority octets dropped by the packet processor to traffic manager";
                                            }

                                            leaf low-priority-dropped-packets {
                                                type yang:counter64;
                                                description "The number of low-priority packets dropped by the packet processor to traffic manager";
                                            }

                                            leaf low-priority-dropped-octets {
                                                type yang:counter64;
                                                description "The number of low-priority octets dropped by the packet processor to traffic manager";
                                            }

                                            leaf high-priority-forwarded-packets {
                                                type yang:counter64;
                                                description "The number of high-priority packets forwarded by the packet processor to traffic manager";
                                            }

                                            leaf high-priority-forwarded-octets {
                                                type yang:counter64;
                                                description "The number of high-priority octets forwarded by the packet processor to traffic manager";
                                            }

                                            leaf low-priority-forwarded-packets {
                                                type yang:counter64;
                                                description "The number of low-priority packets forwarded by the packet processor to traffic manager";
                                            }

                                            leaf low-priority-forwarded-octets {
                                                type yang:counter64;
                                                description "The number of low-priority octets forwarded by the packet processor to traffic manager";
                                            }

                                        } // container offered-priority-no-cir

                                    }
                                    case offered-profile-cir {

                                        container offered-profile-cir {
                                            description "Enter the offered-profile-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf uncolor-offered-packets {
                                                type yang:counter64;
                                                description "The number of uncolor packets offered by the packet processor to traffic manager";
                                            }

                                            leaf uncolor-offered-octets {
                                                type yang:counter64;
                                                description "The number of uncolor octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-profile-cir

                                    }
                                    case offered-priority-cir {

                                        container offered-priority-cir {
                                            description "Enter the offered-priority-cir context";

                                            leaf high-priority-offered-packets {
                                                type yang:counter64;
                                                description "The number of high-priority packets offered by the packet processor to traffic manager";
                                            }

                                            leaf high-priority-offered-octets {
                                                type yang:counter64;
                                                description "The number of high-priority octets offered by the packet processor to traffic manager";
                                            }

                                            leaf low-priority-offered-packets {
                                                type yang:counter64;
                                                description "The number of low-priority packets offered by the packet processor to traffic manager";
                                            }

                                            leaf low-priority-offered-octets {
                                                type yang:counter64;
                                                description "The number of low-priority octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-priority-cir

                                    }
                                    case offered-total-cir {

                                        container offered-total-cir {
                                            description "Enter the offered-total-cir context";

                                            leaf all-offered-packets {
                                                type yang:counter64;
                                                description "The number of all the priority packets offered by the packet processor to traffic manager";
                                            }

                                            leaf all-offered-octets {
                                                type yang:counter64;
                                                description "The number of all the priority octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-total-cir

                                    }
                                    case offered-limited-profile-cir {

                                        container offered-limited-profile-cir {
                                            description "Enter the offered-limited-profile-cir context";

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf uncolor-offered-packets {
                                                type yang:counter64;
                                                description "The number of uncolor packets offered by the packet processor to traffic manager";
                                            }

                                            leaf uncolor-offered-octets {
                                                type yang:counter64;
                                                description "The number of uncolor octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-limited-profile-cir

                                    }
                                    case offered-profile-capped-cir {

                                        container offered-profile-capped-cir {
                                            description "Enter the offered-profile-capped-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf uncolor-offered-packets {
                                                type yang:counter64;
                                                description "The number of uncolor packets offered by the packet processor to traffic manager";
                                            }

                                            leaf uncolor-offered-octets {
                                                type yang:counter64;
                                                description "The number of uncolor octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-profile-capped-cir

                                    }
                                    case offered-limited-capped-cir {

                                        container offered-limited-capped-cir {
                                            description "Enter the offered-limited-capped-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                            leaf uncolor-offered-packets {
                                                type yang:counter64;
                                                description "The number of out-of-rofile packets offered by the packet processor to traffic manager";
                                            }

                                            leaf uncolor-offered-octets {
                                                type yang:counter64;
                                                description "The number of out-of-profile octets offered by the packet processor to traffic manager";
                                            }

                                        } // container offered-limited-capped-cir

                                    }
                                }
                            } // container statistics

                            list hardware-policer {
                                key "hardware-policer-string";
                                description "Enter the hardware-policer list instance";

                                leaf hardware-policer-string {
                                    type types-sros:named-item-255;
                                    description "Name of the policer formatted by IOM.";
                                }

                                leaf adapted-admin-cbs {
                                    type types-qos:bytes;
                                    units "bytes";
                                    description "Admin CBS.";
                                }

                                leaf adapted-admin-mbs {
                                    type types-qos:bytes;
                                    units "bytes";
                                    description "Admin MBS.";
                                }

                                leaf adapted-hp-only {
                                    type types-qos:bytes;
                                    units "bytes";
                                    description "Hi Prio Only.";
                                }

                                leaf operational-cir {
                                    type types-qos:int-max;
                                    description "Oper CIR.";
                                }

                                leaf operational-fir {
                                    type types-qos:int-max;
                                    description "Oper FIR.";
                                }

                                leaf operational-pir {
                                    type types-qos:int-max;
                                    description "Oper PIR.";
                                }

                            } // list hardware-policer

                        } // list policer

                    } // list queue-group

                } // container access

                container mcast-path-management {
                    description "Enter the mcast-path-management context";

                    leaf primary-in-use-bandwidth {
                        type uint32;
                        units "kilobps";
                        description
                            "Indicates the in use ingress multicast bandwidth for the primary
                             forwarding path.";
                    }

                    leaf secondary-in-use-bandwidth {
                        type uint32;
                        units "kilobps";
                        description
                            "Indicates the in use ingress multicast bandwidth for the secondary
                             forwarding path.";
                    }

                    leaf blackhole-in-use-bandwidth {
                        type uint32;
                        units "kilobps";
                        description
                            "Indicates the bandwidth of the ingress multicast traffic that
                             is being black holed on the forwarding plane.";
                    }

                } // container mcast-path-management

                container network {
                    description "Enter the network context";

                    list queue-group {
                        key "queue-group-name instance-id";
                        description "Enter the queue-group list instance";

                        leaf queue-group-name {
                            type leafref {
                                path "../../../../../../qos/queue-group-templates/ingress/queue-group/ingress-queue-group-name";
                            }
                            description "Queue group name";
                        }

                        leaf instance-id {
                            type uint16 {
                                range "1..65535";
                            }
                            description "Instance ID";
                        }

                        container policer-control-policy {
                            description "Enter the policer-control-policy context";

                            list arbiter {
                                key "arbiter-name";
                                description "Enter the arbiter list instance";

                                leaf arbiter-name {
                                    type types-sros:named-item;
                                    description "Arbiter name";
                                }

                                container statistics {
                                    description "Enter the statistics context";

                                    leaf forwarded-packets {
                                        type yang:counter64;
                                        description "The number of forwarded packets.";
                                    }

                                    leaf forwarded-octets {
                                        type yang:counter64;
                                        description "The number of forwarded octets.";
                                    }

                                } // container statistics

                            } // list arbiter

                        } // container policer-control-policy

                        list policer {
                            key "policer-id";
                            description "Enter the policer list instance";

                            leaf policer-id {
                                type types-qos:ingress-policer-id;
                                description "The unique identifier for the policer.";
                            }

                            container statistics {
                                description "Enter the statistics context";

                                choice stat-mode {
                                    case minimal {

                                        container minimal {
                                            description "Enter the minimal context";

                                            leaf all-offered-packets {
                                                type yang:counter64;
                                                description "The number of all the priority packets offered by the packet processor to traffic manager";
                                            }

                                            leaf all-offered-octets {
                                                type yang:counter64;
                                                description "The number of all the priority octets offered by the packet processor to traffic manager";
                                            }

                                            leaf all-dropped-packets {
                                                type yang:counter64;
                                                description "The number of all the priority packets dropped by the packet processor to traffic manager";
                                            }

                                            leaf all-dropped-octets {
                                                type yang:counter64;
                                                description "The number of all the priority octets dropped by the packet processor to traffic manager";
                                            }

                                            leaf all-forwarded-packets {
                                                type yang:counter64;
                                                description "The number of all the priority packets forwarded by the packet processor to traffic manager";
                                            }

                                            leaf all-forwarded-octets {
                                                type yang:counter64;
                                                description "The number of all the priority octets forwarded by the packet processor to traffic manager";
                                            }

                                        } // container minimal

                                    }
                                    case offered-profile-no-cir {

                                        container offered-profile-no-cir {
                                            description "Enter the offered-profile-no-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-profile-no-cir

                                    }
                                    case offered-priority-no-cir {

                                        container offered-priority-no-cir {
                                            description "Enter the offered-priority-no-cir context";

                                            leaf high-priority-offered-packets {
                                                type yang:counter64;
                                                description "The number of high-priority packets offered by the packet processor to traffic manager";
                                            }

                                            leaf high-priority-offered-octets {
                                                type yang:counter64;
                                                description "The number of high-priority octets offered by the packet processor to traffic manager";
                                            }

                                            leaf low-priority-offered-packets {
                                                type yang:counter64;
                                                description "The number of low-priority packets offered by the packet processor to traffic manager";
                                            }

                                            leaf low-priority-offered-octets {
                                                type yang:counter64;
                                                description "The number of low-priority octets offered by the packet processor to traffic manager";
                                            }

                                            leaf high-priority-dropped-packets {
                                                type yang:counter64;
                                                description "The number of high-priority packets dropped by the packet processor to traffic manager";
                                            }

                                            leaf high-priority-dropped-octets {
                                                type yang:counter64;
                                                description "The number of high-priority octets dropped by the packet processor to traffic manager";
                                            }

                                            leaf low-priority-dropped-packets {
                                                type yang:counter64;
                                                description "The number of low-priority packets dropped by the packet processor to traffic manager";
                                            }

                                            leaf low-priority-dropped-octets {
                                                type yang:counter64;
                                                description "The number of low-priority octets dropped by the packet processor to traffic manager";
                                            }

                                            leaf high-priority-forwarded-packets {
                                                type yang:counter64;
                                                description "The number of high-priority packets forwarded by the packet processor to traffic manager";
                                            }

                                            leaf high-priority-forwarded-octets {
                                                type yang:counter64;
                                                description "The number of high-priority octets forwarded by the packet processor to traffic manager";
                                            }

                                            leaf low-priority-forwarded-packets {
                                                type yang:counter64;
                                                description "The number of low-priority packets forwarded by the packet processor to traffic manager";
                                            }

                                            leaf low-priority-forwarded-octets {
                                                type yang:counter64;
                                                description "The number of low-priority octets forwarded by the packet processor to traffic manager";
                                            }

                                        } // container offered-priority-no-cir

                                    }
                                    case offered-profile-cir {

                                        container offered-profile-cir {
                                            description "Enter the offered-profile-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf uncolor-offered-packets {
                                                type yang:counter64;
                                                description "The number of uncolor packets offered by the packet processor to traffic manager";
                                            }

                                            leaf uncolor-offered-octets {
                                                type yang:counter64;
                                                description "The number of uncolor octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-profile-cir

                                    }
                                    case offered-priority-cir {

                                        container offered-priority-cir {
                                            description "Enter the offered-priority-cir context";

                                            leaf high-priority-offered-packets {
                                                type yang:counter64;
                                                description "The number of high-priority packets offered by the packet processor to traffic manager";
                                            }

                                            leaf high-priority-offered-octets {
                                                type yang:counter64;
                                                description "The number of high-priority octets offered by the packet processor to traffic manager";
                                            }

                                            leaf low-priority-offered-packets {
                                                type yang:counter64;
                                                description "The number of low-priority packets offered by the packet processor to traffic manager";
                                            }

                                            leaf low-priority-offered-octets {
                                                type yang:counter64;
                                                description "The number of low-priority octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-priority-cir

                                    }
                                    case offered-total-cir {

                                        container offered-total-cir {
                                            description "Enter the offered-total-cir context";

                                            leaf all-offered-packets {
                                                type yang:counter64;
                                                description "The number of all the priority packets offered by the packet processor to traffic manager";
                                            }

                                            leaf all-offered-octets {
                                                type yang:counter64;
                                                description "The number of all the priority octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-total-cir

                                    }
                                    case offered-limited-profile-cir {

                                        container offered-limited-profile-cir {
                                            description "Enter the offered-limited-profile-cir context";

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf uncolor-offered-packets {
                                                type yang:counter64;
                                                description "The number of uncolor packets offered by the packet processor to traffic manager";
                                            }

                                            leaf uncolor-offered-octets {
                                                type yang:counter64;
                                                description "The number of uncolor octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-limited-profile-cir

                                    }
                                    case offered-profile-capped-cir {

                                        container offered-profile-capped-cir {
                                            description "Enter the offered-profile-capped-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf uncolor-offered-packets {
                                                type yang:counter64;
                                                description "The number of uncolor packets offered by the packet processor to traffic manager";
                                            }

                                            leaf uncolor-offered-octets {
                                                type yang:counter64;
                                                description "The number of uncolor octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-profile-capped-cir

                                    }
                                    case offered-limited-capped-cir {

                                        container offered-limited-capped-cir {
                                            description "Enter the offered-limited-capped-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                            leaf uncolor-offered-packets {
                                                type yang:counter64;
                                                description "The number of out-of-rofile packets offered by the packet processor to traffic manager";
                                            }

                                            leaf uncolor-offered-octets {
                                                type yang:counter64;
                                                description "The number of out-of-profile octets offered by the packet processor to traffic manager";
                                            }

                                        } // container offered-limited-capped-cir

                                    }
                                }
                            } // container statistics

                            list hardware-policer {
                                key "hardware-policer-string";
                                description "Enter the hardware-policer list instance";

                                leaf hardware-policer-string {
                                    type types-sros:named-item-255;
                                    description "Name of the policer formatted by IOM.";
                                }

                                leaf adapted-admin-cbs {
                                    type types-qos:bytes;
                                    units "bytes";
                                    description "Admin CBS.";
                                }

                                leaf adapted-admin-mbs {
                                    type types-qos:bytes;
                                    units "bytes";
                                    description "Admin MBS.";
                                }

                                leaf adapted-hp-only {
                                    type types-qos:bytes;
                                    units "bytes";
                                    description "Hi Prio Only.";
                                }

                                leaf operational-cir {
                                    type types-qos:int-max;
                                    description "Oper CIR.";
                                }

                                leaf operational-fir {
                                    type types-qos:int-max;
                                    description "Oper FIR.";
                                }

                                leaf operational-pir {
                                    type types-qos:int-max;
                                    description "Oper PIR.";
                                }

                            } // list hardware-policer

                        } // list policer

                    } // list queue-group

                    list pool {
                        key "name";
                        description "Enter the pool list instance";

                        leaf name {
                            type types-sros:named-item;
                            description "Unique pool name for the FP";
                        }

                        container pool-usage {
                            description "Enter the pool-usage context";

                            leaf total-pool-size {
                                type uint32;
                                units "kilobytes";
                                description "Total buffer pools size.";
                            }

                            leaf total-pool-in-use {
                                type uint32;
                                units "kilobytes";
                                description "Total buffer pools size in use.";
                            }

                            leaf shared-pool-size {
                                type uint32;
                                units "kilobytes";
                                description "Total shared pools size.";
                            }

                            leaf shared-pool-in-use {
                                type uint32;
                                units "kilobytes";
                                description "Total shared pools size in use.";
                            }

                            leaf reserved-pool-size {
                                type uint32;
                                units "kilobytes";
                                description "Total reserved pools size.";
                            }

                            leaf reserved-pool-in-use {
                                type uint32;
                                units "kilobytes";
                                description "Total reserved pools size in use.";
                            }

                        } // container pool-usage

                    } // list pool

                } // container network

                container policy-accounting {
                    description "Enter the policy-accounting context";

                    leaf classes-in-use {
                        type uint32;
                        description "Indicates the total number of policy accounting class resources currently in use.";
                    }

                    leaf policers-in-use {
                        type uint32;
                        description "Indicates the total number of policy accounting policer resources currently in use.";
                    }

                } // container policy-accounting

                container dist-cpu-protection {
                    description "Enter the dist-cpu-protection context";

                    container dynamic-policer {
                        description "Enter the dynamic-policer context";

                        leaf in-use {
                            type uint32;
                            description "Number of dynamic-policers in-use";
                        }

                        leaf high-water-mark-hit-count {
                            type uint32;
                            description "High water-mark hit-count";
                        }

                        leaf high-water-mark-hit-time {
                            type yang:date-and-time;
                            description "High water-mark hit-time";
                        }

                        leaf allocation-fail-count {
                            type uint32;
                            description "Count of allocation fails for dynamic-policers";
                        }

                    } // container dynamic-policer

                } // container dist-cpu-protection

            } // container ingress

            container statistics {
                description "Enter the statistics context";

                leaf ingress-fcs-error {
                    type yang:counter32;
                    description
                        "Indicates the number of times the complex experienced a FCS
                         error in the ingress direction since startup, last clear,
                         or card reboot.";
                }

                leaf ingress-fcs-error-time {
                    type yang:date-and-time;
                    description "Indicates the last time ingress-fcs-error incremented.";
                }

                leaf egress-fcs-error {
                    type yang:counter32;
                    description
                        "Indicates the number of times the complex experienced a FCS
                         error in the egress direction since startup, last clear, or
                         card reboot.";
                }

                leaf egress-fcs-error-time {
                    type yang:date-and-time;
                    description "Indicates the last time egress-fcs-error incremented.";
                }

                leaf memory-parity-error {
                    type yang:counter32;
                    description
                        "Indicates the number of times the complex experienced a memory
                         parity error since startup, last clear, or card reboot.";
                }

                leaf memory-parity-error-time {
                    type yang:date-and-time;
                    description "Indicates the last time memory-parity-error incremented.";
                }

                leaf cam-error {
                    type yang:counter32;
                    description
                        "Indicates the number of times the complex experienced a CAM
                         error since startup, last clear, or card reboot.";
                }

                leaf cam-error-time {
                    type yang:date-and-time;
                    description "Indicates the last time cam-error incremented.";
                }

                leaf buffer-memory-error {
                    type yang:counter32;
                    description
                        "Indicates the number of times the complex experienced a buffer
                         memory error since startup, last clear, or card reboot.";
                }

                leaf buffer-memory-error-time {
                    type yang:date-and-time;
                    description "Indicates the last time buffer-memory-error incremented.";
                }

                leaf statistics-memory-error {
                    type yang:counter32;
                    description
                        "Indicates the number of times the complex experienced a
                         statistics memory error since startup, last clear, or card
                         reboot.";
                }

                leaf statistics-memory-error-time {
                    type yang:date-and-time;
                    description "Indicates the last time statistics-memory-error incremented.";
                }

                leaf internal-memory-error {
                    type yang:counter32;
                    description
                        "Indicates the number of times the complex experienced an
                         internal memory error since startup, last clear, or card
                         reboot.";
                }

                leaf internal-memory-error-time {
                    type yang:date-and-time;
                    description "Indicates the last time internal-memory-error incremented.";
                }

                leaf internal-datapath-error {
                    type yang:counter32;
                    description
                        "Indicates the number of times the complex experienced an
                         internal datapath error since startup, last clear, or card
                         reboot.";
                }

                leaf internal-datapath-error-time {
                    type yang:date-and-time;
                    description "Indicates the last time internal-datapath-error incremented.";
                }

                leaf internal-datapath-cell-error {
                    type yang:counter32;
                    description
                        "Indicates the number of times the complex experienced an
                         internal datapath cell error since startup, last clear, or
                         card reboot.";
                }

                leaf internal-datapath-cell-error-time {
                    type yang:date-and-time;
                    description
                        "Indicates the last time internal-datapath-cell-error
                         incremented.";
                }

                leaf source-slots-egress-fcs-error {
                    type types-card:card-slot-bitmap;
                    description
                        "Indicates the source slots reported from the last time
                         egress-fcs-error incremented.";
                }

                leaf egress-encap-exceeded {
                    type yang:counter64;
                    units "packets";
                    description
                        "Addition of egress encapsulation headers would have exceeded
                         the maximum frame size.";
                }

                leaf egress-mtu-exceeded {
                    type yang:counter64;
                    units "packets";
                    description
                        "Protocol supports packet fragmentation but fragmentation was
                         blocked (for example packet is IPv6 or packet is IPv4 and DF
                         set to one).";
                }

                leaf egress-frame-too-big-for-port {
                    type yang:counter64;
                    units "packets";
                    description
                        "Final check before transmitting has detected frame exceeded
                         the port MTU.";
                }

            } // container statistics

            container resource-usage {
                description "Enter the resource-usage context";

                container sap-ingress-qos-policies {
                    description "Enter the sap-ingress-qos-policies context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container sap-ingress-qos-policies

                container dynamic-egress-classification {
                    description "Enter the dynamic-egress-classification context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                    container in-use-by-sap-egress {
                        description "Enter the in-use-by-sap-egress context";

                        leaf allocated {
                            type yang:counter32;
                            description "The total number of resources that are currently allocated on this FP.";
                        }

                    } // container in-use-by-sap-egress

                    container in-use-by-network-egress {
                        description "Enter the in-use-by-network-egress context";

                        leaf allocated {
                            type yang:counter32;
                            description "The total number of resources that are currently allocated on this FP.";
                        }

                    } // container in-use-by-network-egress

                } // container dynamic-egress-classification

                container ingress-queues {
                    description "Enter the ingress-queues context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container ingress-queues

                container egress-queues {
                    description "Enter the egress-queues context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-queues

                container ingress-policers {
                    description "Enter the ingress-policers context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container ingress-policers

                container ingress-policer-stat-entries {
                    description "Enter the ingress-policer-stat-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container ingress-policer-stat-entries

                container egress-policers {
                    description "Enter the egress-policers context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-policers

                container egress-policer-stat-entries {
                    description "Enter the egress-policer-stat-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-policer-stat-entries

                container qos-ingress-root-arbiters {
                    description "Enter the qos-ingress-root-arbiters context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container qos-ingress-root-arbiters

                container qos-egress-root-arbiters {
                    description "Enter the qos-egress-root-arbiters context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container qos-egress-root-arbiters

                container egress-qos-bypass {
                    description "Enter the egress-qos-bypass context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-qos-bypass

                container dynamic-queues {
                    description "Enter the dynamic-queues context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                    container in-use-by-ingress {
                        description "Enter the in-use-by-ingress context";

                        leaf allocated {
                            type yang:counter32;
                            description "The total number of resources that are currently allocated on this FP.";
                        }

                    } // container in-use-by-ingress

                    container in-use-by-egress {
                        description "Enter the in-use-by-egress context";

                        leaf allocated {
                            type yang:counter32;
                            description "The total number of resources that are currently allocated on this FP.";
                        }

                    } // container in-use-by-egress

                } // container dynamic-queues

                container dynamic-policers {
                    description "Enter the dynamic-policers context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                    container in-use-by-ingress {
                        description "Enter the in-use-by-ingress context";

                        leaf allocated {
                            type yang:counter32;
                            description "The total number of resources that are currently allocated on this FP.";
                        }

                    } // container in-use-by-ingress

                    container in-use-by-egress {
                        description "Enter the in-use-by-egress context";

                        leaf allocated {
                            type yang:counter32;
                            description "The total number of resources that are currently allocated on this FP.";
                        }

                    } // container in-use-by-egress

                } // container dynamic-policers

                container dynamic-policer-stat-entries {
                    description "Enter the dynamic-policer-stat-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                    container in-use-by-ingress {
                        description "Enter the in-use-by-ingress context";

                        leaf allocated {
                            type yang:counter32;
                            description "The total number of resources that are currently allocated on this FP.";
                        }

                    } // container in-use-by-ingress

                    container in-use-by-egress {
                        description "Enter the in-use-by-egress context";

                        leaf allocated {
                            type yang:counter32;
                            description "The total number of resources that are currently allocated on this FP.";
                        }

                    } // container in-use-by-egress

                } // container dynamic-policer-stat-entries

                container egress-user-queues {
                    description "Enter the egress-user-queues context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-user-queues

                container egress-user-policers {
                    description "Enter the egress-user-policers context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-user-policers

                container ingress-ip-acl-qos-entries {
                    description "Enter the ingress-ip-acl-qos-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container ingress-ip-acl-qos-entries

                container ingress-ip-filter-entries {
                    description "Enter the ingress-ip-filter-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container ingress-ip-filter-entries

                container ingress-ip-qos-entries {
                    description "Enter the ingress-ip-qos-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container ingress-ip-qos-entries

                container ingress-ipv6-filter-entries {
                    description "Enter the ingress-ipv6-filter-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container ingress-ipv6-filter-entries

                container ingress-ipv6-qos-entries {
                    description "Enter the ingress-ipv6-qos-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container ingress-ipv6-qos-entries

                container egress-ip-acl-qos-entries {
                    description "Enter the egress-ip-acl-qos-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-ip-acl-qos-entries

                container egress-ip-filter-entries {
                    description "Enter the egress-ip-filter-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-ip-filter-entries

                container egress-ip-qos-entries {
                    description "Enter the egress-ip-qos-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-ip-qos-entries

                container egress-ipv6-filter-entries {
                    description "Enter the egress-ipv6-filter-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-ipv6-filter-entries

                container egress-ipv6-qos-entries {
                    description "Enter the egress-ipv6-qos-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-ipv6-qos-entries

                container ingress-ip-filter-policies {
                    description "Enter the ingress-ip-filter-policies context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container ingress-ip-filter-policies

                container ingress-ipv6-filter-policies {
                    description "Enter the ingress-ipv6-filter-policies context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container ingress-ipv6-filter-policies

                container egress-ip-filter-policies {
                    description "Enter the egress-ip-filter-policies context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-ip-filter-policies

                container egress-ipv6-filter-policies {
                    description "Enter the egress-ipv6-filter-policies context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-ipv6-filter-policies

                container sap-ingqgrp-redirlst-entries {
                    description "Enter the sap-ingqgrp-redirlst-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container sap-ingqgrp-redirlst-entries

                container dynamic-service-entries {
                    description "Enter the dynamic-service-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                    container encap-group-members {
                        description "Enter the encap-group-members context";

                        leaf total {
                            type yang:counter32;
                            description "The total number of resources supported on this FP.";
                        }

                        leaf allocated {
                            type yang:counter32;
                            description "The total number of resources that are currently allocated on this FP.";
                        }

                        leaf free {
                            type yang:counter32;
                            description "The total number of resources that are remaining free on this FP.";
                        }

                    } // container encap-group-members

                    container egress-network-queue-group-mappings {
                        description "Enter the egress-network-queue-group-mappings context";

                        leaf total {
                            type yang:counter32;
                            description "The total number of resources supported on this FP.";
                        }

                        leaf allocated {
                            type yang:counter32;
                            description "The total number of resources that are currently allocated on this FP.";
                        }

                        leaf free {
                            type yang:counter32;
                            description "The total number of resources that are remaining free on this FP.";
                        }

                    } // container egress-network-queue-group-mappings

                    container sapinst-egrqgrp-redirlst-entries {
                        description "Enter the sapinst-egrqgrp-redirlst-entries context";

                        leaf total {
                            type yang:counter32;
                            description "The total number of resources supported on this FP.";
                        }

                        leaf allocated {
                            type yang:counter32;
                            description "The total number of resources that are currently allocated on this FP.";
                        }

                        leaf free {
                            type yang:counter32;
                            description "The total number of resources that are remaining free on this FP.";
                        }

                    } // container sapinst-egrqgrp-redirlst-entries

                } // container dynamic-service-entries

                container dynamic-wred-pools {
                    description "Enter the dynamic-wred-pools context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container dynamic-wred-pools

                container egress-hs-turbo-queue-group {
                    description "Enter the egress-hs-turbo-queue-group context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-hs-turbo-queue-group

                container egress-hs-queue-group {
                    description "Enter the egress-hs-queue-group context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-hs-queue-group

                container hs-primary-shapers {
                    description "Enter the hs-primary-shapers context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                    container hs-explicit-primary-shapers {
                        description "Enter the hs-explicit-primary-shapers context";

                        leaf allocated {
                            type yang:counter32;
                            description "The total number of resources that are currently allocated on this FP";
                        }

                    } // container hs-explicit-primary-shapers

                    container hs-managed-primary-shapers {
                        description "Enter the hs-managed-primary-shapers context";

                        leaf allocated {
                            type yang:counter32;
                            description "The total number of resources that are currently allocated on this FP";
                        }

                    } // container hs-managed-primary-shapers

                } // container hs-primary-shapers

                container hs-secondary-shapers {
                    description "Enter the hs-secondary-shapers context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container hs-secondary-shapers

                container fast-depth-monitored-queues {
                    description "Enter the fast-depth-monitored-queues context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container fast-depth-monitored-queues

            } // container resource-usage

            list tap {
                key "tap-number";
                description "Enter the tap list instance";

                leaf tap-number {
                    type uint32 {
                        range "1..4";
                    }
                    description
                        "The unique value which uniquely identifies the tap number of the tap corresponding
                         to the forwarding plane within a specific IOM card in the system.";
                }

                container ingress {
                    description "Enter the ingress context";

                    list per-egress-dst {
                        key "dst-card-number dst-fp-number dst-tap-number";
                        description "Enter the per-egress-dst list instance";

                        leaf dst-card-number {
                            type types-card:iom-card-slot;
                            description "The unique value which identifies this destination IOM slot within a chassis in the system.";
                        }

                        leaf dst-fp-number {
                            type uint32 {
                                range "1..8";
                            }
                            description
                                "The unique value which uniquely identifies the destination forwarding plane within
                                 a specific IOM card in the system.";
                        }

                        leaf dst-tap-number {
                            type uint32 {
                                range "1..4";
                            }
                            description
                                "The unique value which uniquely identifies the destination number of the tap corresponding
                                 to the forwarding plane within a specific IOM card in the system.";
                        }

                        container statistics {
                            description "Enter the statistics context";

                            leaf expedite-forwarded-packets {
                                type yang:counter64;
                                description "The number of expedited forwarded packets.";
                            }

                            leaf expedite-forwarded-octets {
                                type yang:counter64;
                                description "The number of expedited forwarded octets.";
                            }

                            leaf best-effort-forwarded-packets {
                                type yang:counter64;
                                description "The number of best effort forwarded packets.";
                            }

                            leaf best-effort-forwarded-octets {
                                type yang:counter64;
                                description "The number of best effort forwarded octets.";
                            }

                        } // container statistics

                    } // list per-egress-dst

                } // container ingress

            } // list tap

        } // list fp

    } // grouping state-card-fp

}
