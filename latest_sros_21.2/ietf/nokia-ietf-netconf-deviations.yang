module nokia-ietf-netconf-deviations {
    yang-version "1.1";

    namespace "urn:nokia.com:sros:ns:yang:sr:ietf-netconf-deviations";
    prefix ietf-netconf-deviations;

    import ietf-netconf {
        prefix nc;
        revision-date 2011-06-01;
    }

    import ietf-netconf-nmda {
        prefix ncds;
        revision-date 2019-01-07;
    }

    organization "Nokia";

    contact
        "Nokia SR OS Support
         Web: <http://www.nokia.com>";

    description
        "YANG Data model for Nokia NETCONF deviations.

        Copyright 2019 Nokia. All rights reserved.
        Reproduction of this document is authorized on the condition
        that the foregoing copyright notice is included.

        This nokia-ietf-netconf-deviations YANG module embodies Nokia's
        proprietary intellectual property.  Nokia retains all title
        and ownership in the Specification, including any revisions.

        Nokia grants all interested parties a non-exclusive license
        to use and distribute an unmodified copy of this Specification
        in connection with management of Nokia products, and without
        fee, provided this copyright notice and license appear on all
        copies.

        This Specification is supplied `as is', and Nokia makes no
        warranty, either express or implied, as to the use, operation,
        condition, or performance of the Specification.";

    revision 2019-01-01;

    //Deviations

    deviation /nc:get-config/nc:input/nc:source/nc:config-source/nc:startup {
        description
            "get-config operation from startup datastore is not supported.";
        deviate not-supported;
    }

    deviation /nc:edit-config/nc:input/nc:edit-content/nc:url {
        description
            "URL-based config content option for edit-config operation is not supported.";
        deviate not-supported;
    }

    deviation /nc:copy-config/nc:input/nc:target/nc:config-target/nc:running {
        description
            "copy-config operation to running datastore is not supported.";
        deviate not-supported;
    }

    deviation /nc:validate/nc:input/nc:source/nc:config-source/nc:startup {
        description
            "validate operation for startup datastore is not supported.";
        deviate not-supported;
    }

    deviation /nc:validate/nc:input/nc:source/nc:config-source/nc:url {
        description
            "validate operation for URL-based config content is not supported.";
        deviate not-supported;
    }

    deviation /ncds:get-data/ncds:input/ncds:filter-spec/ncds:xpath-filter {
        description
            "xpath based filtering for get-data operation is not supported.";
        deviate not-supported;
    }

    deviation /ncds:get-data/ncds:input/ncds:config-filter {
        description
            "config-filter option for get-data operation is not supported.";
        deviate not-supported;
    }

    deviation /ncds:get-data/ncds:input/ncds:origin-filters {
        description
            "origin-filters options for get-data operation are not supported.";
        deviate not-supported;
    }

    deviation /ncds:get-data/ncds:input/ncds:with-origin {
        description
            "with-origin option for get-data operation is not supported.";
        deviate not-supported;
    }

    deviation /ncds:edit-data {
        description
            "edit-data operation is not supported.";
        deviate not-supported;
    }

    deviation /nc:lock/nc:input/nc:target/nc:config-target/ncds:datastore {
        description
            "datastore option for lock operation is not supported.";
        deviate not-supported;
    }

    deviation /nc:unlock/nc:input/nc:target/nc:config-target/ncds:datastore {
        description
            "datastore option for unlock operation is not supported.";
        deviate not-supported;
    }

    deviation /nc:validate/nc:input/nc:source/nc:config-source/ncds:datastore {
        description
            "datastore option for validate operation is not supported.";
        deviate not-supported;
    }
}
