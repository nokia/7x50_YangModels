module nokia-types-mpls {

    yang-version "1.1";

    namespace "urn:nokia.com:sros:ns:yang:sr:types-mpls";

    prefix "types-mpls";

    import nokia-sros-yang-extensions     { prefix "sros-ext"; }
    import nokia-types-sros               { prefix "types-sros"; }


    sros-ext:sros-major-release "rel21";

    organization "Nokia";

    contact
        "Nokia SR OS Support
         Web: <http://www.nokia.com>";

    description
        "Common mpls data types used in the SR OS management system.

         Copyright 2016 Nokia. All rights reserved. Reproduction of this document
         is authorized on the condition that the foregoing copyright notice is included.

         This nokia-types-mpls YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-01-21";

    typedef last-adjustment-cause {
        type enumeration {
            enum "none"                         { value 0; }
            enum "manual"                       { value 1; }
            enum "normal"                       { value 2; }
            enum "overflow"                     { value 3; }
            enum "vll-cac"                      { value 4; }
            enum "underflow"                    { value 5; }
            enum "active-path-change"           { value 6; }
        }
        description "Specifies cause of auto-bandwidth last adjustment.";
    }

    typedef lsp-fail-code {
        type enumeration {
            enum "no-error"                     { value 0; }
            enum "admission-control-error"      { value 1; }
            enum "no-route-to-destination"      { value 2; }
            enum "traffic-control-system-error" { value 3; }
            enum "routing-error"                { value 4; }
            enum "no-resources-available"       { value 5; }
            enum "bad-node"                     { value 6; }
            enum "routing-loop"                 { value 7; }
            enum "label-allocation-error"       { value 8; }
            enum "bad-l3-pid"                   { value 9; }
            enum "tunnel-locally-repaired"      { value 10; }
            enum "unknown-object-class"         { value 11; }
            enum "unknown-ct-ype"               { value 12; }
            enum "no-egress-mpls-interface"     { value 13; }
            enum "no-egress-rsvp-interface"     { value 14; }
            enum "loose-hops-in-frr-lsp"        { value 15; }
            enum "unknown"                      { value 16; }
            enum "retry-exceeded"               { value 17; }
            enum "no-cspf-route-owner"          { value 18; }
            enum "no-cspf-route-to-destination" { value 19; }
            enum "hop-limit-exceeded"           { value 20; }
            enum "loose-hops-in-manual-bypass-lsp" { value 21; }
            enum "empty-path-in-manual-bypass-lsp" { value 22; }
            enum "lsp-flow-controlled"          { value 23; }
            enum "srlg-secondary-not-disjoint"  { value 24; }
            enum "srlg-primary-cspf-disabled"   { value 25; }
            enum "srlg-primary-path-down"       { value 26; }
            enum "local-link-maintenance"       { value 27; }
            enum "unexpected-ct-object"         { value 28; }
            enum "unsupported-ct"               { value 29; }
            enum "invalid-ct"                   { value 30; }
            enum "inv-ct-and-setup-priority"    { value 31; }
            enum "inv-ct-and-hold-priority"     { value 32; }
            enum "inv-ct-and-setup-and-hold-priority" { value 33; }
            enum "local-node-maintenance"       { value 34; }
            enum "soft-preemption"              { value 35; }
            enum "p2mp-not-supported"           { value 36; }
            enum "bad-xro"                      { value 37; }
            enum "local-node-in-xro"            { value 38; }
            enum "route-blocked-by-xro"         { value 39; }
            enum "xro-too-complex"              { value 40; }
            enum "rsvp-not-supported"           { value 41; }
            enum "conflicting-admin-groups"     { value 42; }
            enum "node-in-igp-overload"         { value 43; }
            enum "sr-tunnel-down"               { value 44; }
            enum "fib-add-failed"               { value 45; }
            enum "label-stack-exceeded"         { value 46; }
            enum "pcc-down"                     { value 47; }
            enum "pcc-error"                    { value 48; }
            enum "pce-down"                     { value 49; }
            enum "pce-error"                    { value 50; }
            enum "pce-update-with-empty-ero"    { value 51; }
            enum "pce-init-lsp-disabled"        { value 52; }
            enum "admin-down"                   { value 53; }
            enum "sid-hops-in-rsvp-lsp"         { value 54; }
            enum "ipv6-hops-in-rsvp-lsp"        { value 55; }
            enum "ipv4-hops-in-ipv6-lsp"        { value 56; }
            enum "ipv6-hops-in-ipv4-lsp"        { value 57; }
            enum "sid-hops-in-ipv6-lsp"         { value 58; }
            enum "srlg-path-with-sid-hops"      { value 59; }
            enum "mpls-v4-down"                 { value 60; }
            enum "mpls-v6-down"                 { value 61; }
            enum "lsp-admin-down"               { value 62; }
            enum "path-admin-down"              { value 63; }
            enum "template-admin-down"          { value 64; }
        }
        description "Defines the reason for LSP Path and LSP Crossconnect failure.";
    }

    typedef class-type {
        type int32 {
            range "0..7";
        }
        description "Specifies the class type.";
    }

    typedef priority {
        type int32 {
            range "0..7";
        }
        description "Specifies the priority.";
    }

    typedef success-fail {
        type enumeration {
            enum "none"                         { value 1; }
            enum "success"                      { value 2; }
            enum "fail"                         { value 3; }
        }
        description "Specifies the success or fail result type of a specific action.";
    }

    typedef mbb-type {
        type enumeration {
            enum "none"                         { value 0; }
            enum "config-change"                { value 1; }
            enum "timer-based-resignal"         { value 2; }
            enum "manual-resignal"              { value 3; }
            enum "global-revert"                { value 4; }
            enum "delayed-retry"                { value 5; }
            enum "graceful-shutdown"            { value 6; }
            enum "soft-preemption"              { value 7; }
            enum "path-change"                  { value 8; }
            enum "auto-bandwidth"               { value 9; }
            enum "pce-lsp-update"               { value 10; }
        }
        description "Specifies the type of make-before-break (MBB).";
    }

    typedef oper-down-reason-type {
        type enumeration {
            enum "not-applicable"               { value 0; }
            enum "admin-down"                   { value 1; }
            enum "no-resources"                 { value 2; }
            enum "system-ip-down"               { value 3; }
            enum "iom-failure"                  { value 4; }
            enum "clear-down"                   { value 5; }
            enum "ipv6-te-rtr-down"             { value 6; }
            enum "ipv6-te-rtr-addr-changed"     { value 7; }
            enum "ipv6-te-rtr-id-intf-down"     { value 8; }
        }
        description "Specifies the type of oper-down-reason code.";
    }

    typedef lsp-address-type {
        type enumeration {
            enum "ipv4"                         { value 1; }
            enum "node-id"                      { value 2; }
        }
        description "Specifies the type of lsp destination/source adress type.";
    }

    typedef frr-method-type {
        type enumeration {
            enum "one-to-one"                   { value 1; }
            enum "facility"                     { value 2; }
        }
        description "Specifies the type for fast-reroute method.";
    }

    typedef address-family-numbers {
        type enumeration {
            enum "other"                        { value 0; }
            enum "ipv4"                         { value 1; }
            enum "ipv6"                         { value 2; }
            enum "nsap"                         { value 3; }
            enum "hdlc"                         { value 4; }
            enum "bbn1822"                      { value 5; }
            enum "all802"                       { value 6; }
            enum "e163"                         { value 7; }
            enum "e164"                         { value 8; }
            enum "f69"                          { value 9; }
            enum "x121"                         { value 10; }
            enum "ipx"                          { value 11; }
            enum "apple-talk"                   { value 12; }
            enum "decnet-iv"                    { value 13; }
            enum "banyan-vines"                 { value 14; }
            enum "e164-with-nsap"               { value 15; }
            enum "dns"                          { value 16; }
            enum "distinguished-name"           { value 17; }
            enum "as-number"                    { value 18; }
            enum "xtp-over-ipv4"                { value 19; }
            enum "xtp-over-ipv6"                { value 20; }
            enum "xtp-native-mode-xtp"          { value 21; }
            enum "fibre-channel-wwpn"           { value 22; }
            enum "fibre-channel-wwnn"           { value 23; }
            enum "gwid"                         { value 24; }
            enum "reserved"                     { value 65535; }
        }
        description
            "The definition of this textual convention with the
             addition of newly assigned values is published
             periodically by the IANA, in either the Assigned
             Numbers RFC, or some derivative of it specific to
             Internet Network Management number assignments.
             (The latest arrangements can be obtained by
             contacting the IANA.)

             The enumerations are described as:

             other(0),    -- none of the following
             ipv4(1),     -- IP Version 4
             ipv6(2),     -- IP Version 6
             nsap(3),     -- NSAP
             hdlc(4),     -- (8-bit multidrop)
             bbn1822(5),
             all802(6),   -- (includes all 802 media
                          --   plus Ethernet 'canonical format')
             e163(7),
             e164(8),     -- (SMDS, Frame Relay, ATM)
             f69(9),      -- (Telex)
             x121(10),    -- (X.25, Frame Relay)
             ipx(11),     -- IPX (Internet Protocol Exchange)
             apple-talk(12),  -- Apple Talk
             decnet-iv(13),   -- DEC Net Phase IV
             banyan-vines(14),  -- Banyan Vines
             e164-with-nsap(15),
                          -- (E.164 with NSAP format subaddress)
             dns(16),     -- (Domain Name System)
             distinguished-name(17), -- (Distinguished Name, per X.500)
             as-number(18), -- (16-bit quantity, per the AS number space)
             xtp-over-ipv4(19),  -- XTP over IP version 4
             xtp-over-ipv6(20),  -- XTP over IP version 6
             xtp-native-mode-xtp(21),  -- XTP native mode XTP
             fibre-channel-wwpn(22),  -- Fibre Channel World-Wide Port Name
             fibre-channel-wwnn(23),  -- Fibre Channel World-Wide Node Name
             gwid(24),    -- Gateway Identifier
             reserved(65535)";
    }

    typedef mpls-tp-node-id {
        type types-sros:ipv4-address;
        description "MPLS Transport Profile node identifier.";
    }

    typedef lsp-fc-bits {
        type bits {
            bit be                             { position 0; }
            bit l2                             { position 1; }
            bit af                             { position 2; }
            bit l1                             { position 3; }
            bit h2                             { position 4; }
            bit ef                             { position 5; }
            bit h1                             { position 6; }
            bit nc                             { position 7; }
            bit default-lsp                    { position 8; }
        }
        description "Lsp forwarding classes.";
    }

    typedef lsp-name {
        type types-sros:named-item-64;
        description "Lsp name.";
    }

    typedef ilm-owner-type {
        type enumeration {
            enum "rib-api"                      { value 1; }
            enum "fwd-plcy"                     { value 2; }
            enum "sr-plcy"                      { value 3; }
        }
        description "Specifies the owner of ilm entry.";
    }

    typedef retry-limit {
        type union {
            type int32 {
                range "1..10000";
            }
            type enumeration {
                enum "infinite"                     { value 0; }
            }
        }
        description
            "Specify the max number of retry attempts that will be made
             to signal the secondary path with the last adjusted bandwidth.
             A value of zero(0) specifies that the retry limit is infinite.";
    }

    typedef lsp-bandwidth {
        type uint32 {
            range "0..6400000";
        }
        units "megabps";
        description "Specifies the maximum LSP Bandwidth.";
    }

    typedef mpls-transport-type {
        type enumeration {
            enum "invalid"                      { value 0; }
            enum "local"                        { value 1; }
            enum "static"                       { value 2; }
            enum "rsvp"                         { value 3; }
            enum "ldp"                          { value 4; }
            enum "ospf"                         { value 5; }
            enum "isis"                         { value 6; }
            enum "bgp"                          { value 7; }
            enum "sr-te"                        { value 8; }
            enum "udp"                          { value 9; }
            enum "sr-policy"                    { value 10; }
            enum "mpls-fwd-policy"              { value 11; }
            enum "rib-api"                      { value 12; }
            enum "sr-ospf3"                     { value 13; }
        }
        description "Specifies the transport entity.";
    }

}
