submodule nokia-state-pw-port {

    yang-version "1.1";

    belongs-to nokia-state { prefix "state"; }

    import ietf-yang-types                { prefix "yang"; }
    import nokia-sros-yang-extensions     { prefix "sros-ext"; }
    import nokia-types-sros               { prefix "types-sros"; }
    import nokia-types-subscriber-mgmt    { prefix "types-submgt"; }


    sros-ext:sros-major-release "rel21";

    organization "Nokia";

    contact
        "Nokia SR OS Support
         Web: <http://www.nokia.com>";

    description
        "Nokia YANG Data model with operational state for pseudo-wire-ports on SR OS based routers.

         Copyright 2016 Nokia. All rights reserved. Reproduction of this document
         is authorized on the condition that the foregoing copyright notice is included.

         This nokia-state-pw-port YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-11-30";

    grouping state-pw-port {
        list pw-port {
            key "pw-port-id";
            description "Enter the pw-port list instance";

            leaf pw-port-id {
                type types-sros:pw-port;
                description "The identifier which uniquely identifies the pw-port.";
            }

            container subscriber-management {
                description "Enter the subscriber-management context";

                container statistics {
                    description "Enter the statistics context";

                    leaf last-reset-peak-values {
                        type yang:date-and-time;
                        description "Timestamp of the last reset of the peak values";
                    }

                    list ipv4-hosts {
                        key "counter";
                        description "Enter the ipv4-hosts list instance";

                        leaf counter {
                            type types-submgt:submgt-statistics-ipv4-type;
                            description "Type of submgt ipv4 hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list ipv4-hosts

                    list ipv6-hosts {
                        key "counter";
                        description "Enter the ipv6-hosts list instance";

                        leaf counter {
                            type types-submgt:submgt-statistics-ipv6-type;
                            description "Type of submgt ipv6 hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list ipv6-hosts

                    list total-hosts {
                        key "counter";
                        description "Enter the total-hosts list instance";

                        leaf counter {
                            type types-submgt:submgt-statistics-total-type;
                            description "Type of submgt total hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list total-hosts

                    list sessions {
                        key "counter";
                        description "Enter the sessions list instance";

                        leaf counter {
                            type types-submgt:submgt-statistics-session-type;
                            description "Type of submgt sessions counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list sessions

                } // container statistics

                list svlan {
                    key "vlan-id";
                    description "Enter the svlan list instance";

                    leaf vlan-id {
                        type uint32 {
                            range "0..4094";
                        }
                        description "The VLAN identifier.";
                    }

                    leaf active-subscriber-hosts {
                        type yang:counter32;
                        description "The number of active subscriber hosts on this port and VLAN.";
                    }

                    container statistics {
                        description "Enter the statistics context";

                        leaf last-cleared-time {
                            type yang:date-and-time;
                            description "The time when the counters were last cleared.";
                        }

                        leaf ingress-packets {
                            type yang:counter64;
                            description "The number of IP packets received through this port and VLAN.";
                        }

                        leaf ingress-octets {
                            type yang:counter64;
                            description "The number of octets in IP packets received through this port and VLAN.";
                        }

                        leaf egress-packets {
                            type yang:counter64;
                            description "The number of IP packets sent through this port and VLAN.";
                        }

                        leaf egress-octets {
                            type yang:counter64;
                            description "The number of octets in IP packets sent through this port and VLAN.";
                        }

                    } // container statistics

                } // list svlan

            } // container subscriber-management

        } // list pw-port

    } // grouping state-pw-port

}
