submodule nokia-conf-svc-sdp {

    yang-version "1.1";

    belongs-to nokia-conf { prefix "conf"; }

    import nokia-sros-yang-extensions     { prefix "sros-ext"; }
    import nokia-types-services           { prefix "types-services"; }
    import nokia-types-sros               { prefix "types-sros"; }

    include nokia-conf-groups;
    include nokia-conf-log;
    include nokia-conf-router;
    include nokia-conf-service;

    sros-ext:sros-major-release "rel21";

    organization "Nokia";

    contact
        "Nokia SR OS Support
         Web: <http://www.nokia.com>";

    description
        "Nokia YANG Data model to configure services on SR OS based routers.

         Copyright 2016 Nokia. All rights reserved. Reproduction of this document
         is authorized on the condition that the foregoing copyright notice is included.

         This nokia-conf-svc-sdp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-01-07";

    grouping conf-svc-sdp {
        list sdp {
            key "sdp-id";
            description "Enter the sdp list instance";

            leaf sdp-id {
                type types-services:sdp-id;
                description "Service Distribution Point (SDP) identifier";
            }

            leaf description {
                type types-sros:description;
                description "Text description";
            }

            leaf admin-state {
                type types-sros:admin-state;
                default "disable";
                description "Administrative state of SDP";
            }

            leaf delivery-type {
                type types-services:sdp-delivery-type;
                sros-ext:immutable;
                description "Specifies the type of delivery used by this SDP";
            }

            leaf accounting-policy {
                type leafref {
                    path "../../../log/accounting-policy/policy-id";
                }
                description "Policy to use to collect accounting statistics on this SDP. The value zero indicates that default accounting policy to be used, if one exists.";
            }

            leaf adv-mtu-override {
                type boolean;
                default "false";
                description "Whether the advertised MTU of a VLL spoke SDP bind should include the 14-byte L2 header, so that it is backward compatible with pre-2.0 software.";
            }

            leaf booking-factor {
                type uint32 {
                    range "0..1000";
                }
                default "100";
                description "Percentage of the SDP max available bandwidth for VLL call admission. When the value is zero (0), no new VLL spoke-sdp bindings with non-zero bandwidth are permitted with this SDP. It is used to calculate the max SDP available bandwidth. Overbooking, >100% is allowed.";
            }

            leaf collect-stats {
                type boolean;
                default "false";
                description "Collect accounting statistics for this SDP";
            }

            leaf local-end {
                type types-sros:ip-address;
                sros-ext:auto-restart-to-modify;
                description "IP address of the local end of the tunnel defined by this SDP.";
            }

            leaf metric {
                type uint32 {
                    range "1..65535";
                }
                description "Metric to be used within the Tunnel Table Manager for decision making purposes. When multiple SDPs going to the same destination exist, this value is used as a tie-breaker by Tunnel Table Manager users like MP-BGP to select route with lower value.";
            }

            leaf network-domain {
                type leafref {
                    path "../../../router/network-domains/network-domain/domain-name";
                }
                description "Network-domain name this SDP is associated with. The network-domain defines the list of network interfaces this SDP can send traffic on.";
            }

            leaf path-mtu {
                type int32 {
                    range "576..9782";
                }
                units "bytes";
                description "Desired largest service frame size (in octets) that can be transmitted through this SDP to the far-end ESR, without requiring the packet to be fragmented. The default value of zero indicates that the path MTU should be computed dynamically from the corresponding MTU of the tunnel.";
            }

            leaf pbb-etype {
                type types-services:etype-value;
                default "0x88E7";
                description "Ethertype used in frames sent out on this SDP when VC type is 'vlan' for Provider Backbone Bridging frames as 0xXXYY with range 0x0600-0xFFFF.";
            }

            leaf signaling {
                type enumeration {
                    enum "off"                          { value 1; }
                    enum "tldp"                         { value 2; }
                    enum "bgp"                          { value 3; }
                }
                sros-ext:auto-restart-to-modify;
                description "Signaling protocol used to obtain the ingress and egress labels used in frames transmitted and received on this SDP. When the value is 'off' then the labels are manually assigned at the time the SDP is bound to a service. Default value of this object is set to 'off' when SDP delivery-type is set to 'l2tpv3' otherwise default value is set to 'tldp'.";
            }

            leaf tunnel-far-end {
                type types-sros:ip-address;
                sros-ext:auto-restart-to-modify;
                description "IP address of the remote of the tunnel defined by this SDP.";
            }

            leaf vlan-vc-etype {
                type types-services:etype-value;
                default "0x8100";
                description "Ethertype used in frames sent out this SDP, when the VC type is 'vlan' as 0xXXYY with range 0x0600-0xFFFF.";
            }

            leaf allow-fragmentation {
                type boolean;
                default "false";
                description "Whether to allow gre or gre-eth-bridged encapsulated packets to be sent without setting the DF bit.";
            }

            leaf ldp {
                type boolean;
                sros-ext:auto-restart-to-modify;
                default "false";
                description "Enable LDP-signaled LSPs";
            }

            leaf bgp-tunnel {
                type boolean;
                default "false";
                description "Whether the transport tunnel is BGP.";
            }

            leaf sr-isis {
                type boolean;
                default "false";
                description "Whether Segment Routing is enabled for IS-IS.";
            }

            leaf sr-ospf {
                type boolean;
                default "false";
                description "Whether Segment Routing is enabled for OSPF.";
            }

            leaf weighted-ecmp {
                type boolean;
                default "false";
                description "Allow weighted load-balancing on an SDP";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container keep-alive {
                description "Enter the keep-alive context";

                leaf admin-state {
                    type types-sros:admin-state;
                    default "disable";
                    description "Administrative state of keepalive mechanism for the SDP";
                }

                leaf hello-time {
                    type int32 {
                        range "1..3600";
                    }
                    units "seconds";
                    sros-ext:auto-restart-to-modify;
                    default "10";
                    description "How often the SDP Echo Request messages are transmitted on this SDP.";
                }

                leaf hold-down-time {
                    type int32 {
                        range "0..3600";
                    }
                    units "seconds";
                    default "10";
                    description "Amount of time to wait before the keep-alive operating status is eligible to enter the 'alive' state.";
                }

                leaf maximum-drop-count {
                    type int32 {
                        range "1..5";
                    }
                    default "3";
                    description "Maximum number of consecutive SDP Echo Request messages that can be unacknowledged before the keep-alive protocol reports a fault.";
                }

                leaf message-length {
                    type int32 {
                        range "40..9198";
                    }
                    description "Length of the SDP Echo Request messages transmitted on this SDP. The default value of zero indicates that the message length should be equal to the SDP's operating path MTU";
                }

                leaf timeout {
                    type int32 {
                        range "1..10";
                    }
                    units "seconds";
                    default "5";
                    description "Number of seconds to wait for an SDP Echo Response message before declaring a timeout.";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container keep-alive

            container mixed-lsp-mode {
                presence "Enter the 'mixed-lsp-mode' context";
                description "Enable the mixed-lsp-mode context";

                leaf revert-time {
                    type types-services:revert-time;
                    default "immediate";
                    description "Time to wait before reverting back from LDP to the configured LSPs, after having failed over to LDP.";
                }

            } // container mixed-lsp-mode

            container source-bmac-lsb {
                description "Enter the source-bmac-lsb context";

                leaf value {
                    type types-services:bmac-lsb-no-zero;
                    description "16 least significant bits (lsb as 00:00 or 00-00) which when combined with the 32 most significant bits of the PBB source-bmac forms the virtual backbone MAC address.";
                }

                leaf control-pw-vc-id {
                    type types-services:vc-id;
                    description "Spoke-SDP VC identifier to be used as a control pseudo-wire to determine whether Shortest Path Bridging Module (SPBM) advertises the virtual backbone MAC.";
                }

            } // container source-bmac-lsb

            container far-end {
                description "Enter the far-end context";

                choice ip-or-node {
                    case ip {

                        leaf ip-address {
                            type types-sros:ip-address;
                            sros-ext:auto-restart-to-modify;
                            description "Specifies the IP address of the far-end.";
                        }

                    }
                }
            } // container far-end

            container class-forwarding {
                presence "Enter the 'class-forwarding' context";
                description "Enable the class-forwarding context";

                leaf admin-state {
                    type types-sros:admin-state;
                    default "disable";
                    description "Administrative state of class-based forwarding on this SDP";
                }

                leaf default-lsp {
                    type leafref {
                        path "../../lsp/lsp-name";
                    }
                    mandatory true;
                    description "LSP name that is used as a default when class-based forwarding is enabled on this SDP.";
                }

                leaf enforce-diffserv-lsp-fc {
                    type boolean;
                    default "false";
                    description "Whether service manager must validate with RSVP the support of the FC by the LSP.";
                }

                leaf multicast-lsp {
                    type leafref {
                        path "../../lsp/lsp-name";
                    }
                    description "LSP name that all multicast traffic will be forwarded on when class-based forwarding is enabled on this SDP.";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list fc {
                    key "fc-name";
                    description "Enter the fc list instance";

                    leaf fc-name {
                        type types-sros:fc-name;
                        description "Forwarding class for which this mapping is defined.";
                    }

                    leaf lsp {
                        type leafref {
                            path "../../../lsp/lsp-name";
                        }
                        mandatory true;
                        description "LSP name that traffic corresponding to the forwarding class will be forwarded on. It MUST be specified at row creation time.";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list fc

            } // container class-forwarding

            container pw-port {
                description "Enter the pw-port context";

                leaf binding-port {
                    type types-sros:port-named;
                    description "Binding port";
                }

            } // container pw-port

            list sdp-group {
                key "group-name";
                description "Add a list entry for sdp-group";

                leaf group-name {
                    type leafref {
                        path "../../../sdp-group/group-name/group-name";
                    }
                    description "Service Distribution Point (SDP) SDP Group Name.";
                }

            } // list sdp-group

            list lsp {
                key "lsp-name";
                max-elements 16;
                description "Add a list entry for lsp";

                leaf lsp-name {
                    type types-sros:named-item-64;
                    description "LSP name.";
                }

            } // list lsp

        } // list sdp

    } // grouping conf-svc-sdp

}
