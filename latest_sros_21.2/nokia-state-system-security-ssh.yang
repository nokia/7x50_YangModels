submodule nokia-state-system-security-ssh {

    yang-version "1.1";

    belongs-to nokia-state { prefix "state"; }

    import nokia-sros-yang-extensions     { prefix "sros-ext"; }
    import nokia-types-security           { prefix "types-security"; }
    import nokia-types-sros               { prefix "types-sros"; }


    sros-ext:sros-major-release "rel21";

    organization "Nokia";

    contact
        "Nokia SR OS Support
         Web: <http://www.nokia.com>";

    description
        "Nokia YANG Data model with operational state for system security parameters. on SR OS based routers.

         Copyright 2016 Nokia. All rights reserved. Reproduction of this document
         is authorized on the condition that the foregoing copyright notice is included.

         This nokia-state-system-security-ssh YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-09-16";

    grouping state-system-security-ssh {
        container ssh {
            description "Enter the ssh context";

            leaf server-oper-state {
                type types-sros:oper-state;
                description "Current status of the SSH server.";
            }

            leaf rsa-host-fingerprint-v1 {
                type types-security:key-fingerprint;
                description "RSA Host Key Fingerprint.";
            }

            leaf dsa-host-fingerprint-v2 {
                type types-security:key-fingerprint;
                description "DSA Host Key Fingerprint.";
            }

            leaf rsa-host-fingerprint-v2 {
                type types-security:key-fingerprint;
                description "RSA Host Key Fingerprint.";
            }

            leaf-list server-cipher-list-v1-state {
                type enumeration {
                    enum "des"                          { value 2; }
                    enum "3des"                         { value 3; }
                    enum "blowfish"                     { value 6; }
                }
                description "The list of allowed ciphers by the SSH server version 1.";
            }

            leaf-list server-cipher-list-v2-state {
                type enumeration {
                    enum "3des-cbc"                     { value 32; }
                    enum "blowfish-cbc"                 { value 33; }
                    enum "cast128-cbc"                  { value 34; }
                    enum "arcfour"                      { value 35; }
                    enum "aes128-cbc"                   { value 36; }
                    enum "aes192-cbc"                   { value 37; }
                    enum "aes256-cbc"                   { value 38; }
                    enum "rijndael-cbc"                 { value 39; }
                    enum "aes128-ctr"                   { value 40; }
                    enum "aes192-ctr"                   { value 41; }
                    enum "aes256-ctr"                   { value 42; }
                }
                description "The list of allowed ciphers by the SSH server version 2.";
            }

            leaf-list server-mac-list-v2-state {
                type enumeration {
                    enum "hmac-sha2-512"                { value 1; }
                    enum "hmac-sha2-256"                { value 2; }
                    enum "hmac-sha1"                    { value 3; }
                    enum "hmac-sha1-96"                 { value 4; }
                    enum "hmac-md5"                     { value 5; }
                    enum "hmac-ripemd160"               { value 6; }
                    enum "hmac-ripemd160-openssh-com"   { value 7; }
                    enum "hmac-md5-96"                  { value 8; }
                }
                description "The list of allowed MAC algorithms by the SSH server version 2.";
            }

            leaf-list server-kex-list-v2-state {
                type enumeration {
                    enum "diffie-hellman-group1-sha1"   { value 1; }
                    enum "diffie-hellman-group14-sha1"  { value 2; }
                    enum "diffie-hellman-group-exchange-sha1" { value 3; }
                    enum "diffie-hellman-group14-sha256" { value 4; }
                    enum "diffie-hellman-group16-sha512" { value 5; }
                }
                description "The list of allowed KEX algorithms by the SSH server version 2.";
            }

            leaf-list client-cipher-list-v1-state {
                type enumeration {
                    enum "des"                          { value 2; }
                    enum "3des"                         { value 3; }
                    enum "blowfish"                     { value 6; }
                }
                description "The list of allowed ciphers by the SSH client version 1.";
            }

            leaf-list client-cipher-list-v2-state {
                type enumeration {
                    enum "3des-cbc"                     { value 32; }
                    enum "blowfish-cbc"                 { value 33; }
                    enum "cast128-cbc"                  { value 34; }
                    enum "arcfour"                      { value 35; }
                    enum "aes128-cbc"                   { value 36; }
                    enum "aes192-cbc"                   { value 37; }
                    enum "aes256-cbc"                   { value 38; }
                    enum "rijndael-cbc"                 { value 39; }
                    enum "aes128-ctr"                   { value 40; }
                    enum "aes192-ctr"                   { value 41; }
                    enum "aes256-ctr"                   { value 42; }
                }
                description "The list of allowed ciphers by the SSH client version 2.";
            }

            leaf-list client-mac-list-v2-state {
                type enumeration {
                    enum "hmac-sha2-512"                { value 1; }
                    enum "hmac-sha2-256"                { value 2; }
                    enum "hmac-sha1"                    { value 3; }
                    enum "hmac-sha1-96"                 { value 4; }
                    enum "hmac-md5"                     { value 5; }
                    enum "hmac-ripemd160"               { value 6; }
                    enum "hmac-ripemd160-openssh-com"   { value 7; }
                    enum "hmac-md5-96"                  { value 8; }
                }
                description "The list of allowed MAC algorithms by the SSH client version 2.";
            }

            leaf-list client-kex-list-v2-state {
                type enumeration {
                    enum "diffie-hellman-group1-sha1"   { value 1; }
                    enum "diffie-hellman-group14-sha1"  { value 2; }
                    enum "diffie-hellman-group-exchange-sha1" { value 3; }
                    enum "diffie-hellman-group14-sha256" { value 4; }
                    enum "diffie-hellman-group16-sha512" { value 5; }
                }
                description "The list of allowed KEX algorithms by the SSH client version 2.";
            }

            list connection {
                key "session-id";
                description "Enter the connection list instance";

                leaf session-id {
                    type uint32;
                    description "The unique identifier of ssh session.";
                }

                leaf connection-ip {
                    type types-sros:ip-address-with-zone;
                    description "Connection ip address.";
                }

                leaf version {
                    type uint32 {
                        range "1|2";
                    }
                    description "The value indicates the SSH protocol version used for connection.";
                }

                leaf cipher {
                    type enumeration {
                        enum "des"                          { value 2; }
                        enum "3des"                         { value 3; }
                        enum "blowfish"                     { value 6; }
                        enum "3des-cbc"                     { value 32; }
                        enum "blowfish-cbc"                 { value 33; }
                        enum "cast128-cbc"                  { value 34; }
                        enum "arcfour"                      { value 35; }
                        enum "aes128-cbc"                   { value 36; }
                        enum "aes192-cbc"                   { value 37; }
                        enum "aes256-cbc"                   { value 38; }
                        enum "rijndael-cbc"                 { value 39; }
                        enum "aes128-ctr"                   { value 40; }
                        enum "aes192-ctr"                   { value 41; }
                        enum "aes256-ctr"                   { value 42; }
                    }
                    description "Used cipher for the connection.";
                }

                leaf mac {
                    type enumeration {
                        enum "hmac-sha2-512"                { value 1; }
                        enum "hmac-sha2-256"                { value 2; }
                        enum "hmac-sha1"                    { value 3; }
                        enum "hmac-sha1-96"                 { value 4; }
                        enum "hmac-md5"                     { value 5; }
                        enum "hmac-ripemd160"               { value 6; }
                        enum "hmac-ripemd160-openssh-com"   { value 7; }
                        enum "hmac-md5-96"                  { value 8; }
                    }
                    description "Used mac for the connection.";
                }

                leaf kex {
                    type enumeration {
                        enum "diffie-hellman-group1-sha1"   { value 1; }
                        enum "diffie-hellman-group14-sha1"  { value 2; }
                        enum "diffie-hellman-group-exchange-sha1" { value 3; }
                        enum "diffie-hellman-group14-sha256" { value 4; }
                        enum "diffie-hellman-group16-sha512" { value 5; }
                    }
                    description "Used kex for the connection.";
                }

                leaf user {
                    type types-sros:named-item;
                    description "Name of the user.";
                }

                leaf server {
                    type types-sros:named-item;
                    description "Name of the server.";
                }

                leaf router-instance {
                    type types-sros:router-instance;
                    description "The value indicates the routing context of a connection.";
                }

                container key-re-exchange {
                    description "Enter the key-re-exchange context";

                    leaf minutes {
                        type uint32 {
                            range "0..1440";
                        }
                        units "minutes";
                        description "Time left until re-exchange of the ssh Keys.";
                    }

                    leaf mbytes {
                        type uint32 {
                            range "0..64000";
                        }
                        units "megabytes";
                        description "Data limit which starts re-exchange of the ssh Keys.";
                    }

                } // container key-re-exchange

            } // list connection

        } // container ssh

    } // grouping state-system-security-ssh

}
